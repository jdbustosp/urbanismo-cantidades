(defun c:AUDITSOBRE (/ f ss i be d nom over left right nomw area span ancho atts)
  (setq f (open "C:/Users/jdbus/Documents/URBANISMO/work/etapas/audit_sobre.txt" "w"))
  (setq ss (ssget "_X" (list (cons 0 "INSERT") (cons -3 (list (list "URB_VIA"))))) i 0)
  (if ss
    (while (< i (sslength ss))
      (setq be (ssname ss i))
      (setq d (urb:get-xdata-strings be "URB_VIA"))
      (setq atts (urb:block-attribute-values (vlax-ename->vla-object be)))
      (setq nom (urb:safe-string (nth 1 d) "?")
            over (urb:safe-string (nth 13 d) "?")
            left (atof (urb:safe-string (nth 14 d) "0"))
            right (atof (urb:safe-string (nth 15 d) "0"))
            nomw (atof (urb:safe-string (nth 16 d) "0"))
            area (atof (urb:safe-string (nth 17 d) "0"))
            span (atof (urb:safe-string (nth 18 d) "0")))
      (setq ancho (if (> span 1e-9) (/ area span) 0.0))
      (write-line (strcat nom
        " | modo=" over
        " | izq=" (rtos left 2 2) " der=" (rtos right 2 2)
        " | ancho_nominal=" (rtos nomw 2 2)
        " | area=" (rtos area 2 1) " long=" (rtos span 2 1)
        " | ANCHO MEDIO REAL=" (rtos ancho 2 2)
        " | nominal+sobre=" (rtos (+ nomw left right) 2 2)
        " | SOBREANCHO_ATT=" (urb:safe-string (cdr (assoc "VIA_SOBREANCHO_M2" atts)) "?")) f)
      (setq i (1+ i))))
  (write-line "FIN-AUDITSOBRE" f)
  (close f) (princ))
(princ)
