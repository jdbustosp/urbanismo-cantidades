(setq eta:labels (quote (
  ("9D" 83618.015 95836.399)
  ("9C" 83640.138 95949.586)
  ("9B" 83564.348 95988.345)
  ("9A" 83669.049 96177.896)
  ("8D" 83635.184 95375.992)
  ("8C" 83812.309 95365.938)
  ("8B" 83669.051 95529.402)
  ("8A" 83593.306 95669.928)
  ("5G" 83063.252 95206.584)
  ("5F" 83259.847 95287.207)
  ("5A" 82839.08 95299.263)
  ("4E" 83140.813 95346.877)
  ("4A" 83266.196 95574.997)
  ("4" 83066.278 95531.634)
  ("4F" 83231.15 95469.133)
  ("5D" 83046.953 95128.903)
  ("5C" 82910.748 95194.408)
  ("5B" 82964.457 95319.417)
  ("5E" 83162.163 95207.989)
  ("4C" 82965.175 95521.248)
  ("4D" 83042.295 95410.776)
  ("4B" 82910.088 95485.411)
  ("3B" 83581.582 95205.992)
  ("3A" 83433.472 95235.945)
  ("3" 83443.845 95413.057)
  ("7" 82937.217 95818.515)
  ("6" 82705.772 95445.611)
  ("1" 83284.227 96179.76)
  ("2" 83217.282 95723.647)
)))
(princ (strcat "
labels: " (itoa (length eta:labels))))(princ)
