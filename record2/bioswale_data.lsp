;;; polys: lista de (closed (x y bulge) (x y bulge)...)
(setq bios:polys (quote (
  (1
   (83387.6642 95919.3637 0)
   (83352.0289 95928.6143 0)
   (83351.5443 95926.7478 0)
   (83387.1797 95917.4972 0)
  )
  (1
   (83415.3027 96002.5065 0)
   (83374.4535 95974.4092 0)
   (83373.5458 95975.7288 0)
   (83414.3966 96003.824 0)
  )
  (1
   (83431.784 96013.8428 0)
   (83417.4449 96003.98 0)
   (83416.5396 96005.2962 0)
   (83430.8765 96015.1623 0)
  )
  (1
   (83356.9585 95962.4358 0)
   (83339.6519 95950.5313 0)
   (83326.3722 95939.6263 0)
   (83325.352 95940.8698 0)
   (83338.6843 95951.8074 0)
   (83356.0517 95963.754 0)
  )
  (0
   (83326.9029 95933.1445 0)
   (83341.5191 95929.3503 0)
   (83342.0037 95931.2168 0)
   (83327.3875 95935.011 0)
   (83326.9029 95933.1445 0)
  )
)))
(setq bios:ins (quote (
)))
(princ (strcat "
bios: " (itoa (length bios:polys)) " polys, " (itoa (length bios:ins)) " inserts PL1"))(princ)
