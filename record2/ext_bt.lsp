;;; extrae del record BT: segmentos de red ejecutada, cajas y fotometrias
;;; (postes/luminarias) -> rec_bt_raw.txt  (formato: TIPO|x1|y1[|x2|y2])
(defun bt:ws (f x1 y1 x2 y2)
  (write-line (strcat "SEG|" (rtos x1 2 3) "|" (rtos y1 2 3) "|"
    (rtos x2 2 3) "|" (rtos y2 2 3)) f))
(defun bt:emit-poly (f ed / pts g prev)
  (setq pts nil)
  (foreach g ed (if (= 10 (car g)) (setq pts (cons (cdr g) pts))))
  (setq pts (reverse pts) prev nil)
  (foreach p pts
    (if prev (bt:ws f (car prev) (cadr prev) (car p) (cadr p)))
    (setq prev p)))
(defun c:EXTBT (/ f ss i ed ty p q)
  (setq f (open "C:/Users/jdbus/Documents/URBANISMO/work/record2/rec_bt_raw.txt" "w"))
  (setq ss (ssget "_X" '((8 . "0_0 RED BAJA TENSION,0_0 RED BT SUBT PROY,0_0 TUBERIA,0_0 RED DUCTO EXIS,CO_RED_DUCTO_EXIS"))) i 0)
  (while (and ss (< i (sslength ss)))
    (setq ed (entget (ssname ss i)) ty (cdr (assoc 0 ed)))
    (cond
      ((= ty "LINE")
        (setq p (cdr (assoc 10 ed)) q (cdr (assoc 11 ed)))
        (bt:ws f (car p) (cadr p) (car q) (cadr q)))
      ((= ty "LWPOLYLINE") (bt:emit-poly f ed)))
    (setq i (1+ i)))
  (setq ss (ssget "_X" '((0 . "INSERT") (8 . "0_0 CAJAS"))) i 0)
  (while (and ss (< i (sslength ss)))
    (setq ed (entget (ssname ss i)) p (cdr (assoc 10 ed)))
    (write-line (strcat "CAJA|" (rtos (car p) 2 3) "|" (rtos (cadr p) 2 3)) f)
    (setq i (1+ i)))
  (setq ss (ssget "_X" '((0 . "INSERT") (8 . "FOTOM_ROYALPHA"))) i 0)
  (while (and ss (< i (sslength ss)))
    (setq ed (entget (ssname ss i)) p (cdr (assoc 10 ed)))
    (write-line (strcat "FOTO|" (rtos (car p) 2 3) "|" (rtos (cadr p) 2 3)) f)
    (setq i (1+ i)))
  (write-line "FIN-EXTBT" f)
  (close f) (princ))
(princ "\nEXTBT listo")(princ)
