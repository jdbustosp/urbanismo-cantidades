;;; extrae segmentos ejecutados del record MT -> rec_mt_segs.lsp
(defun rmt:ws (f x1 y1 x2 y2)
  (write-line (strcat "  (" (rtos x1 2 3) " " (rtos y1 2 3) " "
    (rtos x2 2 3) " " (rtos y2 2 3) ")") f))
(defun rmt:emit-poly (f ed / pts g prev)
  (setq pts nil)
  (foreach g ed (if (= 10 (car g)) (setq pts (cons (cdr g) pts))))
  (setq pts (reverse pts) prev nil)
  (foreach p pts
    (if prev (rmt:ws f (car prev) (cadr prev) (car p) (cadr p)))
    (setq prev p)))
(defun c:EXTMT (/ f lays ss i ed ty p q lay)
  (setq f (open "C:/Users/jdbus/Documents/URBANISMO/work/record2/rec_mt_segs.lsp" "w"))
  (write-line "(setq rec:mt-segs '(" f)
  (setq lays "0_0 TUBERIA PROY,0_0 RED_MT_SUBT_PROY,0_0 RED MT SUBT PROY,CO_RED_MT_SUBT_PROY,CO_PLUMA_.1_PROY")
  (setq ss (ssget "_X" (list (cons 8 lays))) i 0)
  (while (and ss (< i (sslength ss)))
    (setq ed (entget (ssname ss i)) ty (cdr (assoc 0 ed)))
    (cond
      ((= ty "LINE")
        (setq p (cdr (assoc 10 ed)) q (cdr (assoc 11 ed)))
        (rmt:ws f (car p) (cadr p) (car q) (cadr q)))
      ((= ty "LWPOLYLINE") (rmt:emit-poly f ed))
      ((= ty "ARC")
        (setq p (cdr (assoc 10 ed)))
        (rmt:ws f (+ (car p) (* (cdr (assoc 40 ed)) (cos (cdr (assoc 50 ed)))))
                  (+ (cadr p) (* (cdr (assoc 40 ed)) (sin (cdr (assoc 50 ed)))))
                  (+ (car p) (* (cdr (assoc 40 ed)) (cos (cdr (assoc 51 ed)))))
                  (+ (cadr p) (* (cdr (assoc 40 ed)) (sin (cdr (assoc 51 ed))))))))
    (setq i (1+ i)))
  (write-line "))" f)
  (write-line "(princ (strcat \"\nmt-segs: \" (itoa (length rec:mt-segs))))(princ)" f)
  (close f) (princ))
(princ "\nEXTMT listo")(princ)
