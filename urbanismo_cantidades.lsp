;;; urbanismo_cantidades.lsp
;;; Herramientas para cuantificar andenes y vias a partir de polilineas cerradas.
;;; Compatible con AutoCAD para Windows (Visual LISP / ActiveX).
;;; 5.2.0: diametros de tuberia EDITABLES desde Configuracion, con la
;;;   misma mecanica del catalogo de etapas (la lista vive en la config
;;;   del dibujo: URB_DIAMETROS_ALC / URB_DIAMETROS_ACU). El gestor avisa
;;;   cuando un diametro nuevo no tiene ancho en la tabla de zanja, porque
;;;   su excavacion saldria en cero sin decir nada. Los dialogos de
;;;   creacion dejan de elegir el diametro por defecto por POSICION y lo
;;;   eligen por VALOR: con la lista editable un indice fijo apuntaba a
;;;   otro diametro. Agregado el 45" del GRP.
;;; 5.1.0: la auditoria de cotas deja de BLOQUEAR la exportacion (cinco
;;;   puntos malos impedian actualizar todo el libro); ahora avisa, y los
;;;   elementos con cota invalida no se miden en vez de meter volumenes
;;;   absurdos. La auditoria cubre pozos, sumideros, cabezales y camaras
;;;   (antes solo MP_PUNTO_POZO_*) y reporta LAS DOS COTAS para saber cual
;;;   corregir. Nuevo urb:q-refresh-puntos: la profundidad se rederiva de
;;;   tapa - clave dentro de la preactualizacion que ya corria para los
;;;   tramos, asi que corregir una cota ajusta lo que cuelga de ella.
;;; 4.59.1: fix de raiz -- mp:normalize-tramo-graphics (llamada SIEMPRE
;;;   tras crear un tramo) deshacia el gap correcto de borde de caja en
;;;   MT/BT-AP; usaba el predicado viejo hydro-tramo-p en vez de
;;;   tramo-own-node-blocks-p. Ver PROGRESS.md 2026-08-26 para el detalle.
;;; 4.59.0: alumbrado por circuitos reales (cajas AP-274/275, postes con
;;;   sus luminarias y acometidas, transformador pedestal) en capa
;;;   PPTO-ELECTRICA-BT-AP; filas de ppto de poste/luminaria/acometida/
;;;   trafo alineadas al libro; CIRCUITOS multiplica el cable MT.
;;; 4.58.0: cajas electricas con la simbologia del plano (CS276 tapa doble,
;;;   CS280 con circulo, CS274/275 sencilla, centradas y a escala real
;;;   2.00x1.70) y tramos MT/BT-AP de caja a caja sin recorte visual.
;;; 4.57.6: tramos MT/BT-AP ya no dibujan circulos propios en cada extremo
;;;   (los pozos/cajas ya son bloques puntuales independientes, igual que
;;;   en redes hidrosanitarias) -- se ve la caja real en vez de un circulo.
;;; 4.23.4: estabiliza memorias de vias y evita recalcular superficies al mostrarlas.
;;; 4.23.0: interpola conexiones, incorpora bombeo y memorias con propiedades depuradas.
;;; 4.22.1: simplifica rasantes/propiedades y configura apariencia de tramos.
;;; 4.17.7: evita unidades adicionales por residuos decimales de punto flotante.
;;; 4.17.6: separa giro de 90 grados y cambio del extremo inicial.
;;; 4.17.5: ancla la modulacion al contorno real y evita losetas iniciales cortadas.
;;; 4.17.4: conserva la elevacion y permite invertir la modulacion del anden.
;;; Integra el sentido en la misma XDATA para evitar perdida de metadatos.
;;; 4.17.2: evita confundir los cierres cortos con nuevos brazos del anden.
;;; 4.17.1: orienta andenes irregulares por ejes dominantes locales.
;;; 4.17.0: crea zonas verdes y cuantifica area y tierra negra.
;;; 4.16.6: alinea la cuadrilla al eje largo considerando el UCS del dibujo.
;;; 4.16.4: mantiene franjas transversales y rota correctamente su reticula.
;;; 4.16.3: orienta las franjas de loseta paralelas al eje del anden.
;;; 4.16.2: conserva la correccion grafica aunque las tierras queden pendientes.
;;; 4.16.1: alinea graficamente las losetas con el eje principal del anden.
;;; 4.16.0: calcula y guarda pendientes variables de andenes vinculados a vias.
;;; 4.15.3: simplifica creacion de redes y limpia extremos automaticos huerfanos.
;;; 4.15.2: extrae automaticamente cotas de terreno de redes desde SUP_TN.
;;; 4.15.1: descuenta franjas tactiles del area contractual de adoquin.
;;; 4.15.0: alinea actividades exportadas con los presupuestos de vias y andenes.
;;; 4.14.1: corrige desbordamiento entero al generar el token temporal de sesion.
;;; 4.14.0: controles de integridad, Excel maestro multi-DWG y depuracion general.
;;; 4.13.1: depura el menu principal retirando Mantenimiento e Informacion.
;;; 4.13.0: topologia, geometria 2D/3D, controles y cantidades constructivas de redes.
;;; 4.12.3: corrige exportacion Excel y muestra errores reales sin llamadas invalidas.
;;; 4.12.2: corrige la carga interpretada del recolector de cantidades de redes.
;;; 4.12.1: limpia de la sesion los comandos heredados al recargar.
;;; 4.12.0: interfaz unificada; solo URBANISMO y EDITAR quedan como comandos.
;;; 4.11.3: creacion de redes disponible solo desde el menu URBANISMO.
;;; 4.11.2: funciones Excel disponibles solo desde el menu URBANISMO.
;;; 4.11.1: vinculo compatible con libros XLSX y XLSM sin perder macros.
;;; 4.11.0: tabla Excel unica, vinculo persistente y actualizacion segura.
;;; 4.10.1: exportacion Excel con separadores colombianos y apertura automatica.
;;; 4.10.0: vinculo persistente via-anden y exportacion consolidada a Excel.
;;; Conserva las validaciones y la malla orientada incorporadas en 4.9.0.

(vl-load-com)

(setq *urb-version* "5.7.27")
(setq *urb-road-grade-silent* nil)
;; 5.7.2: contador de cargas por documento (diagnostico de la doble carga)
(setq *urb-load-count* (1+ (if (numberp *urb-load-count*) *urb-load-count* 0)))
(setq *urb-memory-reactor-busy* nil)
(setq *urb-memory-pending* nil)
(setq *urb-memory-command-scheduled* nil)
(setq *urb-schema-version* "23")
(setq *urb-prefab-schema-version* "1")
(setq *urb-green-schema-version* "1")
(setq *urb-excel-table-schema* "2")
(setq *mp-terrain-surface-name* "SUP_TN")
(setq *mp-network-construction-enabled* T)
;; Si no es nil, mp:tramo-depth-profile usa min(terreno,subrasante) en vez
;; de solo terreno -- ver mp:select-road-subrasante-reference. Se pone y se
;; quita alrededor de cada llamada a mp:insert-tramo-forced, nunca queda
;; encendido entre comandos.
(setq *mp-tramo-road-ref* nil)
(setq *mp-suppress-regen* nil)
(setq *urb-pattern-scale* 1.0)
(setq *urb-etapa-list* '("1" "2" "3" "4" "5" "6" "7" "8" "9"))
(setq *urb-material-list* '("Loseta"))
(setq *urb-yes-no-list* '("No" "Si"))
(setq *urb-loseta-format-list* '("40 x 40 cm" "20 x 20 cm"))
(setq *urb-anden-grade-source-list*
  '("Via creada" "Cotas seleccionadas" "Alineamiento + cotas"))
(setq *urb-prefab-list* '("Bordillo" "Sardinel" "Canuela"))
;; 2026-09-11 (pedido del usuario: "define lo referente a los materiales"):
;; los prefabricados que nacen dentro de un modulo de rampa se cobran en EL
;; CAPITULO DE ESE MODULO, no en andenes -- "Suministro sardinel bajo A-85
;; para rampa" solo existe en 2.2.4 (vehicular) y 2.2.5 (peatonal).
(setq *urb-prefab-destinos*
  '("Anden" "Via" "Rampa vehicular" "Rampa peatonal" "Paso peatonal"))

(defun urb:prefab-destino-default (prefab)
  ;; Compatibilidad con bloques anteriores a 4.74.0: conserva la regla
  ;; historica solo cuando el elemento aun no trae destino explicito.
  (if (wcmatch (strcase (urb:safe-string prefab "")) "*SARDINEL*")
    "Via" "Anden"))

(defun urb:prefab-destino-red (destino prefab / value)
  (setq value (strcase (urb:safe-string destino "")))
  ;; 5.7.24 (pedido del usuario 2026-09-23: "todos los sardineles van por
  ;; vias"): el SARDINEL va SIEMPRE al capitulo de via, aunque el bloque
  ;; traiga otro destino. Antes 229 sardineles A-10 caian en ANDENES.
  (if (wcmatch (strcase (urb:safe-string prefab "")) "*SARDINEL*")
    (setq value "VIA"))
  (cond
    ((member value '("VIA")) "VIA")
    ((member value '("ANDEN" "ANDENES")) "ANDEN")
    ((member value '("RAMPA VEHICULAR" "RAMPA-VEHICULAR")) "RAMPA-VEHICULAR")
    ((member value '("RAMPA PEATONAL" "RAMPA-PEATONAL")) "RAMPA-PEATONAL")
    ((member value '("PASO PEATONAL" "PASO-PEATONAL" "PASO PEATONAL SEGURO"))
      "PASO-PEATONAL")
    (T (strcase (urb:prefab-destino-default prefab)))))

;; Largo de la pieza por tipo de prefabricado (m). El libro compra por
;; UNIDAD y mide la instalacion por ML, asi que UN = ML / largo.
;; A-80 = bordillo de 0,80; los sardineles de rampa IDU son de 1,00.
(setq *urb-prefab-largos*
  '(("A-80" . 0.80) ("A-85" . 1.00) ("A-86" . 1.00) ("A-100" . 1.00)
    ("A-10" . 1.00)))

(defun urb:prefab-largo (prefab / tipo res)
  (setq tipo (strcase (urb:safe-string prefab "")) res nil)
  (foreach e *urb-prefab-largos*
    (if (and (null res) (wcmatch tipo (strcat "*" (car e) "*")))
      (setq res (cdr e))))
  (if res res 0.80))

;; Peso por pieza (kg) para la actividad "Transporte de prefabricados" (KG)
;; de los capitulos 2.2.1.2.5 / 2.2.5.2.13 / 2.2.6.2.3. Calculado con el
;; volumen real de cada pieza x 2.400 kg/m3:
;;   adoquin 20x10x6 = 0,20 x 0,10 x 0,06 = 0,0012 m3 ->  2,88 kg
;;   loseta  20x20x6 = 0,20 x 0,20 x 0,06 = 0,0024 m3 ->  5,76 kg
;;   bordillo A-80   = 0,80 x 0,20 x 0,35 = 0,0560 m3 -> 134,40 kg
;;   sardinel A-85   = 1,00 x 0,25 x 0,20 = 0,0500 m3 -> 120,00 kg
;;   sardinel A-86   = 1,00 x 0,35 x 0,20 = 0,0700 m3 -> 168,00 kg
;; Si el proveedor da otros pesos, se cambian SOLO aqui.
(setq *urb-prefab-pesos*
  '(("ADOQUIN" . 2.88) ("LOSETA" . 5.76) ("A-80" . 134.40)
    ("A-85" . 120.00) ("A-86" . 168.00) ("A-100" . 150.00)
    ("A-105" . 100.00)))

(defun urb:prefab-peso (clave / tipo res)
  (setq tipo (strcase (urb:safe-string clave "")) res nil)
  (foreach e *urb-prefab-pesos*
    (if (and (null res) (wcmatch tipo (strcat "*" (car e) "*")))
      (setq res (cdr e))))
  (if res res 0.0))

(defun urb:prefab-conceptos (prefab / tipo)
  ;; Textos contractuales verificados contra urbanismo maipore.xlsx.
  (setq tipo (strcase (urb:safe-string prefab "")))
  (cond
    ;; 2026-09-11 (foto acotada del usuario): los sardineles de rampa del
    ;; libro. En el acceso vehicular el A-85 va en la LONGITUD MAYOR (el
    ;; frente, sobre el bordillo de la via) y el A-80 en las curvas y en la
    ;; longitud menor. Van ANTES del comodin *SARDINEL* para que no se los
    ;; lleve el A-10 generico. La M.O. de los tres es la generica de
    ;; sardinel prefabricado (2.2.4.7.3 / 2.2.2.7.1).
    ((wcmatch tipo "*A-85*")
      (list "Suministro sardinel bajo A-85 para rampa"
            "M.O. instalacion de sardinel prefabricado" "SARDINEL"))
    ((wcmatch tipo "*A-86*")
      (list "Suministro sardinel alto A-86 para rampas"
            "M.O. instalacion de sardinel prefabricado" "SARDINEL"))
    ((wcmatch tipo "*A-100*")
      (list "Suministro sardinel especial A-100 para rampa"
            "M.O. instalacion de sardinel prefabricado" "SARDINEL"))
    ((wcmatch tipo "*SARDINEL*")
      (list "Sardinel prefabricado A-10"
            "M.O. instalación de sardinel prefabricado" "SARDINEL"))
    ((wcmatch tipo "*CANUELA*")
      (list "Suministro de cañuela prefabricada"
            "M.O. instalación de cañuela prefabricada" "BORDILLO"))
    ;; 2026-09-11 (pedido del usuario: capas y presupuesto de los
    ;; prefabricados de las rampas): las aletas del acceso vehicular son la
    ;; pieza de remate A-105 del plano, y en el libro se cuentan por UNIDAD
    ;; (una por aleta), no por metro -- de ahi el cuarto elemento PIEZA.
    ((wcmatch tipo "*A-105*")
      (list "Suministro pieza remate A-105 para rampa"
            "M.O. instalación pieza remate A-105" "BORDILLO" "PIEZA"))
    (T
      (list "Bordillo prefabricado A-80"
            "M.O. instalación de bordillo prefabricado" "BORDILLO"))))
;; anillo perimetral de anden/sendero (v4.50)
(setq *urb-anillo-prefab-list* '("Ninguno" "Bordillo" "Sardinel" "Canuela"))
(setq *urb-anillo-pos-list* '("Externo" "Interno"))
(setq *urb-prefab-mode-list* '("Interior" "Exterior"))
(setq *urb-unit-warning-dwg* nil)
(setq *urb-current-tactile-side-point* nil)
;; Proyeccion exacta del clic sobre el borde que existia cuando el usuario
;; eligio el lado de la via. El contorno se recorta despues contra bordillos y
;; contenedores; conservar solo el clic exterior podia hacer que, tras ese
;; recorte, la cadena opuesta pareciera mas cercana.
(setq *urb-current-tactile-side-anchor* nil)
;; Distancia de la fila de GUIA al borde de la via (m). U-201 usa 2.50 en
;; los modulos de curva (fila tactil intermedia); antes estaba fijo en
;; 1.20. Configurable en un solo lugar por si otro proyecto usa otra.
(setq *urb-guide-offset* 2.50)
;; Par de cotas (inicial final) seleccionadas en el flujo de via modo
;; "Pendiente"; se limpia al terminar cada creacion de via.
(setq *urb-road-picked-cotas* nil)
;; Punto de insercion de la tabla de verificacion de via, puesto SOLO por
;; urb:road-audit-table-command (Cantidades). Si es nil, el calculo de
;; movimiento de tierras NO crea tabla (2026-08-11: ya no se crea sola).
(setq *urb-road-audit-point* nil)
;; Records (distancia-eje cota) del modo Pendiente con 3+ cotas (pozos
;; sobre la via); se limpia al terminar cada creacion de via.
(setq *urb-road-picked-stations* nil)
;; 5.7.2: fuente de cada cota tomada (pozo/via/texto) para el PERFIL
(setq *urb-road-picks-raw* nil *urb-road-picked-sources* nil)
(setq *urb-profile-ask-point* nil)
;; Pendiente en % cuando el usuario solo tiene UNA cota de referencia
;; (2026-09-10: "puede que tenga via al principio pero no al final").
;; Se limpia igual que las otras dos.
(setq *urb-road-picked-slope* nil)
;; Bordes extremos (e1 e2) elegidos al calcular el eje automatico; los
;; sardineles los reutilizan sin repreguntar. Se limpia por creacion.
(setq *urb-road-end-edges* nil)
;; Lado elegido para el toperol/guia ("Arriba"/"Abajo"/"Izquierda"/"Derecha").
;; Tiene prioridad sobre *urb-current-tactile-side-point* en
;; urb:reference-v-edge; se resuelve por-anden con el bbox de cada contorno.
(setq *urb-current-tactile-side-choice* nil)
(setq *urb-surface-cache* nil)
(setq *urb-session-token*
  ;; DATE es un real juliano de aproximadamente 2.46e6. Multiplicarlo y
  ;; pasarlo por ITOA excedia el rango de entero de AutoLISP e interrumpia
  ;; APPLOAD con "bad argument type: fixnump". RTOS evita esa conversion.
  (strcat
    (rtos (getvar "MILLISECS") 2 0)
    "_"
    (vl-string-translate ".," "__" (rtos (getvar "DATE") 2 8))))

(defun urb:temp-file (base extension)
  (strcat (getvar "TEMPPREFIX") base "_" *urb-session-token* extension)
)

(defun urb:patterns-folder (/ root base folder)
  ;; Los patrones ya no se publican en %TEMP% ni agregan esa carpeta completa
  ;; al Support Path. Se usa una carpeta estable y exclusiva de la aplicacion.
  (setq root (getenv "LOCALAPPDATA")
        base
          (strcat
            (if (and root (/= root "")) root (getvar "TEMPPREFIX"))
            "\\UrbanismoCantidades")
        folder (strcat base "\\Patterns"))
  (if (not (vl-file-directory-p base))
    (vl-catch-all-apply 'vl-mkdir (list base)))
  (if (not (vl-file-directory-p folder))
    (vl-catch-all-apply 'vl-mkdir (list folder)))
  folder
)

(defun urb:prompt-tactile-side-point (/ result)
  ;; Un solo click del lado de la via/sardinel: el toperol queda pegado al
  ;; borde del anden mas cercano a ese punto, la guia 1.20m hacia adentro.
  ;; (El desplegable Arriba/Abajo/Izquierda/Derecha que existio brevemente
  ;; se quito a pedido del usuario: con andenes diagonales "arriba/abajo"
  ;; es ambiguo; el click sobre el lado real no.)
  (setq result
    (vl-catch-all-apply
      'getpoint
      (list
        "\nMarque un punto del lado de la VIA/sardinel (lado del toperol): ")))
  ;; GETPOINT devuelve UCS; los vertices del contorno y las operaciones
  ;; ActiveX estan en WCS. Guardar siempre WCS para que un UCS girado no
  ;; invierta el costado elegido.
  (if (vl-catch-all-error-p result) nil
    (if result (trans result 1 0) nil))
)

(defun urb:tactile-side-anchor (points reference / clean ring a b dx dy len2 tval candidate d best best-d)
  ;; Punto del CONTORNO mas cercano al clic. A diferencia de guardar el clic
  ;; tal cual, este ancla identifica geometricamente el costado elegido y no
  ;; cambia si luego el contorno se recorta o si la via queda lejos del anden.
  (setq clean (if points (urb:dedupe-ring-points points) nil))
  (if (and clean reference (> (length clean) 1))
    (progn
      (setq ring (append clean (list (car clean)))
            best nil best-d nil)
      (while (cadr ring)
        (setq a (car ring) b (cadr ring)
              dx (- (car b) (car a))
              dy (- (cadr b) (cadr a))
              len2 (+ (* dx dx) (* dy dy)))
        (if (> len2 1e-16)
          (progn
            (setq tval
              (/ (+ (* (- (car reference) (car a)) dx)
                    (* (- (cadr reference) (cadr a)) dy))
                 len2))
            (setq tval (max 0.0 (min 1.0 tval))
                  candidate
                    (list (+ (car a) (* tval dx))
                          (+ (cadr a) (* tval dy)))
                  d (distance (list (car reference) (cadr reference)) candidate))
            (if (or (null best-d) (< d best-d))
              (setq best candidate best-d d))))
        (setq ring (cdr ring)))
      best)
    nil)
)

;; El costado tactil es una decision de diseno, no una propiedad que se
;; pueda volver a inferir con seguridad despues de recortar el contorno.
;; Se guarda como un ancla WCS independiente para que EDITAR, una rampa o
;; un contenedor no puedan mandar la guia/toperol al costado contrario.
(defun urb:set-tactile-side-data (ename anchor)
  (if (and (urb:valid-ename-p ename) anchor
           (numberp (car anchor)) (numberp (cadr anchor)))
    (urb:set-xdata-strings ename "URB_ANDEN_SIDE"
      (list (rtos (car anchor) 2 10) (rtos (cadr anchor) 2 10)))
    (if (urb:valid-ename-p ename)
      (urb:set-xdata-strings ename "URB_ANDEN_SIDE" nil))))

(defun urb:tactile-side-data (ename / data)
  (setq data
    (if (urb:valid-ename-p ename)
      (urb:get-xdata-strings ename "URB_ANDEN_SIDE") nil))
  (if (and data (> (length data) 1)
           (/= (car data) "") (/= (cadr data) ""))
    (list (atof (car data)) (atof (cadr data)))
    nil))

(defun urb:confirm-tactile-side (ename / points corners chains chain chosen other temp answer result)
  ;; Resaltar la MISMA cadena que consume el constructor tactil. Un punto
  ;; en su mitad, en vez del clic junto a un remate, fija el costado sin empate.
  (setq points (urb:lwpoly-points-with-arcs-fine ename))
  (if (not (vl-some '(lambda (p)
            (and (= (car p) 42) (not (equal (cdr p) 0.0 1e-12)))) (entget ename)))
    (setq points (urb:ring-remove-notches points)))
  (setq chosen (urb:anden-tactile-chain points)
        corners (urb:polygon-corner-indices points (* pi 0.25))
        chains (urb:polygon-chains-at-corners points corners))
  (foreach chain chains
    (if (and (not (equal chain chosen 1e-7))
             (or (null other) (> (urb:chain-total-length chain)
                                (urb:chain-total-length other))))
      (setq other chain)))
  (if (and chosen other)
    (progn
      (progn
        (setq temp (urb:poly-chain-polyline
          (mapcar '(lambda (p) (list (car p) (cadr p) 0.0)) chosen)))
        (urb:highlight-chain temp)
        (initget "1 2")
        (setq answer (vl-catch-all-apply 'getkword
          (list "\nTOPEROL: 1 = costado resaltado, 2 = costado opuesto [1/2] <1>: ")))
        (setq result (urb:curve-pt temp (* 0.5 (urb:curve-length temp))))
        (urb:set-chain-highlight temp nil)
        (entdel temp)
        (redraw)
        (if (vl-catch-all-error-p answer) (quit))
        (if (= answer "2")
          (progn
            (setq temp (urb:poly-chain-polyline
              (mapcar '(lambda (p) (list (car p) (cadr p) 0.0)) other)))
            (setq result (urb:curve-pt temp (* 0.5 (urb:curve-length temp))))
            (entdel temp))))
      (setq *urb-current-tactile-side-choice* nil
            *urb-current-tactile-side-point* result
            *urb-current-tactile-side-anchor* result)
      (urb:set-tactile-side-data ename result)))
  result)

(defun urb:tactile-side-point-from-choice
  (choice points / minx miny maxx maxy pt cx cy diag)
  ;; Traduce una eleccion de lado (Arriba/Abajo/Izquierda/Derecha, en
  ;; coordenadas de mundo/pantalla) a un punto sintetico muy afuera del
  ;; bbox del contorno, del lado pedido. Ya NO esta expuesta en la
  ;; interfaz (el usuario marca un punto con click); se conserva como
  ;; mecanismo interno para las verificaciones headless, que necesitan
  ;; fijar un lado sin emular clicks (global *urb-current-tactile-side-choice*).
  (if (null points)
    nil
    (progn
      (setq minx (car (car points)) maxx minx
            miny (cadr (car points)) maxy miny)
      (foreach pt (cdr points)
        (if (< (car pt) minx) (setq minx (car pt)))
        (if (> (car pt) maxx) (setq maxx (car pt)))
        (if (< (cadr pt) miny) (setq miny (cadr pt)))
        (if (> (cadr pt) maxy) (setq maxy (cadr pt))))
      (setq cx (* 0.5 (+ minx maxx)) cy (* 0.5 (+ miny maxy)))
      (setq diag (max 1.0 (distance (list minx miny) (list maxx maxy))))
      (cond
        ((= choice "Arriba") (list cx (+ maxy diag)))
        ((= choice "Abajo") (list cx (- miny diag)))
        ((= choice "Izquierda") (list (- minx diag) cy))
        ((= choice "Derecha") (list (+ maxx diag) cy))
        (T nil))))
)

;; Marcas de sesion: fuerzan a reescribir los DCL temporales tras recargar el LSP.
(setq *urb-anden-dcl-ok* nil)
(setq *urb-prefab-dcl-ok* nil)
(setq *urb-green-dcl-ok* nil)
(setq *urb-stage-dcl-ok* nil)
;; dialogos del PRESUPUESTO (v4.31): sin este reset, recargar un LSP con
;; DCL cambiado reutilizaba el .dcl viejo cacheado en temp
(setq *urb-ppto-match-dcl-ok* nil)
(setq *urb-ppto-match2-dcl-okB* nil)
(setq *urb-ppto-view-dcl-ok* nil)
(setq *urb-ppto-param-dcl-okB* nil)
(setq *urb-ppto-prev-dcl-ok* nil)
(setq *urb-ppto-libro-dcl-ok* nil)
(setq *urb-ppto-hoja-dcl-ok* nil)
(setq *urb-ppto-vinc-dcl-ok* nil)
(setq *urb-ppto-params-dcl-ok* nil)
(setq *urb-mob-dcl-ok* nil)
(setq *urb-rampa-dcl-ok* nil)
(setq *urb-loc-dcl-ok* nil)

(defun urb:safe-string (value default)
  (cond
    ((eq (type value) 'STR) value)
    ((eq value T) "Si")
    ((null value) default)
    (T (vl-princ-to-string value)))
)

(defun urb:string-equal-p (left right)
  (= (strcase (urb:safe-string left ""))
     (strcase (urb:safe-string right "")))
)

(defun urb:yes-p (value)
  (urb:string-equal-p value "Si")
)

;; Normaliza referencias antes de cruzar la frontera ENAME/ActiveX.
;; Nunca acepta T como si fuera una entidad: ese valor produjo el error
;; "unable to get ObjectID: T" durante el calculo de un anden.
(defun urb:valid-ename-p (value / result)
  (if (= (type value) 'ENAME)
    (progn
      (setq result (vl-catch-all-apply 'entget (list value)))
      (and (not (vl-catch-all-error-p result)) result))
    nil)
)

(defun urb:valid-vla-object-p (value / result)
  (if (= (type value) 'VLA-OBJECT)
    (progn
      (setq result (vl-catch-all-apply 'vla-get-Handle (list value)))
      (and (not (vl-catch-all-error-p result)) result))
    nil)
)

(defun urb:as-ename (value / result)
  (cond
    ((urb:valid-ename-p value) value)
    ((urb:valid-vla-object-p value)
      (setq result
        (vl-catch-all-apply 'vlax-vla-object->ename (list value)))
      (if (and (not (vl-catch-all-error-p result))
               (urb:valid-ename-p result))
        result
        nil))
    (T nil))
)

(defun urb:as-vla-object (value / ename result)
  (cond
    ((urb:valid-vla-object-p value) value)
    ((setq ename (urb:as-ename value))
      (setq result
        (vl-catch-all-apply 'vlax-ename->vla-object (list ename)))
      (if (and (not (vl-catch-all-error-p result))
               (urb:valid-vla-object-p result))
        result
        nil))
    (T nil))
)

;; Convierte entradas decimales con punto o coma. Tambien reconoce los dos
;; formatos con miles: 1.234,56 (Colombia) y 1,234.56 (internacional).
(defun urb:remove-character (text character)
  (vl-list->string
    (vl-remove (ascii character) (vl-string->list text))))

(defun urb:parse-real (value / text comma-pos dot-pos parsed)
  (setq text (vl-string-trim " " (urb:safe-string value ""))
        comma-pos (vl-string-position 44 text 0 T)
        dot-pos (vl-string-position 46 text 0 T))
  (cond
    ((and comma-pos dot-pos)
      (if (> comma-pos dot-pos)
        (setq text
          (vl-string-translate "," "." (urb:remove-character text ".")))
        (setq text (urb:remove-character text ","))))
    (comma-pos (setq text (vl-string-translate "," "." text))))
  (if (/= text "")
    (progn
      (setq parsed (vl-catch-all-apply 'distof (list text 2)))
      (if (vl-catch-all-error-p parsed) nil parsed))
    nil)
)

;; Todas las cantidades del programa se expresan en m, m2 y m3. No se
;; convierte el dibujo automaticamente: se exige confirmacion una vez por
;; DWG cuando INSUNITS no declara metros.
(defun urb:confirm-meter-units (/ units drawing choice)
  (setq units (getvar "INSUNITS"))
  (setq drawing
    (strcase
      (strcat (urb:safe-string (getvar "DWGPREFIX") "")
              (urb:safe-string (getvar "DWGNAME") ""))))
  (cond
    ((= units 6) T)
    ((= drawing *urb-unit-warning-dwg*) T)
    (T
      (initget "Si No")
      (setq choice
        (getkword
          (strcat
            "\nEl dibujo no tiene INSUNITS en metros (codigo "
            (itoa units)
            "). El programa supone 1 unidad = 1 m."
            " Continuar [Si/No] <No>: ")))
      (if (= choice "Si")
        (progn (setq *urb-unit-warning-dwg* drawing) T)
        nil)))
)

;; Remove public commands left in memory by older versions.
(foreach old-command
  '(c:EDITARANDEN c:UNIFICARANDEN c:LIMPIARANDEN
    c:AGRUPARANDEN c:REPARARANDEN c:AREAANDEN
    c:URBANDEN c:URBLOSETA c:BORDILLO c:SARDINEL c:CANUELA
    c:URBVIA c:URBCANT c:URBAYUDA
    c:AP c:BT c:INS_TRAMO_BT_AP
    c:CAJA_ELECTRICA c:CAJA_ELEC c:INS_ELEM_ELEC
    c:INS_ACC_ACUEDUCTO c:ACC_ACUEDUCTO
    c:AGUAS_LLUVIAS c:INS_TRAMO_RED
    c:SANITARIO c:PLUVIAL c:ACUEDUCTO
    c:MT c:MEDIA_TENSION c:MEDIATENSION c:ALUMBRADO c:INS_TRAMO_MT)
  (vl-catch-all-apply 'vl-acad-undefun (list old-command)))

;; --- Etapas/subetapas EDITABLES y des/habilitables (2026-08-11) ------
;; El catalogo vive en la configuracion del dibujo (URB_ETAPAS_CATALOGO,
;; misma mecanica que los perfiles de via); el interruptor global en
;; URB_ETAPAS_ACTIVO. Se administra desde Ajustes -> Etapas y subetapas
;; (urb:etapas-manager-command). Con etapas DESHABILITADAS, los popups
;; "etapa"/"subetapa" de TODOS los dialogos de creacion quedan grises
;; (centralizado en urb:fill-popup y mp:fill-popup) y los elementos se
;; crean con la etapa por defecto.
(defun urb:default-etapas-catalog ()
  (list
    (list "1" (list "1"))
    (list "2" (list "2"))
    (list "3" (list "3" "3A" "3B"))
    (list "4" (list "4" "4A" "4B" "4C" "4D" "4E"))
    (list "5" (list "5A" "5B" "5C" "5D" "5E"))
    (list "6" (list "6"))
    (list "7" (list "7"))
    (list "8" (list "8A" "8B" "8C"))
    (list "9" (list "9A" "9B" "9C" "9D" "9E"))))
(setq *urb-etapas-catalog* (urb:default-etapas-catalog))

(defun urb:refresh-etapas-catalog (/ raw parsed)
  ;; corre al cargar el lsp (despues de que exista urb:config-read) y
  ;; tras cada edicion del catalogo
  (setq raw (urb:config-read "URB_ETAPAS_CATALOGO"))
  (if (and raw (/= raw ""))
    (progn
      (setq parsed (urb:read-lisp-safe raw))
      (if (and parsed (listp parsed) (listp (car parsed)))
        (setq *urb-etapas-catalog* parsed))))
  (setq *urb-etapa-list* (mapcar 'car *urb-etapas-catalog*))
  (setq *mp-etapa-list* *urb-etapa-list*)
  (princ))

(defun urb:save-etapas-catalog ()
  (urb:config-write "URB_ETAPAS_CATALOGO"
    (urb:serialize-lisp *urb-etapas-catalog*))
  (setq *urb-etapa-list* (mapcar 'car *urb-etapas-catalog*))
  (setq *mp-etapa-list* *urb-etapa-list*))

(defun urb:etapas-enabled-p ()
  (/= (urb:safe-string (urb:config-read "URB_ETAPAS_ACTIVO") "1") "0"))

;; separa "3,3A,3B" (o con ; o espacios) en lista limpia de strings
(defun urb:split-subetapas (text / result token i c)
  (setq text (urb:safe-string text "") result nil token "" i 1)
  (while (<= i (strlen text))
    (setq c (substr text i 1))
    (if (member c '("," ";" " "))
      (progn
        (if (/= token "") (setq result (cons token result)))
        (setq token ""))
      (setq token (strcat token c)))
    (setq i (1+ i)))
  (if (/= token "") (setq result (cons token result)))
  (reverse result))

(defun urb:etapas-print-catalog (/ entry linea)
  (prompt
    (strcat "\nEtapas "
      (if (urb:etapas-enabled-p) "HABILITADAS" "DESHABILITADAS (grises en los dialogos)")
      ":"))
  (foreach entry *urb-etapas-catalog*
    (setq linea "")
    (foreach s (cadr entry)
      (setq linea (strcat linea (if (= linea "") "" ", ") s)))
    (prompt (strcat "\n  Etapa " (car entry) " -> subetapas: " linea)))
  (princ))

;; texto "3A,3B" de las subetapas de una etapa (para el edit_box)
(defun urb:etapas-subs-string (etapa / linea)
  (setq linea "")
  (foreach s (urb:subetapas-for etapa)
    (setq linea (strcat linea (if (= linea "") "" ",") s)))
  linea)

(defun urb:etapas-replace-at (i newentry / k out entry)
  (setq k 0 out nil)
  (foreach entry *urb-etapas-catalog*
    (setq out (cons (if (= k i) newentry entry) out))
    (setq k (1+ k)))
  (setq *urb-etapas-catalog* (reverse out)))

(defun urb:etapas-remove-at (i / k out entry)
  (setq k 0 out nil)
  (foreach entry *urb-etapas-catalog*
    (if (/= k i) (setq out (cons entry out)))
    (setq k (1+ k)))
  (setq *urb-etapas-catalog* (reverse out)))

;; Gestor de Ajustes -> Etapas y subetapas (2026-08-11 v2: CUADRO DE
;; DIALOGO con desplegables, pedido del usuario -- no menu de linea de
;; comandos). El dialogo se reabre tras cada operacion para refrescar la
;; lista; el toggle Habilitadas se persiste en cada salida. Con etapas
;; deshabilitadas, los popups etapa/subetapa de los dialogos de creacion
;; quedan grises (urb:fill-popup / mp:fill-popup).
(defun urb:etapas-manager-command
  (/ filename dcl-id done code idx activo subs nueva nuevasubs lst etapa)
  (urb:refresh-etapas-catalog)
  (setq done nil idx 0)
  (while (not done)
    (setq filename (urb:write-main-menu-dcl))
    (setq dcl-id (if filename (load_dialog filename) -1))
    (if (and dcl-id (> dcl-id 0) (new_dialog "urb_etapas" dcl-id))
      (progn
        (if (>= idx (length *urb-etapa-list*)) (setq idx 0))
        ;; llenado DIRECTO (sin urb:fill-popup: esa pondria gris el popup
        ;; del propio gestor cuando las etapas estan deshabilitadas)
        (start_list "etapa")
        (mapcar 'add_list *urb-etapa-list*)
        (end_list)
        (set_tile "etapa" (itoa idx))
        (set_tile "activo" (if (urb:etapas-enabled-p) "1" "0"))
        (set_tile "subs" (urb:etapas-subs-string (nth idx *urb-etapa-list*)))
        (action_tile "etapa"
          (strcat
            "(setq idx (atoi $value))"
            "(set_tile \"subs\" (urb:etapas-subs-string (nth idx *urb-etapa-list*)))"))
        (action_tile "guardar"
          "(setq activo (get_tile \"activo\") subs (get_tile \"subs\"))(done_dialog 2)")
        (action_tile "quitar"
          "(setq activo (get_tile \"activo\"))(done_dialog 3)")
        (action_tile "agregar"
          "(setq activo (get_tile \"activo\") nueva (get_tile \"nueva\") nuevasubs (get_tile \"nuevasubs\"))(done_dialog 4)")
        (action_tile "restaurar"
          "(setq activo (get_tile \"activo\"))(done_dialog 5)")
        (action_tile "accept"
          "(setq activo (get_tile \"activo\"))(done_dialog 1)")
        (setq code (start_dialog))
        (unload_dialog dcl-id)
        (if activo
          (progn
            (urb:config-write "URB_ETAPAS_ACTIVO" (if (= activo "1") "1" "0"))
            ;; 2026-08-12: los tiles etapa/subetapa se OCULTAN (no se
            ;; emiten en el DCL) cuando las etapas estan deshabilitadas;
            ;; se invalidan los caches para que los dialogos de creacion
            ;; se regeneren con el estado nuevo del toggle.
            (setq *urb-anden-dcl-ok* nil
                  *urb-prefab-dcl-ok* nil
                  *urb-green-dcl-ok* nil
                  *urb-stage-dcl-ok* nil
                  *mp-dcl-listas-ok* nil
                  *mp-dcl-puntos-ok* nil)))
        (cond
          ((= code 2)
            (setq lst (urb:split-subetapas subs))
            (setq etapa (nth idx *urb-etapa-list*))
            (if (and lst etapa)
              (progn
                (urb:etapas-replace-at idx (list etapa lst))
                (urb:save-etapas-catalog))
              (alert "Escriba al menos una subetapa.")))
          ((= code 3)
            (if (<= (length *urb-etapas-catalog*) 1)
              (alert "Debe quedar al menos una etapa.")
              (progn
                (urb:etapas-remove-at idx)
                (urb:save-etapas-catalog)
                (setq idx 0))))
          ((= code 4)
            (setq nueva (vl-string-trim " " (urb:safe-string nueva "")))
            (cond
              ((= nueva "") (alert "Escriba el nombre de la etapa nueva."))
              ((assoc nueva *urb-etapas-catalog*) (alert "Esa etapa ya existe."))
              (T
                (setq lst (urb:split-subetapas nuevasubs))
                (if (null lst) (setq lst (list nueva)))
                (setq *urb-etapas-catalog*
                  (append *urb-etapas-catalog* (list (list nueva lst))))
                (urb:save-etapas-catalog)
                (setq idx (1- (length *urb-etapa-list*))))))
          ((= code 5)
            (setq *urb-etapas-catalog* (urb:default-etapas-catalog))
            (urb:save-etapas-catalog)
            (setq idx 0))
          (T (setq done T))))
      (progn
        (prompt "\nNo se pudo abrir el dialogo de etapas.")
        (setq done T))))
  (princ))

(defun urb:subetapas-for (etapa / entry)
  (setq entry (assoc etapa *urb-etapas-catalog*))
  (if entry (cadr entry) (list (urb:safe-string etapa "1")))
)

(defun urb:index-of (value items / index found)
  (setq value (urb:safe-string value ""))
  (setq index 0)
  (while (and items (null found))
    (if (= (strcase value) (strcase (car items)))
      (setq found index)
      (progn
        (setq index (1+ index))
        (setq items (cdr items))))
  )
  (if found found 0)
)

(defun urb:fill-popup (key items selected)
  (start_list key)
  (mapcar 'add_list items)
  (end_list)
  (set_tile key (itoa selected))
  ;; etapas deshabilitadas -> el popup queda gris en TODOS los dialogos
  (if (and (member key '("etapa" "subetapa"))
           (not (urb:etapas-enabled-p)))
    (mode_tile key 1))
)

(defun urb:dialog-update-subetapa ()
  (setq *urb-dialog-etapa*
    (nth (atoi (get_tile "etapa")) *urb-etapa-list*))
  (urb:fill-popup
    "subetapa"
    (urb:subetapas-for *urb-dialog-etapa*)
    0)
)

(defun urb:write-dialog-dcl (prefix cache-flag lines / filename stream)
  ;; Helper generico compartido por write-anden-dcl/write-prefab-dcl/write-green-dcl:
  ;; cache-flag es un simbolo citado ('*urb-x-dcl-ok*) para leer/escribir el flag
  ;; de cache de cada dialogo sin duplicar la logica de escritura del .dcl.
  (setq filename (urb:temp-file prefix ".dcl"))
  (cond
    ((and (eval cache-flag) (findfile filename)) filename)
    ((setq stream (open filename "w"))
      (foreach line lines (write-line line stream))
      (close stream)
      (set cache-flag T)
      filename)
    (T nil))
)

;; 2026-09-07 (rediseño pedido por el usuario): el dialogo va por DOS
;; niveles -- Tipologia = CATEGORIA (Andenes / Senderos / Equipamientos)
;; y Material/acabado = la VARIANTE de esa categoria.
;; La rampa salio de aqui (tiene su boton propio). El bloque de
;; movimiento de tierras desaparecio: la superficie se reconoce sola
;; (SUP_TN) y tras dibujar solo se piden las COTAS DE IMPLANTACION (una
;; o varias) con el picker universal. Guia/toperol/formato solo aplican
;; a Anden en Loseta (se deshabilitan en vivo para el resto).
(setq *urb-elem-categorias*
  '("Andenes" "Senderos" "Equipamientos"))
;; variantes por categoria: (etiqueta . codigo de *urb-send-tipos*);
;; codigo "" = anden nativo en loseta (todo el motor de losetas)
(setq *urb-elem-variantes*
  '(("Andenes" ("Loseta" . "") ("Concreto" . "ANDEN-CONC"))
    ;; 5.6.2 (pedido del usuario): los materiales de la convencion del
    ;; plano. Fuera de la lista a proposito: B1 anden propuesto (es
    ;; Andenes), B5-C ciclorruta existente (no se construye), verde plano,
    ;; verde talud, lamina de agua y gavion existente.
    ("Senderos" ("Sendero ecologico en mulch (B2-A)" . "SEND-MULCH-ECO")
                 ("Sendero de trote en mulch (B2-B)" . "SEND-MULCH-TROTE")
                 ("Sendero en concreto ocre (B3)" . "SEND-CONC-OCRE")
                 ("Ecopavimento (B4)" . "SEND-ECOPAV")
                 ("Ciclorruta propuesta (B5-A)" . "CICLORRUTA")
                 ("Bicicarril propuesto (B5-B)" . "BICICARRIL")
                 ("Superficie en caucho reciclado (B6)" . "SEND-CAUCHO")
                 ("Superficie en deck de madera plastica (B7)" . "SEND-DECK"))
    ("Equipamientos"
      ("Concreto - plazoleta" . "PLAZOLETA")
      ("Sintetico - cancha" . "CANCHA-SINT")
      ("Asfalto - cancha multiple" . "CANCHA-MULT")
      ("Skatepark" . "SKATEPARK")
      ("Escaleras en concreto" . "ESCALERA")
      ("Graderia en concreto" . "GRADERIA")
      ("Pista de trote (caucho)" . "PISTA-CAUCHO")
      ("Parque de ninos (piso)" . "PARQUE-NINOS")
      ("Zona gym biosaludable (piso)" . "ZONA-GYM")
      ("Biciparqueo (piso)" . "BICIPARQUEO"))))

(defun urb:elem-variantes-de (cat)
  (cdr (assoc cat *urb-elem-variantes*)))

;; refresca el popup de variantes y habilita/deshabilita los tiles de
;; loseta segun la seleccion actual (corre en vivo desde action_tile)
(defun urb:anden-refresh-variantes (cat-idx / cat vars)
  (setq cat (nth cat-idx *urb-elem-categorias*))
  (setq vars (urb:elem-variantes-de cat))
  (urb:fill-popup "material" (mapcar 'car vars) 0)
  (urb:anden-refresh-loseta cat-idx 0))

(defun urb:anden-refresh-loseta (cat-idx mat-idx / cat vars es-loseta modo)
  (setq cat (nth cat-idx *urb-elem-categorias*))
  (setq vars (urb:elem-variantes-de cat))
  (setq es-loseta
    (and (= cat "Andenes")
         (= (urb:safe-string (cdr (nth mat-idx vars)) "") "")))
  (setq modo (if es-loseta 0 1))
  (mode_tile "formato" modo)
  (mode_tile "guia" modo)
  (mode_tile "toperol" modo))

(defun urb:write-anden-dcl ()
  (urb:write-dialog-dcl
    "urbanismo_anden"
    '*urb-anden-dcl-ok*
    (list
      "urbanismo_anden : dialog { label = \"Datos del elemento de urbanismo\";"
      ": boxed_column { label = \"Clasificacion\";"
      ": popup_list { label = \"Tipologia\"; key = \"tipoelem\"; }"
      ": popup_list { label = \"Material / acabado\"; key = \"material\"; }"
      ": popup_list { label = \"Formato de loseta\"; key = \"formato\"; }"
      ;; 2026-08-12: si las etapas estan deshabilitadas los tiles NO se
      ;; emiten (pedido del usuario: ocultar, no engrisar). El gestor de
      ;; etapas resetea *urb-anden-dcl-ok* al cambiar el toggle.
      (if (urb:etapas-enabled-p)
        ": popup_list { label = \"Etapa\"; key = \"etapa\"; }" "")
      (if (urb:etapas-enabled-p)
        ": popup_list { label = \"Subetapa\"; key = \"subetapa\"; }" "")
      "}"
      ": boxed_column { label = \"Accesibilidad (solo loseta)\";"
      ": popup_list { label = \"Loseta guia\"; key = \"guia\"; }"
      ": popup_list { label = \"Loseta toperol\"; key = \"toperol\"; }"
      "}"
      ;; 5.6.2 (pedido del usuario): fuera la seccion de prefabricado por
      ;; costados. Se elige DESPUES de dibujar, costado por costado, como
      ;; en las vias (tipo, sentido y tramos sin prefabricado).
      ": text { label = \"Prefabricados: despues de dibujar se elige costado por costado.\"; }"
      ": text { label = \"Contenedores existentes se omiten solos: dibuje el contorno exterior sin rodearlos.\"; }"
      ": text { label = \"Al dibujar: superficie SUP_TN automatica + cotas de implantacion.\"; }"
      " ok_cancel; }"))
)

(defun urb:dialog-anden
  (current-material current-format current-etapa current-subetapa
   current-guia current-toperol current-calculate current-surface current-grade-source
   current-orientation current-start orientation-list start-list
   / filename dcl-id accepted subetapas result surfaces)
  ;; orientation-list/start-list vienen del llamador porque EDITAR necesita
  ;; la opcion extra "Conservar" (mantener el sentido de cada anden) que en
  ;; la creacion no tiene sentido. El lado de la via/toperol NO va en el
  ;; dialogo: se marca con un click despues de dibujar (urb:prompt-tactile-side-point).
  (setq filename (urb:write-anden-dcl))
  (setq current-material (urb:safe-string current-material "Loseta"))
  (setq current-format (urb:safe-string current-format "40 x 40 cm"))
  (setq current-etapa (urb:safe-string current-etapa "1"))
  (setq current-subetapa (urb:safe-string current-subetapa current-etapa))
  (setq current-guia (urb:safe-string current-guia "No"))
  (setq current-toperol (urb:safe-string current-toperol "No"))
  (setq current-calculate (urb:safe-string current-calculate "Si"))
  (setq current-grade-source (urb:safe-string current-grade-source "Via creada"))
  (setq current-orientation
    (urb:safe-string current-orientation (car orientation-list)))
  (setq current-start (urb:safe-string current-start (car start-list)))
  (setq surfaces (urb:civil-surface-names))
  (setq current-surface
    (urb:safe-string current-surface
      (if surfaces (car surfaces) "Seleccionar en dibujo")))
  (setq surfaces (urb:add-unique-string current-surface surfaces))
  (if (and filename
           (> (setq dcl-id (load_dialog filename)) 0)
           (new_dialog "urbanismo_anden" dcl-id))
    (progn
      ;; 2026-09-07: dos niveles -- categoria + variante dependiente
      (urb:fill-popup "tipoelem" *urb-elem-categorias* 0)
      (urb:anden-refresh-variantes 0)
      (action_tile "tipoelem"
        "(urb:anden-refresh-variantes (atoi $value))")
      (action_tile "material"
        "(urb:anden-refresh-loseta (atoi (get_tile \"tipoelem\")) (atoi $value))")
      (urb:fill-popup
        "formato"
        *urb-loseta-format-list*
        (urb:index-of current-format *urb-loseta-format-list*))
      ;; 2026-08-12: etapa/subetapa solo existen en el DCL cuando las
      ;; etapas estan habilitadas -- get_tile sobre un tile ausente truena,
      ;; asi que todo lo relacionado va condicionado.
      (if (urb:etapas-enabled-p)
        (progn
          (urb:fill-popup
            "etapa"
            *urb-etapa-list*
            (urb:index-of current-etapa *urb-etapa-list*))
          (setq *urb-dialog-etapa*
            (nth (atoi (get_tile "etapa")) *urb-etapa-list*))
          (setq subetapas (urb:subetapas-for *urb-dialog-etapa*))
          (urb:fill-popup
            "subetapa"
            subetapas
            (urb:index-of current-subetapa subetapas))
          (action_tile "etapa" "(urb:dialog-update-subetapa)")))
      (urb:fill-popup
        "guia"
        *urb-yes-no-list*
        (urb:index-of current-guia *urb-yes-no-list*))
      (urb:fill-popup
        "toperol"
        *urb-yes-no-list*
        (urb:index-of current-toperol *urb-yes-no-list*))
      (action_tile
        "accept"
        (strcat
          "(setq *urb-dialog-material-index* (atoi (get_tile \"material\"))"
          " *urb-dialog-format-index* (atoi (get_tile \"formato\"))"
          (if (urb:etapas-enabled-p)
            (strcat
              " *urb-dialog-etapa-index* (atoi (get_tile \"etapa\"))"
              " *urb-dialog-subetapa-index* (atoi (get_tile \"subetapa\"))")
            "")
          " *urb-dialog-guia-index* (atoi (get_tile \"guia\"))"
          " *urb-dialog-toperol-index* (atoi (get_tile \"toperol\"))"
          " *urb-dialog-tipoelem-index* (atoi (get_tile \"tipoelem\")))"
          "(done_dialog 1)"))
      (setq accepted (= 1 (start_dialog)))
      (unload_dialog dcl-id)
      (if accepted
        (progn
          ;; 2026-09-07: el material del ANDEN nativo sigue siendo Loseta
          ;; (el motor de losetas); la VARIANTE elegida viaja en nth 14
          (setq current-material "Loseta")
          (setq current-format
            (nth *urb-dialog-format-index* *urb-loseta-format-list*))
          (if (urb:etapas-enabled-p)
            (progn
              (setq current-etapa
                (nth *urb-dialog-etapa-index* *urb-etapa-list*))
              (setq subetapas (urb:subetapas-for current-etapa))
              (setq current-subetapa
                (nth *urb-dialog-subetapa-index* subetapas))))
          (setq current-guia
            (nth *urb-dialog-guia-index* *urb-yes-no-list*))
          (setq current-toperol
            (nth *urb-dialog-toperol-index* *urb-yes-no-list*))
          ;; Movimiento de tierras SIEMPRE se calcula (2026-08-12);
          ;; 2026-09-07: superficie AUTOMATICA (SUP_TN si existe, si no
          ;; la primera del dibujo) y rasante por cotas de implantacion
          (setq current-calculate "Si")
          (setq current-surface
            (if (member "SUP_TN" surfaces) "SUP_TN" (car surfaces)))
          (setq current-grade-source "Cotas seleccionadas")
          ;; Modulacion eliminada del dialogo: la orientacion y el extremo
          ;; conservan lo que paso el llamador (creacion = "Automatico"/
          ;; "Normal"; EDITAR = "Conservar").
          ;; 2026-08-24: al final van los COSTADOS (11 = tipo derecha,
          ;; 12 = tipo izquierda, 13 = posicion); los llamadores viejos
          ;; los ignoran. 5.6.2: ya no salen de la ventana -- quedan en
          ;; Ninguno y el llamador pregunta costado por costado.
          (setq result
            (list current-material current-format current-etapa current-subetapa
                  current-guia current-toperol current-calculate
                  current-surface current-grade-source
                  current-orientation current-start
                  "Ninguno" "Ninguno" "Externo"
                  ;; nth 14 (2026-09-07): CODIGO de la variante elegida en
                  ;; *urb-send-tipos*; "" = anden nativo en loseta
                  (urb:safe-string
                    (cdr (nth *urb-dialog-material-index*
                      (urb:elem-variantes-de
                        (nth *urb-dialog-tipoelem-index*
                          *urb-elem-categorias*))))
                    ""))))))
  )
  result
)

(defun urb:write-prefab-dcl ()
  (urb:write-dialog-dcl
    "urbanismo_prefabricado"
    '*urb-prefab-dcl-ok*
    (list
      ;; 2026-09-02 (pedido del usuario): sin campo de espesor -- los
      ;; prefabricados tienen dimension PREDETERMINADA por tipo (editable
      ;; en URBANISMO > Configuracion, claves URB_PREFAB_ANCHO_*).
      "urbanismo_prefabricado : dialog { label = \"Datos del prefabricado\";"
      ": popup_list { label = \"Tipo\"; key = \"tipo\"; }"
      ": popup_list { label = \"Capitulo destino del presupuesto\"; key = \"destino\"; }"
      ": text { label = \"Espesor predeterminado por tipo (Configuracion).\"; }"
      (if (urb:etapas-enabled-p)
        ": popup_list { label = \"Etapa\"; key = \"etapa\"; }" "")
      (if (urb:etapas-enabled-p)
        ": popup_list { label = \"Subetapa\"; key = \"subetapa\"; }" "")
      ": popup_list { label = \"Modelado\"; key = \"modo\"; }"
      "ok_cancel; }"))
)

(defun urb:dialog-prefab
  (current-type current-width current-etapa current-subetapa current-mode current-destino
   / filename dcl-id accepted subetapas result width-value)
  (setq current-type (urb:safe-string current-type "Bordillo"))
  (setq current-width
    (if (numberp current-width)
      current-width
      (urb:parse-real (urb:safe-string current-width "0.20"))))
  (if (null current-width) (setq current-width 0.20))
  (if (<= current-width 0.0) (setq current-width 0.20))
  (setq current-etapa (urb:safe-string current-etapa "1"))
  (setq current-subetapa
    (urb:safe-string current-subetapa current-etapa))
  (setq current-mode (urb:safe-string current-mode "Interior"))
  (setq current-destino
    (urb:safe-string current-destino
      (urb:prefab-destino-default current-type)))
  (setq filename (urb:write-prefab-dcl))
  (if (and filename
           (> (setq dcl-id (load_dialog filename)) 0)
           (new_dialog "urbanismo_prefabricado" dcl-id))
    (progn
      (urb:fill-popup
        "tipo" *urb-prefab-list*
        (urb:index-of current-type *urb-prefab-list*))
      (urb:fill-popup
        "destino" *urb-prefab-destinos*
        (urb:index-of current-destino *urb-prefab-destinos*))
      (if (urb:etapas-enabled-p)
        (progn
          (urb:fill-popup
            "etapa" *urb-etapa-list*
            (urb:index-of current-etapa *urb-etapa-list*))
          (setq *urb-dialog-etapa*
            (nth (atoi (get_tile "etapa")) *urb-etapa-list*))
          (setq subetapas (urb:subetapas-for *urb-dialog-etapa*))
          (urb:fill-popup
            "subetapa" subetapas
            (urb:index-of current-subetapa subetapas))
          (action_tile "etapa" "(urb:dialog-update-subetapa)")))
      (urb:fill-popup
        "modo" *urb-prefab-mode-list*
        (urb:index-of current-mode *urb-prefab-mode-list*))
      (action_tile
        "accept"
        (strcat
          "(setq *urb-dialog-prefab-index* (atoi (get_tile \"tipo\"))"
          (if (urb:etapas-enabled-p)
            (strcat
              " *urb-dialog-etapa-index* (atoi (get_tile \"etapa\"))"
              " *urb-dialog-subetapa-index* (atoi (get_tile \"subetapa\"))")
            "")
          " *urb-dialog-prefab-mode-index* (atoi (get_tile \"modo\"))"
          " *urb-dialog-prefab-destino-index* (atoi (get_tile \"destino\")))"
          "(done_dialog 1)"))
      (setq accepted (= 1 (start_dialog)))
      (unload_dialog dcl-id)
      (if accepted
        (progn
          (setq current-type
            (nth *urb-dialog-prefab-index* *urb-prefab-list*))
          (if (urb:etapas-enabled-p)
            (progn
              (setq current-etapa
                (nth *urb-dialog-etapa-index* *urb-etapa-list*))
              (setq subetapas (urb:subetapas-for current-etapa))
              (setq current-subetapa
                (nth *urb-dialog-subetapa-index* subetapas))))
          (setq current-mode
            (nth *urb-dialog-prefab-mode-index*
              *urb-prefab-mode-list*))
          (setq current-destino
            (nth *urb-dialog-prefab-destino-index*
              *urb-prefab-destinos*))
          ;; espesor SIEMPRE el predeterminado del tipo elegido
          ;; (URB_PREFAB_ANCHO_<TIPO> en Configuracion; 0.20 por defecto)
          (setq width-value (urb:prefab-default-ancho current-type))
          (setq result
            (list current-type width-value current-etapa
                  current-subetapa current-mode current-destino))))))
  result
)

;; espesor de tierra negra PREDETERMINADO (2026-09-02, pedido del
;; usuario): ya no se digita en la ventana de zona verde; se edita una
;; sola vez en Configuracion (clave URB_GREEN_ESP_TIERRA, 0.20 default).
(defun urb:green-default-espesor (/ v)
  (setq v
    (urb:parse-real
      (urb:safe-string (urb:config-read "URB_GREEN_ESP_TIERRA") "")))
  (if (and v (> v 0.0)) v 0.20))

(defun urb:write-green-dcl ()
  (urb:write-dialog-dcl
    "urbanismo_zona_verde"
    '*urb-green-dcl-ok*
    (list
      "urbanismo_zona_verde : dialog { label = \"Datos de la zona verde\";"
      ;; sin etapas habilitadas la Clasificacion completa se omite (solo
      ;; contiene etapa/subetapa)
      (if (urb:etapas-enabled-p)
        ": boxed_column { label = \"Clasificacion\";" "")
      (if (urb:etapas-enabled-p)
        ": popup_list { label = \"Etapa\"; key = \"etapa\"; }" "")
      (if (urb:etapas-enabled-p)
        ": popup_list { label = \"Subetapa\"; key = \"subetapa\"; }" "")
      (if (urb:etapas-enabled-p) "}" "")
      ": text { label = \"Tierra negra: espesor predeterminado (Configuracion).\"; }"
      "ok_cancel; }"))
)

(defun urb:dialog-green
  (current-etapa current-subetapa current-thickness
   / filename dcl-id accepted subetapas result thickness-value)
  (setq current-etapa (urb:safe-string current-etapa "1")
        current-subetapa
          (urb:safe-string current-subetapa current-etapa)
        current-thickness
          (if (numberp current-thickness)
            current-thickness
            (urb:parse-real
              (urb:safe-string current-thickness "0.20"))))
  (if (or (null current-thickness) (<= current-thickness 0.0))
    (setq current-thickness 0.20))
  (setq filename (urb:write-green-dcl))
  (if (and filename
           (> (setq dcl-id (load_dialog filename)) 0)
           (new_dialog "urbanismo_zona_verde" dcl-id))
    (progn
      (if (urb:etapas-enabled-p)
        (progn
          (urb:fill-popup
            "etapa" *urb-etapa-list*
            (urb:index-of current-etapa *urb-etapa-list*))
          (setq *urb-dialog-etapa*
            (nth (atoi (get_tile "etapa")) *urb-etapa-list*))
          (setq subetapas (urb:subetapas-for *urb-dialog-etapa*))
          (urb:fill-popup
            "subetapa" subetapas
            (urb:index-of current-subetapa subetapas))
          (action_tile "etapa" "(urb:dialog-update-subetapa)")))
      (action_tile
        "accept"
        (strcat
          (if (urb:etapas-enabled-p)
            (strcat
              "(setq *urb-dialog-etapa-index* (atoi (get_tile \"etapa\"))"
              " *urb-dialog-subetapa-index* (atoi (get_tile \"subetapa\")))")
            "")
          "(done_dialog 1)"))
      (setq accepted (= 1 (start_dialog)))
      (unload_dialog dcl-id)
      (if accepted
        (progn
          (if (urb:etapas-enabled-p)
            (setq current-etapa
              (nth *urb-dialog-etapa-index* *urb-etapa-list*)
                  subetapas (urb:subetapas-for current-etapa)
                  current-subetapa
                    (nth *urb-dialog-subetapa-index* subetapas)))
          ;; espesor SIEMPRE el predeterminado de Configuracion
          (setq thickness-value (urb:green-default-espesor))
          (setq result
            (list current-etapa current-subetapa thickness-value))))))
  result
)

(defun urb:remove-app-xdata (edata app / result item sections kept section)
  (setq app (urb:safe-string app ""))
  (foreach item edata
    (if (= (car item) -3)
      (progn
        ;; ENTGET puede agrupar en un solo registro -3 las XDATA de varias
        ;; aplicaciones. La version anterior eliminaba el registro completo
        ;; al actualizar una de ellas y, con el, URB_VIA_MOV. Por eso el
        ;; calculo salia bien en la consola pero el bloque recibia ceros.
        (setq sections (cdr item) kept nil)
        (foreach section sections
          (if (not
                (and section
                     (urb:string-equal-p (car section) app)))
            (setq kept (cons section kept))))
        (if kept
          (setq result (cons (cons -3 (reverse kept)) result))))
      (setq result (cons item result)))
  )
  (reverse result)
)

(defun urb:set-xdata-strings
  (ename app values / edata records modified update-result
   kept-sections plain item)
  (setq ename (urb:as-ename ename))
  (if (and ename (= (type app) 'STR) (/= app ""))
    (progn
      (if (not (tblsearch "APPID" app))
        (regapp app))
      (setq edata (urb:remove-app-xdata (entget ename '("*")) app))
      (setq records
        (mapcar
          '(lambda (value)
            (cons 1000 (urb:safe-string value "")))
          values))
      ;; 2026-08-13 (cazado por la sonda del protocolo v3): agregar la
      ;; app nueva como un SEGUNDO grupo -3 nunca funciono -- en
      ;; entidades planas entmod se quedaba solo con el grupo agregado
      ;; (BORRABA la xdata de las demas apps devolviendo "exito") y en
      ;; entidades creadas por ActiveX el entmod fallaba y la escritura
      ;; se perdia (por eso el eje-display quedaba sin URB_VIA_EJE y la
      ;; recuperacion del eje dentro del bloque no encontraba nada).
      ;; Misma familia del bug de julio ("actualizar URB_VIA borraba
      ;; URB_VIA_MOV"), que solo se corrigio del lado de LECTURA.
      ;; Correcto: UN solo grupo -3 con las secciones conservadas de las
      ;; otras apps + la seccion nueva.
      (setq kept-sections nil plain nil)
      (foreach item edata
        (if (= (car item) -3)
          (setq kept-sections (append kept-sections (cdr item)))
          (setq plain (cons item plain))))
      (setq modified
        (vl-catch-all-apply
          'entmod
          (list
            (append (reverse plain)
              (list
                (cons -3
                  (append kept-sections
                    (list (append (list app) records)))))))))
      (if (or (vl-catch-all-error-p modified) (null modified))
        nil
        (progn
          (setq update-result
            (vl-catch-all-apply 'entupd (list ename)))
          (if (vl-catch-all-error-p update-result) nil values))))
    nil)
)

;; 5.6.3: lectura por ActiveX GetXData. entget -- aun filtrado por APPID --
;; serializa TODO el objeto: en una REGION los datos ACIS, en un HATCH sus
;; lazos y lineas de patron. Con 6000 piezas de un anden curvo eran ~6.6 ms
;; por lectura (40 s solo para hallar el contorno de tierras). GetXData
;; devuelve solo el XDATA. Si falla, se usa el camino entget de siempre.
(defun urb:get-xdata-strings (ename app / obj xt xv r vals)
  (if (/= (type ename) 'ENAME) (setq ename (urb:as-ename ename)))
  (if ename
    (progn
      (setq r (vl-catch-all-apply
                '(lambda ()
                   (setq obj (vlax-ename->vla-object ename))
                   (vla-GetXData obj app 'xt 'xv)
                   (if (and xv (= (type xv) 'VARIANT) (> (vlax-variant-type xv) 8192))
                     (setq xv (vlax-variant-value xv)))
                   (if (= (type xv) 'SAFEARRAY)
                     (mapcar '(lambda (v) (if (= (type v) 'VARIANT) (vlax-variant-value v) v))
                             (vlax-safearray->list xv))
                     'VACIO))))
      (cond
        ((vl-catch-all-error-p r) (urb:get-xdata-strings-entget ename app))
        ((eq r 'VACIO) nil)
        ;; el primer valor es el nombre de la aplicacion (codigo 1001)
        (T (mapcar '(lambda (v) (urb:safe-string v "")) (cdr r)))))))

(defun urb:get-xdata-strings-entget (ename app / item section)
  ;; Para ENAME no pedir primero TODO el DXF solo para validarlo y luego
  ;; pedirlo otra vez con el APPID. Una sola lectura filtrada y protegida.
  (if (/= (type ename) 'ENAME) (setq ename (urb:as-ename ename)))
  (if ename
    (progn
      (setq item (vl-catch-all-apply 'entget (list ename (list app))))
      (setq item (if (vl-catch-all-error-p item) nil (assoc -3 item)))))
  (if item
    (progn
      (setq section (cadr item))
      (mapcar
        '(lambda (record)
          (urb:safe-string (cdr record) ""))
        (cdr section)))
    nil)
)

(defun urb:list-set-extended (values index value / result)
  (setq result values)
  (while (<= (length result) index)
    (setq result (append result (list ""))))
  (urb:replace-nth index value result)
)

(defun urb:clear-xdata-app (ename app / edata modified update-result)
  (setq ename (urb:as-ename ename))
  (if ename
    (progn
      (setq edata
        (urb:remove-app-xdata (entget ename '("*")) app))
      (setq modified
        (vl-catch-all-apply 'entmod (list edata)))
      (if (or (vl-catch-all-error-p modified) (null modified))
        nil
        (progn
          (setq update-result
            (vl-catch-all-apply 'entupd (list ename)))
          (not (vl-catch-all-error-p update-result)))))
    nil)
)

(defun urb:loseta-module (format)
  (if (urb:starts-with (urb:safe-string format "40 x 40 cm") "40") 0.40 0.20)
)

(defun urb:unit-count-ceiling (area unit-area / quotient nearest lower tolerance)
  (if (or (not (numberp area))
          (not (numberp unit-area))
          (<= area 1e-12)
          (<= unit-area 1e-12))
    0
    (progn
      (setq quotient (/ area unit-area)
            nearest (fix (+ quotient 0.5))
            lower (fix quotient)
            tolerance (max 1e-6 (* 1e-9 (abs quotient))))
      ;; Los booleanos REGION pueden devolver 100.0000000003 para una
      ;; cantidad geometricamente exacta de 100 piezas. En ese caso se
      ;; conserva el entero; solo se redondea hacia arriba cuando existe
      ;; una fraccion real mayor que la tolerancia numerica.
      (if (equal quotient nearest tolerance)
        nearest
        (if (> quotient lower) (1+ lower) lower))))
)

;; Devuelve: area lisa, unidades lisas, guia ML, toperol ML,
;; area de adoquin blanco 20x10 y unidades de adoquin.
(defun urb:polygon-band-area
  (triangles umin umax angle-value / triangle piece result)
  (setq result 0.0)
  (foreach triangle triangles
    (setq piece
      (urb:clip-polygon-to-band triangle umin umax angle-value))
    (if piece
      (setq result
        (+ result (abs (urb:polygon-signed-area piece))))))
  result
)

(defun urb:composite-exact-band-areas
  (points angle-value reverse-pattern
   / triangles bounds umin umax cursor next gray phase-state first-band
   band-width gray-area white-area guard band-area)
  ;; Mide las MISMAS franjas 0.80/1.00 que se dibujan. El recorte se hace
  ;; sobre triangulos internos del contorno, por lo que una banda que
  ;; atraviesa dos islas de un anden concavo suma ambas sin aproximarla
  ;; mediante largo x ancho.
  (setq triangles (urb:triangulate-polygon points))
  (if triangles
    (progn
      (setq bounds (urb:project-bounds points angle-value)
            umin (nth 0 bounds)
            umax (nth 1 bounds)
            cursor (if reverse-pattern umax umin)
            phase-state (urb:composite-phase-state 0.0)
            gray (car phase-state)
            first-band T
            gray-area 0.0
            white-area 0.0
            guard 0)
      (while
        (and
          (if reverse-pattern
            (> cursor (+ umin 0.000001))
            (< cursor (- umax 0.000001)))
          (< guard 20000))
        (setq guard (1+ guard)
              band-width
                (if first-band
                  (cdr phase-state)
                  (if gray 0.80 1.00))
              next
                (if reverse-pattern
                  (max umin (- cursor band-width))
                  (min umax (+ cursor band-width)))
              band-area
                (urb:polygon-band-area triangles
                  (if reverse-pattern next cursor)
                  (if reverse-pattern cursor next)
                  angle-value))
        (if gray
          (setq gray-area (+ gray-area band-area))
          (setq white-area (+ white-area band-area)))
        (setq cursor next gray (not gray) first-band nil))
      (list gray-area white-area))
    nil)
)

(defun urb:anden-quantity-pattern-angle
  (ename points pattern-mode / forced-angle clusters result)
  ;; Repite la misma eleccion de eje usada por create-composite-loseta.
  ;; Antes las cantidades ignoraban URB_ANDEN_AXIS y podian repartir las
  ;; bandas con otra orientacion distinta a la que se veia en planta.
  (setq forced-angle
    (urb:parse-real
      (urb:safe-string
        (car (urb:get-xdata-strings ename "URB_ANDEN_AXIS")) "")))
  (if (and (null forced-angle) (urb:lwpoly-has-arcs-p ename))
    (progn
      (setq forced-angle (urb:anden-straight-edges-angle ename))
      (if forced-angle
        (setq forced-angle (+ forced-angle (* 0.5 pi))))))
  (setq clusters (urb:dominant-anden-axis-clusters points))
  (setq result
    (cond
      (forced-angle forced-angle)
      (clusters (car (car clusters)))
      (T (urb:anden-axis-angle points))))
  (urb:anden-pattern-angle result pattern-mode)
)

(defun urb:anden-finish-quantities
  (points area format guia toperol pattern-mode pattern-angle
   / module corridor-angle bounds length-value
   corridor-bounds corridor-length width-value driving-chain
   guide-ml toperol-ml guide-area toperol-area finish-area
   smooth-area smooth-count adoquin-area adoquin-count cursor next gray
   gray-length white-length ratio exact-areas raw-total area-scale)
  (setq module (urb:loseta-module format))
  (setq corridor-angle (urb:anden-axis-angle points)
        pattern-angle
          (if (numberp pattern-angle)
            pattern-angle
            (urb:anden-pattern-angle corridor-angle pattern-mode))
        corridor-bounds
          (urb:project-bounds points corridor-angle)
        bounds (urb:project-bounds points pattern-angle))
  ;; La proyeccion sobre un solo eje (corridor-bounds) subestima la
  ;; longitud real en un tramo curvo -incluso con los puntos del arco ya
  ;; expandidos, proyectar sobre UN eje nunca converge al arco real. Si hay
  ;; una cadena guia con varios segmentos reales (anden curvo), se usa su
  ;; longitud real sumada; si no (anden recto/simple), se conserva la
  ;; proyeccion de siempre -da el mismo resultado ahi de todas formas.
  (setq driving-chain (urb:anden-driving-chain points))
  (setq corridor-length
    (if (and driving-chain (>= (length (urb:open-chain-edges driving-chain)) 2))
      (urb:chain-total-length driving-chain)
      (max 0.0 (- (nth 1 corridor-bounds) (nth 0 corridor-bounds)))))
  (setq length-value (max 0.0 (- (nth 1 bounds) (nth 0 bounds))))
  (setq width-value (max 0.0 (- (nth 3 bounds) (nth 2 bounds))))
  ;; Guia y toperol son franjas longitudinales independientes.
  (setq toperol-ml (if (urb:yes-p toperol) corridor-length 0.0))
  (setq guide-ml
    (if (urb:yes-p guia) corridor-length 0.0))
  (setq guide-area (* guide-ml module))
  (setq toperol-area (* toperol-ml module))
  (setq finish-area (max 0.0 (- area guide-area toperol-area)))
  (if (< module 0.30)
    (progn
      ;; En curvas/codos el ancho interceptado por cada banda cambia. Se
      ;; mide el area real recortada de gris y blanco; luego se normaliza
      ;; contra el area ACIS exacta del contorno y se descuentan las
      ;; franjas tactiles contractuales.
      (setq exact-areas
        (urb:composite-exact-band-areas
          points pattern-angle
          (urb:anden-pattern-reversed-p pattern-mode)))
      (setq raw-total
        (if exact-areas (+ (car exact-areas) (cadr exact-areas)) 0.0))
      (setq ratio
        (if (> raw-total 1e-9)
          (/ (car exact-areas) raw-total)
          (/ 0.80 1.80)))
      (setq smooth-area (* finish-area ratio))
      (setq adoquin-area (- finish-area smooth-area)))
    (setq smooth-area finish-area adoquin-area 0.0))
  (setq smooth-count
    (urb:unit-count-ceiling smooth-area (* module module)))
  (setq adoquin-count
    (urb:unit-count-ceiling adoquin-area 0.02))
  (list smooth-area smooth-count guide-ml toperol-ml
        adoquin-area adoquin-count)
)

;; Para un anden cuyo acabado principal es adoquin, las franjas guia y
;; toperol reemplazan acabado y deben descontarse del area contractual.
;; Devuelve la misma estructura de urb:anden-finish-quantities.
(defun urb:adoquin-finish-quantities
  (points area format guia toperol / tactile module guide-ml toperol-ml
   adoquin-area adoquin-count)
  (setq tactile
    (urb:anden-finish-quantities
      points area format guia toperol "AUTOMATICO" nil)
        module (urb:loseta-module format)
        guide-ml (nth 2 tactile)
        toperol-ml (nth 3 tactile)
        adoquin-area
          (max 0.0
            (- area
              (* module (+ guide-ml toperol-ml))))
        adoquin-count
          (urb:unit-count-ceiling adoquin-area 0.02))
  (list 0.0 0 guide-ml toperol-ml adoquin-area adoquin-count)
)

(defun urb:set-anden-data
  (ename material etapa subetapa guia toperol format calculate surface grade-source
   / object elevation pattern-mode)
  (setq object (urb:as-vla-object ename)
        pattern-mode (urb:anden-pattern-mode ename)
        elevation
          (if (and object
                   (vlax-property-available-p object 'Elevation))
            (vla-get-Elevation object)
            0.0))
  (urb:set-xdata-strings
    ename
    "URB_ANDEN"
    (list "ANDEN"
          (strcase (urb:safe-string material "Loseta"))
          (urb:safe-string etapa "1")
          (urb:safe-string subetapa "1")
          (urb:safe-string guia "No")
          (urb:safe-string toperol "No")
          (urb:safe-string format "40 x 40 cm")
          (urb:safe-string calculate "Si")
          (urb:safe-string surface "Seleccionar en dibujo")
          (urb:safe-string grade-source "Via creada")
          (rtos elevation 2 8)
          pattern-mode))
)

(defun urb:normalize-anden-pattern-mode (mode)
  (setq mode (strcase (urb:safe-string mode "AUTOMATICO")))
  (cond
    ((member mode '("GIRAR90_OPUESTO" "GIRAR90_INVERTIR"))
      "GIRAR90_OPUESTO")
    ((= mode "GIRAR90") "GIRAR90")
    ((member mode '("OPUESTO" "INVERTIR" "INVERTIR_INICIO"))
      "OPUESTO")
    (T "AUTOMATICO"))
)

(defun urb:anden-pattern-rotated-p (mode)
  (member
    (urb:normalize-anden-pattern-mode mode)
    '("GIRAR90" "GIRAR90_OPUESTO"))
)

(defun urb:anden-pattern-reversed-p (mode)
  (member
    (urb:normalize-anden-pattern-mode mode)
    '("OPUESTO" "GIRAR90_OPUESTO"))
)

(defun urb:compose-anden-pattern-mode (rotated reversed)
  (cond
    ((and rotated reversed) "GIRAR90_OPUESTO")
    (rotated "GIRAR90")
    (reversed "OPUESTO")
    (T "AUTOMATICO"))
)

(defun urb:anden-pattern-angle (angle-value mode)
  (urb:normalize-axis-angle
    (if (urb:anden-pattern-rotated-p mode)
      (+ angle-value (/ pi 2.0))
      angle-value))
)

(defun urb:anden-pattern-mode
  (ename / anden-data block-data legacy-data mode object attributes)
  (setq anden-data (urb:get-xdata-strings ename "URB_ANDEN")
        block-data (urb:get-xdata-strings ename "URB_ANDEN_BLOCK")
        legacy-data (urb:get-xdata-strings ename "URB_ANDEN_PATTERN")
        mode
          (cond
            ((> (length anden-data) 11) (nth 11 anden-data))
            ((> (length block-data) 20) (nth 20 block-data))
            (legacy-data (car legacy-data))
            (T
              (setq object (urb:as-vla-object ename))
              (if (and object
                       (urb:string-equal-p
                         (vla-get-ObjectName object)
                         "AcDbBlockReference"))
                (progn
                  (setq attributes
                    (urb:block-attribute-values object))
                  (urb:attribute-alist-value
                    attributes "ANDEN_SENTIDO" "AUTOMATICO"))
                "AUTOMATICO")))
        mode (urb:normalize-anden-pattern-mode mode))
  mode
)

(defun urb:set-anden-pattern-mode
  (ename mode / anden-data block-data object result)
  (setq mode (urb:normalize-anden-pattern-mode mode))
  (setq anden-data (urb:get-xdata-strings ename "URB_ANDEN")
        block-data (urb:get-xdata-strings ename "URB_ANDEN_BLOCK"))
  (cond
    (anden-data
      (setq result
        (urb:set-xdata-strings
          ename "URB_ANDEN"
          (urb:list-set-extended anden-data 11 mode))))
    (block-data
      (setq result
        (urb:set-xdata-strings
          ename "URB_ANDEN_BLOCK"
          (urb:list-set-extended block-data 20 mode)))
      (setq object (urb:as-vla-object ename))
      (if object
        (urb:set-block-attribute object "ANDEN_SENTIDO" mode)))
    (T
      ;; Compatibilidad con contornos antiguos que aun no tienen URB_ANDEN.
      (setq result
        (urb:set-xdata-strings ename "URB_ANDEN_PATTERN" (list mode)))))
  result
)

(defun urb:tag-generated (obj parent-handle / ename)
  (urb:tag-generated-role obj parent-handle "")
)

;; role identifica el papel de la pieza generada, independiente de en que
;; capa quedo. urb:set-block-draw-order y urb:extract-prefab-reference lo
;; usan para decidir orden de dibujo / identificar interior-exterior sin
;; tener que abrir una capa por cada rol (asi se puede consolidar capas).
(defun urb:tag-generated-role (obj parent-handle role / ename)
  (if (and obj (not (vl-catch-all-error-p obj)))
    (progn
      (setq ename
        (vl-catch-all-apply
          'vlax-vla-object->ename
          (list obj)))
      (if (and ename (not (vl-catch-all-error-p ename)))
        (vl-catch-all-apply
          'urb:set-xdata-strings
          (list ename
                "URB_ANDEN_GEN"
                (list parent-handle (urb:safe-string role ""))))))
  )
  obj
)

(defun urb:generated-role (item / ename data)
  (setq ename
    (vl-catch-all-apply 'vlax-vla-object->ename (list item)))
  (if (and ename (not (vl-catch-all-error-p ename)))
    (setq data (urb:get-xdata-strings ename "URB_ANDEN_GEN")))
  (if (> (length data) 1) (nth 1 data) "")
)

(defun urb:delete-generated
  (parent-handle / ss index ename data obj deleted)
  (setq deleted 0)
  ;; Filtra por XData en el ssget: evita recorrer todo el dibujo.
  (if (setq ss (ssget "_X" '((-3 ("URB_ANDEN_GEN")))))
    (progn
      (setq index 0)
      (repeat (sslength ss)
        (setq ename (ssname ss index))
        (setq data (urb:get-xdata-strings ename "URB_ANDEN_GEN"))
        (if (and data (= (car data) parent-handle))
          (progn
            (setq obj (vlax-ename->vla-object ename))
            (if (urb:safe-delete obj)
              (setq deleted (1+ deleted)))))
        (setq index (1+ index)))))
  deleted
)

(defun urb:group-name (parent-handle)
  (strcat "URB_ANDEN_" parent-handle)
)

(defun urb:get-group (group-name / result)
  (setq result
    (vl-catch-all-apply
      'vla-Item
      (list
        (vla-get-Groups (urb:doc))
        group-name)))
  (if (vl-catch-all-error-p result) nil result)
)

(defun urb:remove-anden-group (parent-handle / group)
  (if (setq group
        (urb:get-group (urb:group-name parent-handle)))
    (vl-catch-all-apply 'vla-Delete (list group)))
  T
)

(defun urb:generated-objects
  (parent-handle / ss index ename data objects)
  ;; Durante BUILD/PACKAGE solo se crearon piezas despues del marcador.
  ;; No revisar otra vez todos los acabados historicos del DWG maestro.
  ;; Fuera de esa operacion (edicion vieja, reapertura, padre empaquetado)
  ;; conservar la busqueda completa por XDATA.
  (if (and (boundp '*urb-generation-parent*)
           (= parent-handle *urb-generation-parent*)
           (boundp '*urb-generation-start*) *urb-generation-start*
           (entget *urb-generation-start*)
           (handent parent-handle) (entget (handent parent-handle)))
    (progn
      (setq ename (entnext *urb-generation-start*))
      (while ename
        (setq data (urb:get-xdata-strings ename "URB_ANDEN_GEN"))
        (if (and data (= (car data) parent-handle))
          (setq objects (cons (vlax-ename->vla-object ename) objects)))
        (setq ename (entnext ename))))
    (if (setq ss (ssget "_X" '((-3 ("URB_ANDEN_GEN")))))
    (progn
      (setq index 0)
      (repeat (sslength ss)
        (setq ename (ssname ss index))
        (setq data
          (urb:get-xdata-strings ename "URB_ANDEN_GEN"))
        (if (and data (= (car data) parent-handle))
          (setq objects
            (cons (vlax-ename->vla-object ename) objects)))
        (setq index (1+ index))))))
  (reverse objects)
)

(defun urb:path-ends-with-separator-p (path / last-char)
  (setq last-char (substr path (strlen path) 1))
  (or (= last-char "\\") (= last-char "/"))
)

(defun urb:join-path (folder filename)
  (strcat
    folder
    (if (urb:path-ends-with-separator-p folder) "" "\\")
    filename)
)

(defun urb:path-in-list-p (folder paths / target found)
  (setq target (strcase (vl-string-right-trim "\\/" folder)))
  (while (and paths (not found))
    (if
      (= target
         (strcase
           (vl-string-right-trim "\\/" (car paths))))
      (setq found T)
    )
    (setq paths (cdr paths))
  )
  found
)

(defun urb:ensure-support-path (folder / current paths)
  (setq current (getenv "ACAD"))
  (setq paths
    (if current
      (urb:split-string current ";")
      nil)
  )
  (if (not (urb:path-in-list-p folder paths))
    (setenv "ACAD"
      (if (and current (/= current ""))
        (strcat current ";" folder)
        folder))
  )
)

(defun urb:copy-quantity-scope (source target / data target-ename)
  (setq data
    (if (urb:valid-ename-p source)
      (urb:get-xdata-strings source "URB_Q_SCOPE") nil)
    target-ename (urb:as-ename target))
  (if (and data target-ename)
    (urb:set-xdata-strings target-ename "URB_Q_SCOPE" data))
  target
)

(defun urb:split-string (text separator / position result)
  (while (setq position (vl-string-search separator text))
    (setq result
      (cons (substr text 1 position) result))
    (setq text
      (substr text (+ position (strlen separator) 1)))
  )
  (reverse (cons text result))
)

(defun urb:write-lines (filename lines / stream line)
  (if (setq stream (open filename "w"))
    (progn
      (foreach line lines
        (write-line line stream))
      (close stream)
      T
    )
  )
)

(defun urb:install-patterns
  (/ folder loseta-file adoquin-file guia-file toperol-file)
  (setq folder (urb:patterns-folder))
  (setq loseta-file (urb:join-path folder "URB_LOSETA.pat"))
  (setq adoquin-file (urb:join-path folder "URB_ADOQUIN.pat"))
  (setq guia-file (urb:join-path folder "URB_GUIA.pat"))
  (setq toperol-file (urb:join-path folder "URB_TOPEROL.pat"))
  (if
    (and
      (urb:write-lines
        loseta-file
        '("*URB_LOSETA, Loseta cuadrada modular 0.20 x 0.20"
          "0, 0,0, 0,0.20"
          "90, 0,0, 0.20,0"))
      (urb:write-lines
        adoquin-file
        '("*URB_ADOQUIN, Adoquin rectangular trabado 0.20 x 0.10"
          "0, 0,0, 0,0.10"
          "90, 0,0, 0.20,0.20, 0.10,-0.10"
          "90, 0.10,0.10, 0.20,0.20, 0.10,-0.10"))
      (urb:write-lines
        guia-file
        '("*URB_GUIA, Barras tactiles en loseta guia 0.20 x 0.20"
          "0, 0.02,0.025, 0,0.05, 0.16,-0.04"))
      (urb:write-lines
        toperol-file
        ;; 2026-09-10: medido sobre el bloque real del plano de detalles
        ;; (B-TABLETA 20X20 TACTIL ALERTA, en Detalles_Rampas.dwg): la
        ;; tableta lleva 3 x 3 = 9 domos de r = 0.0119 m, o sea paso de
        ;; 0.0667 m y no los 0.05 que se venian usando.
        '("*URB_TOPEROL, Puntos tactiles en tableta podotactil 0.20 x 0.20"
          "0, 0.0333,0.0333, 0,0.0667, 0,-0.0667")))
    (progn
      (urb:ensure-support-path folder)
      T)
    nil
  )
)

(defun urb:doc ()
  (vla-get-ActiveDocument (vlax-get-acad-object))
)

(defun urb:space (/ doc)
  (setq doc (urb:doc))
  (if (= 1 (getvar "CVPORT"))
    (vla-get-PaperSpace doc)
    (vla-get-ModelSpace doc)
  )
)

(defun urb:starts-with (text prefix)
  (setq text (urb:safe-string text ""))
  (setq prefix (urb:safe-string prefix ""))
  (= (strcase prefix)
     (substr (strcase text) 1 (strlen prefix)))
)

(defun urb:ends-with (text suffix / text-length suffix-length)
  (setq text (urb:safe-string text ""))
  (setq suffix (urb:safe-string suffix ""))
  (setq text-length (strlen text))
  (setq suffix-length (strlen suffix))
  (and (>= text-length suffix-length)
       (= (strcase suffix)
          (substr
            (strcase text)
            (1+ (- text-length suffix-length))
            suffix-length)))
)

(defun urb:ensure-layer (name color plottable / layers layer)
  (setq layers (vla-get-Layers (urb:doc)))
  (setq layer
    (if (tblsearch "LAYER" name)
      (vla-Item layers name)
      (vla-Add layers name)
    )
  )
  (vla-put-Color layer color)
  (if (vlax-property-available-p layer 'Plottable T)
    (vla-put-Plottable layer
      (if plottable :vlax-true :vlax-false))
  )
  layer
)

(defun urb:closed-poly-p (ename / obj result)
  (setq obj (vlax-ename->vla-object ename))
  (setq result
    (and
      (member (vla-get-ObjectName obj)
        '("AcDbPolyline" "AcDb2dPolyline" "AcDb3dPolyline"))
      (vlax-property-available-p obj 'Closed)
      (= :vlax-true (vla-get-Closed obj))
      (not
        (vl-catch-all-error-p
          (vl-catch-all-apply 'vla-get-Area (list obj))))
    )
  )
  result
)

(defun urb:poly-perimeter (obj / ename endparam)
  (setq ename (vlax-vla-object->ename obj))
  (setq endparam (vlax-curve-getEndParam ename))
  (vlax-curve-getDistAtParam ename endparam)
)

(defun urb:make-loop-array (obj / arr)
  (setq arr (vlax-make-safearray vlax-vbObject '(0 . 0)))
  (vlax-safearray-put-element arr 0 obj)
  (vlax-make-variant arr)
)

(defun urb:add-hatch-raw
  (boundary layer pattern pattern-type scale color / hatch)
  (setq layer (urb:safe-string layer "0"))
  (setq pattern (urb:safe-string pattern "SOLID"))
  (setq hatch
    (vla-AddHatch
      (urb:space)
      pattern-type
      pattern
      :vlax-true
    )
  )
  ;; AutoCAD exige agregar el contorno antes de modificar el hatch.
  (vla-AppendOuterLoop hatch (urb:make-loop-array boundary))
  (vla-put-Layer hatch layer)
  (vla-put-Color hatch color)
  (cond
    ((= pattern-type 0)
      (if (vlax-property-available-p hatch 'PatternSpace T)
        (vla-put-PatternSpace hatch scale))
      (if (vlax-property-available-p hatch 'PatternAngle T)
        (vla-put-PatternAngle hatch 0.0))
      (if (vlax-property-available-p hatch 'PatternDouble T)
        (vla-put-PatternDouble hatch :vlax-true)))
    ((and (/= (strcase pattern) "SOLID")
          (vlax-property-available-p hatch 'PatternScale T))
      (vla-put-PatternScale hatch scale))
  )
  (urb:evaluate-render-hatch hatch)
  hatch
)

(defun urb:object-array-variant (objects / arr index obj)
  (setq arr
    (vlax-make-safearray
      vlax-vbObject
      (cons 0 (1- (length objects)))))
  (setq index 0)
  (foreach obj objects
    (vlax-safearray-put-element arr index obj)
    (setq index (1+ index))
  )
  (vlax-make-variant arr)
)

(defun urb:double-array-variant (values / arr index value)
  (setq arr
    (vlax-make-safearray
      vlax-vbDouble
      (cons 0 (1- (length values)))))
  (setq index 0)
  (foreach value values
    (vlax-safearray-put-element arr index value)
    (setq index (1+ index))
  )
  (vlax-make-variant arr)
)

(defun urb:add-region-from-object (obj / result value)
  (setq result
    (vl-catch-all-apply
      'vla-AddRegion
      (list
        (urb:space)
        (urb:object-array-variant (list obj)))))
  (if (vl-catch-all-error-p result)
    result
    (progn
      (setq value
        (if (= (type result) 'VARIANT)
          (vlax-variant-value result)
          result))
      (car (vlax-safearray->list value))
    )
  )
)

(defun urb:anden-region-from-object (obj / result cp attempt i n b a z changed original-area)
  ;; ACIS rechaza algunos contornos recortados con microarcos casi rectos.
  ;; Primero intentar la geometria exacta. Solo ante error, sobre una COPIA,
  ;; sustituir arcos con flecha <= 1 micra. No modificar el contorno fuente,
  ;; no discretizar los demas arcos, ni aceptar cambio de area > 0.00001 m2.
  (setq result (urb:add-region-from-object obj))
  (if (and (vl-catch-all-error-p result)
           (= (vla-get-ObjectName obj) "AcDbPolyline")
           (= (vla-get-Closed obj) :vlax-true))
    (progn
      (setq cp (vla-Copy obj) original-area (vla-get-Area obj))
      (setq attempt
        (vl-catch-all-apply
          '(lambda ()
             (setq i 0 n (fix (vlax-curve-getEndParam cp)) changed nil)
             (repeat n
               (setq b (vla-GetBulge cp i))
               (if (/= b 0.0)
                 (progn
                   (setq a (vlax-curve-getPointAtParam cp i)
                         z (vlax-curve-getPointAtParam cp (1+ i)))
                   (if (<= (* 0.5 (abs b) (distance a z)) 1e-6)
                     (progn (vla-SetBulge cp i 0.0) (setq changed T)))))
               (setq i (1+ i)))
             (if changed (urb:add-region-from-object cp)))))
      (urb:safe-delete cp)
      (if (and attempt (not (vl-catch-all-error-p attempt)))
        (if (<= (abs (- (vla-get-Area attempt) original-area)) 1e-5)
          (setq result attempt)
          (urb:safe-delete attempt)))))
  result)

(defun urb:local-to-world (ucoord vcoord angle-value / cosine sine)
  (setq cosine (cos angle-value))
  (setq sine (sin angle-value))
  (list
    (- (* ucoord cosine) (* vcoord sine))
    (+ (* ucoord sine) (* vcoord cosine)))
)

(defun urb:add-rectangle-poly
  (umin umax vmin vmax angle-value elevation / points coords poly)
  (setq points
    (list
      (urb:local-to-world umin vmin angle-value)
      (urb:local-to-world umax vmin angle-value)
      (urb:local-to-world umax vmax angle-value)
      (urb:local-to-world umin vmax angle-value)))
  (setq coords
    (apply 'append
      (mapcar
        '(lambda (point) (list (car point) (cadr point)))
        points)))
  (setq poly
    (vla-AddLightWeightPolyline
      (urb:space)
      (urb:double-array-variant coords)))
  (if (and (numberp elevation)
           (vlax-property-available-p poly 'Elevation T))
    (vla-put-Elevation poly elevation))
  (vla-put-Closed poly :vlax-true)
  poly
)

(defun urb:rectangle-region
  (umin umax vmin vmax angle-value elevation / poly region)
  (setq poly
    (urb:add-rectangle-poly
      umin umax vmin vmax angle-value elevation))
  (setq region (urb:add-region-from-object poly))
  (vla-Delete poly)
  region
)

(defun urb:lwpoly-points (ename / data points item)
  (setq data (entget ename))
  (foreach item data
    (if (= (car item) 10)
      (setq points
        (cons
          (trans
            (list (cadr item) (caddr item) 0.0)
            ename
            0)
          points))
    )
  )
  (reverse points)
)

(defun urb:arc-samples-for (p1 p2 b / theta chord r len)
  ;; Numero de subdivisiones para un segmento con bulge, ~1 muestra por
  ;; metro de arco REAL (antes eran 8 fijas por arco sin importar el
  ;; tamano: un arco de 30m quedaba en cuerdas de casi 4m y la franja de
  ;; guia/toperol salia visiblemente poligonal/zigzag en vez de seguir la
  ;; curva -- visto en el PDF de verificacion del abanico).
  (setq theta (* 4.0 (atan (abs b))))
  (setq chord (distance p1 p2))
  (if (or (< theta 1e-6) (< chord 1e-6))
    8
    (progn
      (setq r (/ chord (* 2.0 (sin (* 0.5 theta)))))
      (setq len (* r theta))
      (max 8 (min 96 (fix (+ 1.0 len))))))
)

(defun urb:arc-bulge-midpoints (ename p1-wcs p2-wcs n / param1 param2 pts j frac tparam pt)
  ;; Puntos intermedios (sin incluir p1 ni p2) a lo largo del arco real
  ;; entre dos vertices con bulge, consultando la curva de verdad
  ;; (vlax-curve) en vez de recalcular la geometria del arco a mano: evita
  ;; arriesgar un error de signo propio en la formula bulge->circulo.
  (setq param1 (vl-catch-all-apply 'vlax-curve-getParamAtPoint (list ename p1-wcs)))
  (setq param2 (vl-catch-all-apply 'vlax-curve-getParamAtPoint (list ename p2-wcs)))
  (if (or (vl-catch-all-error-p param1) (vl-catch-all-error-p param2))
    nil
    (progn
      ;; Segmento de CIERRE con arco (PLINE opcion Arc + CLose): p2 es el
      ;; PRIMER vertice, cuyo parametro es 0 -- interpolar de param1 hacia
      ;; 0 recorre TODA la polilinea hacia atras en vez del arco de
      ;; cierre, sembrando puntos por todo el contorno (el validador veia
      ;; un falso "monio" y rechazaba andenes curvos validos). El extremo
      ;; correcto por el lado del cierre es el parametro FINAL de la
      ;; curva.
      (if (<= param2 param1)
        (progn
          (setq param2 (vl-catch-all-apply 'vlax-curve-getEndParam (list ename)))
          (if (vl-catch-all-error-p param2) (setq param2 param1))))
      (setq pts nil j 1)
      (repeat (1- n)
        (setq frac (/ (float j) (float n)))
        (setq tparam (+ param1 (* frac (- param2 param1))))
        (setq pt (vl-catch-all-apply 'vlax-curve-getPointAtParam (list ename tparam)))
        ;; pt puede ser NIL sin error (parametro fuera de rango): no
        ;; apendear (nil nil)
        (if (and (not (vl-catch-all-error-p pt)) pt)
          (setq pts (cons (list (car pt) (cadr pt)) pts)))
        (setq j (1+ j)))
      (reverse pts))))

(defun urb:lwpoly-points-with-arcs (ename)
  ;; muestreo ESTANDAR (8 por arco): el que usa el material -- con muchas
  ;; cunas delgadas los booleanos de bandas se degradan (verificado
  ;; visualmente en PDF), asi que el material se queda con cuerdas gruesas
  (urb:lwpoly-points-with-arcs-impl ename nil)
)

;; T si la polilinea tiene al menos un segmento en ARCO real (bulge).
;; 2026-08-12 (pantallazo del usuario: bandas diagonales en la curva):
;; las cuerdas en que se subdivide un arco generaban un segundo "eje
;; dominante" y el material se partia en dos zonas con orientaciones
;; distintas (abanico parcial). Un contorno CON arcos es una curva
;; continua -> UN solo eje y la curva solo recorta; la particion en dos
;; ejes queda solo para andenes en L de esquinas rectas (sin bulges).
(defun urb:lwpoly-has-arcs-p (ename / found pair)
  (foreach pair (entget ename)
    (if (and (= (car pair) 42) (> (abs (cdr pair)) 1e-6))
      (setq found T)))
  found
)

;; Angulo dominante usando SOLO los lados RECTOS reales del contorno
;; (los segmentos con bulge -- arcos -- no votan). En un anden curvo las
;; cuerdas del arco elegian un eje diagonal; el eje correcto es el del
;; tramo recto (tapas / lado compartido con el modulo vecino). Devuelve
;; nil si el contorno no tiene ningun lado recto apreciable.
(defun urb:anden-straight-edges-angle
  (ename / data item pts bulges n i p1 p2 b a len bins entry best)
  (setq data (entget ename) pts nil bulges nil)
  (foreach item data
    (cond
      ((= (car item) 10)
        (setq pts (cons (cdr item) pts) bulges (cons 0.0 bulges)))
      ((= (car item) 42)
        (if bulges (setq bulges (cons (cdr item) (cdr bulges)))))))
  (setq pts (reverse pts) bulges (reverse bulges))
  (setq n (length pts) i 0 bins nil)
  (while (< i n)
    (setq p1 (nth i pts)
          p2 (nth (rem (1+ i) n) pts)
          b (nth i bulges))
    (if (<= (abs b) 1e-6)
      (progn
        (setq len (distance p1 p2))
        (if (> len 1e-6)
          (progn
            (setq a (angle p1 p2))
            (if (>= a pi) (setq a (- a pi)))
            (setq entry
              (vl-some
                '(lambda (x)
                   (if (< (urb:axis-angle-distance a (car x))
                          (* pi (/ 10.0 180.0)))
                     x nil))
                bins))
            (if entry
              (setq bins
                (subst (list (car entry) (+ (cadr entry) len)) entry bins))
              (setq bins (cons (list a len) bins)))))))
    (setq i (1+ i)))
  (setq best nil)
  (foreach entry bins
    (if (or (null best) (> (cadr entry) (cadr best))) (setq best entry)))
  (if best (car best) nil)
)

(defun urb:lwpoly-points-with-arcs-fine (ename)
  ;; muestreo ADAPTATIVO (~1 por metro de arco): solo para la cadena de la
  ;; franja tactil, que necesita seguir el arco real (con 8 cuerdas por
  ;; arco la guia salia poligonal/zigzag)
  (urb:lwpoly-points-with-arcs-impl ename T)
)

(defun urb:lwpoly-points-with-arcs-impl
  (ename adaptive / data points item raw-verts current-pt current-bulge n-samples
   i p1 p2 b mids closed-flag wcs-verts end-param j frac tparam pt param1)
  ;; Igual que urb:lwpoly-points, pero si un segmento tiene bulge (arco
  ;; real dibujado con la opcion Arc de PLINE) lo subdivide en varios
  ;; puntos intermedios siguiendo el arco real en vez de tratarlo como una
  ;; sola cuerda recta. Sin esto, un anden con un tramo curvo dibujado como
  ;; un unico arco (no como muchos segmentos rectos cortos) se modula como
  ;; si fuera un solo panel recto de esquina a esquina.
  (setq data (entget ename))
  (setq raw-verts nil current-pt nil current-bulge 0.0 closed-flag nil)
  (foreach item data
    (cond
      ((= (car item) 10)
        (if current-pt
          (setq raw-verts (cons (list current-pt current-bulge) raw-verts)))
        (setq current-pt (list (cadr item) (caddr item)))
        (setq current-bulge 0.0))
      ((= (car item) 42) (setq current-bulge (cdr item)))
      ((= (car item) 70) (setq closed-flag (= 1 (logand (cdr item) 1))))))
  (if current-pt
    (setq raw-verts (cons (list current-pt current-bulge) raw-verts)))
  (setq raw-verts (reverse raw-verts))
  ;; A WCS una sola vez; urb:arc-bulge-midpoints necesita puntos en el
  ;; mismo espacio que entiende vlax-curve.
  (setq wcs-verts
    (mapcar
      '(lambda (v)
        (list (trans (list (car (car v)) (cadr (car v)) 0.0) ename 0) (cadr v)))
      raw-verts))
  (setq n-samples 8)
  (setq points nil i 0)
  (repeat (length wcs-verts)
    (setq p1 (car (nth i wcs-verts)) b (cadr (nth i wcs-verts)))
    (setq points (cons (list (car p1) (cadr p1)) points))
    (if (and (/= b 0.0) (< (1+ i) (length wcs-verts)))
      (progn
        (setq p2 (car (nth (1+ i) wcs-verts)))
        (setq n-samples (if adaptive (urb:arc-samples-for p1 p2 b) 8))
        (setq mids (urb:arc-bulge-midpoints ename p1 p2 n-samples))
        (foreach m mids (setq points (cons m points)))))
    (setq i (1+ i)))
  (setq points (reverse points))
  ;; Cierre: si es cerrada y el ultimo vertice tiene bulge, ese arco cierra
  ;; contra el primer vertice y no queda representado en el bucle anterior.
  ;; El primer vertice esta en el parametro 0 de la curva, pero para
  ;; continuar despues del ultimo vertice hay que usar el parametro final
  ;; real (EndParam), no volver a buscar el punto de partida.
  (if (and closed-flag wcs-verts (> (length wcs-verts) 1))
    (progn
      (setq p1 (car (nth (1- (length wcs-verts)) wcs-verts))
            b (cadr (nth (1- (length wcs-verts)) wcs-verts)))
      (if (/= b 0.0)
        (progn
          (setq end-param (vl-catch-all-apply 'vlax-curve-getEndParam (list ename)))
          (if (not (vl-catch-all-error-p end-param))
            (progn
              (setq param1
                (vl-catch-all-apply 'vlax-curve-getParamAtPoint (list ename p1)))
              (if (not (vl-catch-all-error-p param1))
                (progn
                  ;; mismo criterio de muestreo que los arcos interiores
                  (setq n-samples
                    (if adaptive
                      (urb:arc-samples-for p1 (car (nth 0 wcs-verts)) b)
                      8))
                  (setq j 1)
                  (repeat (1- n-samples)
                    (setq frac (/ (float j) (float n-samples)))
                    (setq tparam (+ param1 (* frac (- end-param param1))))
                    (setq pt
                      (vl-catch-all-apply 'vlax-curve-getPointAtParam (list ename tparam)))
                    ;; getPointAtParam devuelve NIL (sin error) con un
                    ;; parametro fuera de rango: sin este chequeo se
                    ;; apendaba (nil nil) y todo lo aguas abajo reventaba
                    ;; con "bad argument type: 2D/3D point: (nil nil)".
                    (if (and (not (vl-catch-all-error-p pt)) pt)
                      (setq points (append points (list (list (car pt) (cadr pt))))))
                    (setq j (1+ j)))))))))))
  points
)

(defun urb:longest-edge-angle
  (points / closed p1 p2 edge-length best angle-value)
  (setq closed (append points (list (car points))))
  (setq best -1.0)
  (while (cadr closed)
    (setq p1 (car closed))
    (setq p2 (cadr closed))
    (setq edge-length (distance p1 p2))
    (if (> edge-length best)
      (progn
        (setq best edge-length)
        (setq angle-value (angle p1 p2))))
    (setq closed (cdr closed))
  )
  angle-value
)

(defun urb:project-bounds
  (points angle-value / cosine sine first ucoord vcoord
   umin umax vmin vmax point)
  (setq cosine (cos angle-value))
  (setq sine (sin angle-value))
  (setq first T)
  (foreach point points
    (setq ucoord
      (+ (* (car point) cosine) (* (cadr point) sine)))
    (setq vcoord
      (+ (* (- (car point)) sine) (* (cadr point) cosine)))
    (if first
      (progn
        (setq umin ucoord umax ucoord vmin vcoord vmax vcoord)
        (setq first nil))
      (progn
        (setq umin (min umin ucoord))
        (setq umax (max umax ucoord))
        (setq vmin (min vmin vcoord))
        (setq vmax (max vmax vcoord))))
  )
  (list umin umax vmin vmax)
)

(defun urb:normalize-axis-angle (angle-value)
  ;; El eje no tiene sentido de avance: 0 y PI representan la misma
  ;; alineacion. Mantenerlo en [0, PI) evita giros graficos innecesarios.
  (while (< angle-value 0.0)
    (setq angle-value (+ angle-value pi)))
  (while (>= angle-value pi)
    (setq angle-value (- angle-value pi)))
  angle-value
)

(defun urb:normalize-full-angle (angle-value)
  ;; PatternAngle trabaja con una direccion completa, no solo con un eje.
  (while (< angle-value 0.0)
    (setq angle-value (+ angle-value (* 2.0 pi))))
  (while (>= angle-value (* 2.0 pi))
    (setq angle-value (- angle-value (* 2.0 pi))))
  angle-value
)

(defun urb:wcs-angle-to-current-ucs
  (angle-value / ucs-x ucs-angle)
  ;; La geometria del anden y su eje se calculan en WCS. AutoCAD interpreta
  ;; PatternAngle respecto al eje X del UCS actual, por lo que se descuenta
  ;; la rotacion de ese UCS antes de asignar el patron.
  (setq ucs-x (getvar "UCSXDIR"))
  (setq ucs-angle
    (atan (cadr ucs-x) (car ucs-x)))
  (urb:normalize-full-angle (- angle-value ucs-angle))
)

(defun urb:anden-axis-angle
  (points / closed p1 p2 edge-length candidate bounds
   u-length v-length box-area aspect best-area best-aspect best-angle)
  ;; Busca el rectangulo orientado de menor area entre las direcciones de
  ;; todos los bordes. Su lado mayor define el eje longitudinal del anden.
  ;; Es mas estable que usar un unico borde largo en contornos trapezoidales,
  ;; sesgados o con remates diagonales.
  (if (> (length points) 2)
    (progn
      (setq closed (append points (list (car points))))
      (while (cadr closed)
        (setq p1 (car closed)
              p2 (cadr closed)
              edge-length (distance p1 p2))
        (if (> edge-length 1e-8)
          (progn
            (setq candidate (angle p1 p2))
            (setq bounds (urb:project-bounds points candidate))
            (setq u-length (max 0.0 (- (nth 1 bounds) (nth 0 bounds)))
                  v-length (max 0.0 (- (nth 3 bounds) (nth 2 bounds)))
                  box-area (* u-length v-length))
            (if (> v-length u-length)
              (progn
                (setq candidate (+ candidate (/ pi 2.0)))
                (setq aspect
                  (if (> u-length 1e-9) (/ v-length u-length) 1e99)))
              (setq aspect
                (if (> v-length 1e-9) (/ u-length v-length) 1e99)))
            (if (or
                  (null best-area)
                  (< box-area (- best-area 1e-8))
                  (and (equal box-area best-area 1e-8)
                       (> aspect best-aspect)))
              (setq best-area box-area
                    best-aspect aspect
                    best-angle candidate))))
        (setq closed (cdr closed)))
      (urb:normalize-axis-angle
        (if best-angle best-angle (urb:longest-edge-angle points))))
    (urb:longest-edge-angle points))
)

(defun urb:axis-angle-distance (left right / difference)
  (setq left (urb:normalize-axis-angle left)
        right (urb:normalize-axis-angle right)
        difference (abs (- left right)))
  (min difference (- pi difference))
)

(defun urb:polygon-edge-records
  (points / closed p1 p2 edge-length result)
  (if (> (length points) 1)
    (progn
      (setq closed (append points (list (car points))))
      (while (cadr closed)
        (setq p1 (car closed)
              p2 (cadr closed)
              edge-length (distance p1 p2))
        (if (> edge-length 1e-8)
          (setq result
            (cons
              (list p1 p2 edge-length
                (urb:normalize-axis-angle (angle p1 p2)))
              result)))
        (setq closed (cdr closed)))))
  (reverse result)
)

(defun urb:edge-cluster-from-edges
  (edges / edge weight sine-sum cosine-sum angle-value)
  ;; El promedio se calcula sobre 2*angulo porque un eje no tiene sentido:
  ;; 0 y 180 grados representan la misma direccion.
  (setq weight 0.0 sine-sum 0.0 cosine-sum 0.0)
  (foreach edge edges
    (setq weight (+ weight (nth 2 edge))
          sine-sum
            (+ sine-sum
              (* (nth 2 edge) (sin (* 2.0 (nth 3 edge)))))
          cosine-sum
            (+ cosine-sum
              (* (nth 2 edge) (cos (* 2.0 (nth 3 edge)))))))
  (setq angle-value
    (urb:normalize-axis-angle
      (* 0.5 (atan sine-sum cosine-sum))))
  (list angle-value weight edges)
)

(defun urb:edge-axis-clusters
  (points tolerance / edges clusters edge cluster found updated)
  (setq edges (urb:polygon-edge-records points))
  (foreach edge edges
    (setq found nil updated nil)
    (foreach cluster clusters
      (if (and (not found)
               (<=
                 (urb:axis-angle-distance
                   (nth 3 edge) (car cluster))
                 tolerance))
        (progn
          (setq updated
            (cons
              (urb:edge-cluster-from-edges
                (cons edge (nth 2 cluster)))
              updated))
          (setq found T))
        (setq updated (cons cluster updated))))
    (if (not found)
      (setq updated
        (cons (urb:edge-cluster-from-edges (list edge)) updated)))
    (setq clusters (reverse updated)))
  (vl-sort clusters
    '(lambda (left right) (> (nth 1 left) (nth 1 right))))
)

(defun urb:dominant-anden-axis-clusters
  (points / clusters first second)
  ;; Diez grados absorben pequeños quiebres de levantamiento sin mezclar
  ;; brazos realmente diferentes. El segundo eje debe aportar al menos
  ;; 20% de la longitud del principal y separarse como minimo 15 grados.
  (setq clusters
    (urb:edge-axis-clusters points (* pi (/ 10.0 180.0))))
  ;; Un par de lados de cierre puede tener bastante longitud en andenes
  ;; cortos, pero no representa otro brazo. Solo se conservan familias que
  ;; realmente forman un corredor: dos bordes opuestos cuyo desarrollo
  ;; longitudinal supera claramente su separacion transversal.
  (setq clusters
    (vl-remove-if-not 'urb:corridor-axis-cluster-p clusters))
  (if clusters
    (progn
      (setq first (car clusters)
            second (cadr clusters))
      (if (and second
               (>= (nth 1 second) (* 0.20 (nth 1 first)))
               (>=
                 (urb:axis-angle-distance
                   (car first) (car second))
                 (* pi (/ 15.0 180.0))))
        (list first second)
        (list first)))
    nil)
)

(defun urb:axis-descriptor-from-cluster
  (cluster / angle-value edges edge point midpoint ucoord vcoord
   first umin umax vmin vmax width-value length-value aspect)
  (setq angle-value (car cluster)
        edges (urb:cluster-principal-edges cluster)
        first T)
  (foreach edge edges
    (foreach point (list (car edge) (cadr edge))
      (setq ucoord
        (+ (* (car point) (cos angle-value))
           (* (cadr point) (sin angle-value))))
      (if first
        (setq umin ucoord umax ucoord first nil)
        (setq umin (min umin ucoord)
              umax (max umax ucoord))))
    (setq midpoint
      (list
        (/ (+ (car (car edge)) (car (cadr edge))) 2.0)
        (/ (+ (cadr (car edge)) (cadr (cadr edge))) 2.0)
        0.0)
          vcoord (urb:point-v-coordinate midpoint angle-value))
    (if (null vmin)
      (setq vmin vcoord vmax vcoord)
      (setq vmin (min vmin vcoord)
            vmax (max vmax vcoord))))
  (setq width-value (abs (- vmax vmin))
        length-value (max 0.0 (- umax umin))
        aspect
          (if (> width-value 1e-8)
            (/ length-value width-value)
            0.0))
  (list angle-value (/ (+ vmin vmax) 2.0) umin umax
    width-value aspect)
)

(defun urb:corridor-axis-cluster-p (cluster / descriptor)
  (setq descriptor (urb:axis-descriptor-from-cluster cluster))
  (and
    (>= (length (urb:cluster-principal-edges cluster)) 2)
    (> (nth 4 descriptor) 1e-6)
    (>= (nth 5 descriptor) 1.50))
)

(defun urb:cluster-principal-edges
  (cluster / edges maximum edge)
  (setq edges (nth 2 cluster)
        maximum 0.0)
  (foreach edge edges
    (setq maximum (max maximum (nth 2 edge))))
  (vl-remove-if
    '(lambda (item) (< (nth 2 item) (* maximum 0.25)))
    edges)
)

(defun urb:axis-descriptor-intersection
  (left right / a1 a2 v1 v2 n1x n1y n2x n2y determinant x y)
  (setq a1 (nth 0 left)
        v1 (nth 1 left)
        a2 (nth 0 right)
        v2 (nth 1 right)
        n1x (- (sin a1))
        n1y (cos a1)
        n2x (- (sin a2))
        n2y (cos a2)
        determinant (- (* n1x n2y) (* n1y n2x)))
  (if (> (abs determinant) 1e-8)
    (progn
      (setq x
        (/ (- (* v1 n2y) (* n1y v2)) determinant)
            y
        (/ (- (* n1x v2) (* v1 n2x)) determinant))
      (list x y 0.0))
    nil)
)

(defun urb:axis-outward-vector
  (descriptor joint / angle-value joint-u lower upper direction)
  (setq angle-value (nth 0 descriptor)
        joint-u
          (+ (* (car joint) (cos angle-value))
             (* (cadr joint) (sin angle-value)))
        lower (abs (- joint-u (nth 2 descriptor)))
        upper (abs (- (nth 3 descriptor) joint-u))
        direction (if (> upper lower) 1.0 -1.0))
  (list
    (* direction (cos angle-value))
    (* direction (sin angle-value))
    0.0)
)

(defun urb:two-axis-split-data
  (points first-cluster second-cluster
   / first second joint vector1 vector2 bisector split-angle bounds
   span margin split-v rep1 rep1-v)
  (setq first
    (urb:axis-descriptor-from-cluster first-cluster)
        second
    (urb:axis-descriptor-from-cluster second-cluster)
        joint (urb:axis-descriptor-intersection first second))
  (if joint
    (progn
      (setq vector1 (urb:axis-outward-vector first joint)
            vector2 (urb:axis-outward-vector second joint)
            bisector
              (list
                (+ (car vector1) (car vector2))
                (+ (cadr vector1) (cadr vector2))
                0.0))
      (if (< (distance '(0.0 0.0 0.0) bisector) 1e-8)
        (setq bisector
          (list (- (cadr vector1)) (car vector1) 0.0)))
      (setq split-angle (angle '(0.0 0.0 0.0) bisector)
            bounds (urb:project-bounds points split-angle)
            span
              (max
                (- (nth 1 bounds) (nth 0 bounds))
                (- (nth 3 bounds) (nth 2 bounds))
                1.0)
            margin (+ span 10.0)
            split-v (urb:point-v-coordinate joint split-angle)
            rep1
              (list
                (+ (car joint) (* span (car vector1)))
                (+ (cadr joint) (* span (cadr vector1)))
                0.0)
            rep1-v (urb:point-v-coordinate rep1 split-angle))
      (list first second joint split-angle bounds margin split-v
        (< rep1-v split-v)))
    nil)
)

(defun urb:object-box-points
  (object / minimum maximum min-list max-list result)
  (setq result
    (vl-catch-all-apply
      'vla-GetBoundingBox
      (list object 'minimum 'maximum)))
  (if (vl-catch-all-error-p result)
    nil
    (progn
      (setq min-list (vlax-safearray->list minimum)
            max-list (vlax-safearray->list maximum))
      (list
        (list (car min-list) (cadr min-list)
          (if (caddr min-list) (caddr min-list) 0.0))
        (list (car max-list) (cadr min-list)
          (if (caddr min-list) (caddr min-list) 0.0))
        (list (car max-list) (cadr max-list)
          (if (caddr max-list) (caddr max-list) 0.0))
        (list (car min-list) (cadr max-list)
          (if (caddr max-list) (caddr max-list) 0.0)))))
)

(defun urb:region-outline-points
  (region / exploded objects object ename start-param end-param
   steps index parameter point points box)
  ;; La caja WCS de una REGION rotada es mayor que su geometria real.
  ;; Usarla para iniciar la modulacion genera franjas parciales en ambos
  ;; extremos. Explotar una copia logica de sus bordes permite calcular
  ;; las proyecciones sobre el contorno verdadero, incluso con arcos.
  (setq exploded
    (vl-catch-all-apply 'vla-Explode (list region)))
  (if (not (vl-catch-all-error-p exploded))
    (progn
      (setq objects (urb:variant-object-list exploded))
      (foreach object objects
        (setq ename
          (vl-catch-all-apply
            'vlax-vla-object->ename
            (list object)))
        (if (not (vl-catch-all-error-p ename))
          (progn
            (setq start-param
              (vl-catch-all-apply
                'vlax-curve-getStartParam
                (list ename))
                  end-param
              (vl-catch-all-apply
                'vlax-curve-getEndParam
                (list ename)))
            (if (and (numberp start-param) (numberp end-param))
              (progn
                ;; En una recta los extremos son exactos: las 15 muestras
                ;; interiores repetian trabajo en cada borde de cada banda.
                ;; Los arcos/curvas conservan su muestreo anterior.
                (setq steps (if (= "LINE" (cdr (assoc 0 (entget ename)))) 1 16)
                      index 0)
                (repeat (1+ steps)
                  (setq parameter
                    (+ start-param
                      (* (/ (float index) steps)
                        (- end-param start-param))))
                  (setq point
                    (vl-catch-all-apply
                      'vlax-curve-getPointAtParam
                      (list ename parameter)))
                  (if (and point (not (vl-catch-all-error-p point)))
                    (setq points (cons point points)))
                  (setq index (1+ index))))
              (progn
                (setq box (urb:object-box-points object))
                (if box (setq points (append box points)))))))
        (urb:safe-delete object))))
  (reverse points)
)

;; 5.0.3 Codex / BOG085CD119BDQN. Solo limites graficos del HATCH:
;; fuente ACIS, contorno, cantidades y XDATA permanecen intactos.
;; Error de cuerda <0.1 mm. Caso reproducido: arcos CW de R=260.714 m.
(defun urb:hatch-arc-lines (edge / c r a b ccw sweep n j p q out)
  (setq c (cdr (assoc 10 edge)) r (cdr (assoc 40 edge))
        a (cdr (assoc 50 edge)) b (cdr (assoc 51 edge))
        ccw (= 1 (cdr (assoc 73 edge))))
  (if (and c (numberp r) (> r 1e-8) (numberp a) (numberp b))
    (progn
      (setq sweep (- b a))
      (if (not ccw) (setq a (- a) b (- b)))
      (while (< sweep 0.0) (setq sweep (+ sweep (* 2.0 pi))))
      ;; DXF horario guarda angulos negados; no confundirlo con un giro
      ;; de casi 2*pi. No tocar circulos genuinos ni arcos mayores:
      ;; en las pequenas piezas obtenidas al recortar las bandas.
      (if (and (> sweep 1e-12) (< sweep (- (* 2.0 pi) 1e-10)))
        (progn
          (setq n (1+ (fix (/ sweep (sqrt (/ 0.0008 r))))))
          (setq j 0 p (polar c a r))
          (repeat n
            (setq j (1+ j)
                  q (polar c (+ a (* (if ccw 1.0 -1.0) sweep (/ (float j) n))) r)
                  out (append out (list '(72 . 1) (cons 10 p) (cons 11 q)))
                  p q))
          out)))))

(defun urb:hatch-linearized-data (data / tail item flag count edge flat edges out changed refs)
  (setq tail data flag 0)
  (while tail
    (setq item (car tail) tail (cdr tail))
    (if (= (car item) 92) (setq flag (cdr item)))
    (if (and (= (car item) 93) (= 0 (logand flag 2)))
      (progn
        (setq count 0 edges nil)
        (while (and tail (= (caar tail) 72))
          (setq edge (list (car tail)) tail (cdr tail))
          (while (and tail (not (member (caar tail) '(72 97))))
            (setq edge (append edge (list (car tail))) tail (cdr tail)))
          (setq flat (if (= (cdar edge) 2) (urb:hatch-arc-lines edge)))
          (if flat
            (setq changed T count (+ count (/ (length flat) 3)) edges (append edges flat))
            (setq count (1+ count) edges (append edges edge))))
        (setq out (append out (cons (cons 93 count) edges))))
      (setq out (append out (list item)))))
  (if changed
    (progn
      ;; Desasociar el HATCH aproximado para que Evaluate no restaure los
      ;; arcos. Los objetos fuente conservan geometria y etiquetas intactas.
      (setq tail out out nil)
      (while tail
        (setq item (car tail) tail (cdr tail))
        (cond
          ((= (car item) 71) (setq out (cons '(71 . 0) out)))
          ((= (car item) 97)
            (setq refs (cdr item) out (cons '(97 . 0) out))
            (repeat refs (if (= (caar tail) 330) (setq tail (cdr tail)))))
          (T (setq out (cons item out)))))
      (reverse out))))

(defun urb:hatch-render-data (data)
  ;; No reescribir el formato de splines/elipses (sus grupos 97 difieren).
  (if (not (vl-some
      '(lambda (v) (and (= (car v) 72) (> (cdr v) 2))) data))
    (urb:hatch-linearized-data data)))

(defun urb:stabilize-curved-hatch (hatch / en data fixed result)
  (setq en (urb:as-ename hatch) data (if en (entget en '("*"))))
  (if (and data (= (cdr (assoc 0 data)) "HATCH")
           (wcmatch (strcase (cdr (assoc 8 data))) "URB-ANDEN-*")
           (setq fixed (urb:hatch-render-data data)))
    (progn
      (setq result (vl-catch-all-apply
        '(lambda ()
           (if (not (entmod fixed)) (vl-exit-with-error "HATCH: no se pudo reparar el contorno grafico"))
           (vla-Evaluate (vlax-ename->vla-object en))
           (entupd en)
           T)))
      (if (vl-catch-all-error-p result)
        (progn (entmod data) (entupd en) nil)
        result))))

(defun urb:evaluate-render-hatch (hatch / data)
  (vla-Evaluate hatch)
  (urb:stabilize-curved-hatch hatch)
  (setq data (entget (vlax-vla-object->ename hatch)))
  (if (and (wcmatch (cdr (assoc 8 data)) "URB-ANDEN-*")
           (urb:hatch-render-data data))
    (progn
      (urb:safe-delete hatch)
      (vl-exit-with-error "HATCH curvo: no se pudo garantizar el relleno; se descarta la pieza.")))
  hatch)

(defun urb:repair-anden-hatches (/ block obj en data result n failed)
  ;; Incluye rellenos sueltos y empaquetados, nunca XREF.
  ;; tblnext BLOCK omite Model/PaperSpace: usar la coleccion completa.
  (setq n 0 failed 0)
  (vlax-for block (vla-get-Blocks (urb:doc))
    (if (= :vlax-false (vla-get-IsXRef block))
      (vlax-for obj block
          (setq en (vlax-vla-object->ename obj) data (entget en))
          (if (and (= (cdr (assoc 0 data)) "HATCH")
                   (wcmatch (cdr (assoc 8 data)) "URB-ANDEN-*"))
            (progn
              (setq result (vl-catch-all-apply 'urb:stabilize-curved-hatch (list en)))
              (cond
                ((vl-catch-all-error-p result) (setq failed (1+ failed)))
                (result (setq n (1+ n)))
                ((urb:hatch-render-data data) (setq failed (1+ failed)))))))))
  (if (> n 0)
    (prompt (strcat "\nANDEN: " (itoa n) " rellenos curvos estabilizados; contornos y cantidades conservados.")))
  (if (> failed 0)
    (prompt (strcat "\nANDEN: " (itoa failed) " rellenos pendientes de revision.")))
  n)

;; 2026-09-14: envoltorio con sello de esquema. La reparacion sigue
;; disponible entera (urb:repair-anden-hatches) para llamarla a mano o
;; cuando cambie EL ALGORITMO; una version de entrega nueva no debe repetir
;; el barrido completo del dibujo sin nada que reparar. Los DWG que ya
;; tienen el antiguo sello por version se migran al esquema sin otro censo.
(defun urb:repair-anden-hatches-si-hace-falta (/ sello legacy actual n)
  (setq actual "HATCH_RENDER_V1"
        sello (urb:safe-string (urb:config-read "URB_HATCH_REPAIR_SCHEMA") "")
        legacy (urb:safe-string (urb:config-read "URB_HATCH_REPAIR_VER") ""))
  (cond
    ((= sello actual) 0)
    ((and (= sello "") (/= legacy ""))
      (urb:config-write "URB_HATCH_REPAIR_SCHEMA" actual)
      0)
    (T
      (setq n (urb:repair-anden-hatches))
      (urb:config-write "URB_HATCH_REPAIR_SCHEMA" actual)
      n)))

(defun urb:add-solid-hatch (boundary layer color / hatch)
  (setq layer (urb:safe-string layer "0"))
  (setq hatch
    (vla-AddHatch
      (urb:space)
      1
      "SOLID"
      :vlax-true))
  (vla-AppendOuterLoop hatch (urb:make-loop-array boundary))
  (vla-put-Layer hatch layer)
  (vla-put-Color hatch color)
  (urb:evaluate-render-hatch hatch)
  hatch
)

(defun urb:add-user-hatch-raw
  (boundary layer spacing angle-value double-lines color origin
   / hatch pattern-angle)
  (setq layer (urb:safe-string layer "0"))
  (setq pattern-angle
    (urb:wcs-angle-to-current-ucs angle-value))
  (setq hatch
    (vla-AddHatch
      (urb:space)
      0
      "USER"
      :vlax-true))
  (vla-AppendOuterLoop hatch (urb:make-loop-array boundary))
  (vla-put-Layer hatch layer)
  (vla-put-Color hatch color)
  ;; PatternDouble puede regenerar la definicion USER y devolver el angulo
  ;; a cero. Se configura primero y la rotacion se aplica al final.
  (vla-put-PatternDouble hatch
    (if double-lines :vlax-true :vlax-false))
  (vla-put-PatternSpace hatch spacing)
  (vla-put-PatternAngle hatch pattern-angle)
  (urb:evaluate-render-hatch hatch)
  (if origin
    (urb:set-hatch-origin-dxf hatch origin))
  hatch
)

(defun urb:set-hatch-origin-dxf
  (hatch origin / ename edata item result)
  ;; USER hatches store each pattern-line base in DXF 43/44.
  ;; Updating those codes avoids the global hatch-origin phase.
  (setq ename (vlax-vla-object->ename hatch))
  (setq edata (entget ename))
  (foreach item edata
    (setq result
      (cons
        (cond
          ((= (car item) 43) (cons 43 (car origin)))
          ((= (car item) 44) (cons 44 (cadr origin)))
          (T item))
        result)))
  (if (entmod (reverse result))
    (progn
      (entupd ename)
      T)
    nil)
)

(defun urb:add-user-hatch
  (boundary layer spacing angle-value double-lines color origin
   / result)
  (setq result
    (vl-catch-all-apply
      'urb:add-user-hatch-raw
      (list boundary layer spacing angle-value double-lines color origin)))
  result
)

(defun urb:safe-delete (obj / result)
  (if (urb:valid-vla-object-p obj)
    (progn
      (setq result (vl-catch-all-apply 'vla-Delete (list obj)))
      (if (vl-catch-all-error-p result) nil T))
    nil)
)

(defun urb:region-usable-p (region / area-value)
  ;; Una operacion ACIS puede terminar sin excepcion y aun devolver una
  ;; region vacia/degenerada. Esas regiones fallan despues al crear el
  ;; HATCH y antes se contaban como bandas validas, dejando el fondo negro.
  (setq area-value
    (if (urb:valid-vla-object-p region)
      (vl-catch-all-apply 'vla-get-Area (list region))
      nil))
  (and (numberp area-value) (> area-value 1e-10))
)

(defun urb:stripe-overlaps ()
  ;; Solapes progresivos en metros. Siempre se expanden LOS DOS bordes:
  ;; las bandas vecinas se pisan unas milesimas en vez de separarse.
  '(0.0 0.0005 0.0015 0.004 0.010)
)

(defun urb:clip-stripe-once
  (base-region umin umax vmin vmax angle-value
   / clipped stripe result box elevation)
  (setq clipped (vla-Copy base-region))
  (setq box (urb:object-box-points base-region)
        elevation
          (if (and box (caddr (car box)))
            (caddr (car box))
            0.0))
  (setq stripe
    (urb:rectangle-region
      umin umax vmin vmax angle-value elevation))
  (if (vl-catch-all-error-p stripe)
    (progn
      (urb:safe-delete clipped)
      nil)
    (progn
      (setq result
        (vl-catch-all-apply
          'vla-Boolean
          (list clipped 1 stripe)))
      ;; Boolean consume normalmente la segunda region; si una version de
      ;; AutoCAD la conserva, se limpia de forma defensiva.
      (urb:safe-delete stripe)
      (if (or (vl-catch-all-error-p result)
              (not (urb:region-usable-p clipped)))
        (progn
          (urb:safe-delete clipped)
          nil)
        clipped)
    )
  )
)

;; 2026-08-12 v2: el reintento anterior TRASLADABA toda la banda. Eso
;; rompia la tangencia, pero podia abrir una separacion en el borde que se
;; alejaba de la banda vecina. Ahora la banda se ENSANCHA simetricamente,
;; se valida su area real y el solape queda oculto por el orden de dibujo.
(defun urb:clip-stripe
  (base-region umin umax vmin vmax angle-value / result eps)
  (foreach eps (urb:stripe-overlaps)
    (if (null result)
      (setq result
        (urb:clip-stripe-once
          base-region (- umin eps) (+ umax eps)
          (- vmin eps) (+ vmax eps) angle-value))))
  result
)

(defun urb:grid-phase-shift (global-offset module / m)
  ;; Resto de global-offset sobre "module" en [0, module): cuanto hay que
  ;; correr el origen local de una reticula para que sus juntas caigan
  ;; sobre la reticula GLOBAL de la cadena (juntas cada "module" desde el
  ;; arranque de la cadena completa, no desde cada segmento o banda).
  (setq m (- global-offset (* module (fix (/ global-offset module)))))
  (if (< m 0.0) (+ m module) m)
)

(defun urb:snap-to-row (value vbase module)
  ;; Ajusta un v local a la fila de tabletas mas cercana de la reticula
  ;; anclada en vbase (el mismo anclaje que usa el material), para que la
  ;; franja de guia ocupe filas COMPLETAS de la modulacion en vez de una
  ;; cinta corrida que no respeta las juntas de la loseta.
  (+ vbase (* module (fix (+ (/ (- value vbase) module) (if (< value vbase) -0.5 0.5)))))
)

(defun urb:quad-region (q1 q2 q3 q4 elevation / coords poly region)
  (setq coords
    (apply 'append
      (mapcar '(lambda (p) (list (car p) (cadr p))) (list q1 q2 q3 q4))))
  (setq poly
    (vla-AddLightWeightPolyline
      (urb:space)
      (urb:double-array-variant coords)))
  (if (and (numberp elevation)
           (vlax-property-available-p poly 'Elevation T))
    (vla-put-Elevation poly elevation))
  (vla-put-Closed poly :vlax-true)
  (setq region (urb:add-region-from-object poly))
  (vla-Delete poly)
  region
)

(defun urb:point-near-2d-p (left right tolerance / dx dy)
  (if (and left right)
    (progn
      (setq dx (- (car left) (car right))
            dy (- (cadr left) (cadr right)))
      (<= (+ (* dx dx) (* dy dy)) (* tolerance tolerance)))
    nil)
)

(defun urb:clean-polygon-points (raw-points / result point)
  ;; El muestreo de arcos puede repetir un vertice en una union. Los
  ;; duplicados consecutivos producen triangulos degenerados.
  (foreach point raw-points
    (if (or (null result)
            (not (urb:point-near-2d-p point (car result) 1e-8)))
      (setq result (cons point result))))
  (setq result (reverse result))
  (if (and (> (length result) 2)
           (urb:point-near-2d-p
             (car result) (last result) 1e-8))
    (setq result (reverse (cdr (reverse result)))))
  result
)

(defun urb:polygon-signed-area (points / area i p1 p2 n)
  (setq area 0.0 i 0 n (length points))
  (repeat n
    (setq p1 (nth i points)
          p2 (nth (rem (1+ i) n) points)
          area (+ area (- (* (car p1) (cadr p2))
                          (* (car p2) (cadr p1))))
          i (1+ i)))
  (* 0.5 area)
)

(defun urb:polygon-concave-p (points / clean n orientation i a b c cross found)
  ;; Un entrante alrededor de un contenedor NO es un segundo brazo del
  ;; anden. Detectarlo impide que el modulador de andenes en L cambie de
  ;; eje para "rodear" el vacio y deja una sola reticula continua.
  (setq clean (urb:clean-polygon-points points)
        n (length clean))
  (if (< n 4)
    nil
    (progn
      (setq orientation (if (< (urb:polygon-signed-area clean) 0.0) -1.0 1.0)
            i 0 found nil)
      (while (and (< i n) (not found))
        (setq a (nth (rem (+ i n -1) n) clean)
              b (nth i clean)
              c (nth (rem (1+ i) n) clean)
              cross (urb:triangle-cross a b c))
        (if (< (* orientation cross) -1e-9) (setq found T))
        (setq i (1+ i)))
      found))
)

(defun urb:triangle-cross (a b c)
  (- (* (- (car b) (car a)) (- (cadr c) (cadr a)))
     (* (- (cadr b) (cadr a)) (- (car c) (car a))))
)

(defun urb:point-in-triangle-p (p a b c / c1 c2 c3 tol)
  (setq tol 1e-9
        c1 (urb:triangle-cross a b p)
        c2 (urb:triangle-cross b c p)
        c3 (urb:triangle-cross c a p))
  (or (and (>= c1 (- tol)) (>= c2 (- tol)) (>= c3 (- tol)))
      (and (<= c1 tol) (<= c2 tol) (<= c3 tol)))
)

(defun urb:remove-point-once (points target / removed result point)
  (foreach point points
    (if (and (not removed) (urb:point-near-2d-p point target 1e-12))
      (setq removed T)
      (setq result (cons point result))))
  (reverse result)
)

(defun urb:triangulate-polygon
  (points / verts triangles guard n i prev cur nxt test contains ear-found
   cursor scan determinant xmin xmax ymin ymax padx pady)
  ;; Ear clipping sobre el contorno ordenado de la LWPOLYLINE. Cada
  ;; triangulo es convexo y su interseccion con una banda tambien lo es;
  ;; evita la operacion ACIS multi-isla que falla en curvas concavas.
  (setq verts (urb:clean-polygon-points points))
  (if (< (urb:polygon-signed-area verts) 0.0)
    (setq verts (reverse verts)))
  (setq guard 0 triangles nil)
  (while (and (> (length verts) 3) (< guard 20000))
    (setq n (length verts) i 0 ear-found nil cursor verts prev (last verts))
    (while (and (< i n) (not ear-found))
      (setq cur (car cursor) nxt (if (cdr cursor) (cadr cursor) (car verts))
            determinant (urb:triangle-cross prev cur nxt))
      (if (> determinant 1e-10)
        (progn
          ;; Misma eleccion de orejas y misma tolerancia del predicado.
          ;; Caja conservadora: las coordenadas baricentricas admiten
          ;; +/- tol/determinante; ampliar 2*tol/D por el rango del eje
          ;; incluye tambien la segunda rama del test en triangulos finos.
          (setq xmin (min (car prev) (car cur) (car nxt))
                xmax (max (car prev) (car cur) (car nxt))
                ymin (min (cadr prev) (cadr cur) (cadr nxt))
                ymax (max (cadr prev) (cadr cur) (cadr nxt))
                padx (+ 1e-8 (* (/ 2e-9 determinant) (- xmax xmin)))
                pady (+ 1e-8 (* (/ 2e-9 determinant) (- ymax ymin)))
                xmin (- xmin padx) xmax (+ xmax padx)
                ymin (- ymin pady) ymax (+ ymax pady)
                contains nil scan verts)
          (while (and scan (not contains))
            (setq test (car scan))
            (if (and (<= xmin (car test) xmax) (<= ymin (cadr test) ymax)
                     (not (urb:point-near-2d-p test prev 1e-12))
                     (not (urb:point-near-2d-p test cur 1e-12))
                     (not (urb:point-near-2d-p test nxt 1e-12))
                     (urb:point-in-triangle-p test prev cur nxt))
              (setq contains T))
            (setq scan (cdr scan)))
          (if (not contains)
            (progn
              (setq triangles (cons (list prev cur nxt) triangles)
                    verts (urb:remove-point-once verts cur)
                    ear-found T)))))
      (setq i (1+ i) prev cur cursor (cdr cursor)))
    (if (not ear-found) (setq guard 20000))
    (setq guard (1+ guard)))
  (if (= (length verts) 3)
    (reverse (cons verts triangles))
    nil)
)

(defun urb:point-u-coordinate (point angle-value)
  (+ (* (car point) (cos angle-value))
     (* (cadr point) (sin angle-value)))
)

(defun urb:u-boundary-intersection
  (p1 p2 u1 u2 limit / ratio)
  (if (< (abs (- u2 u1)) 1e-12)
    p2
    (progn
      (setq ratio (/ (- limit u1) (- u2 u1)))
      (list
        (+ (car p1) (* ratio (- (car p2) (car p1))))
        (+ (cadr p1) (* ratio (- (cadr p2) (cadr p1)))))))
)

(defun urb:clip-polygon-u-side
  (points limit angle-value keep-greater
   / output previous current previous-u current-u previous-in current-in)
  (if points
    (progn
      (setq previous (last points)
            previous-u (urb:point-u-coordinate previous angle-value)
            previous-in
              (if keep-greater (>= previous-u (- limit 1e-9))
                (<= previous-u (+ limit 1e-9))))
      (foreach current points
        (setq current-u (urb:point-u-coordinate current angle-value)
              current-in
                (if keep-greater (>= current-u (- limit 1e-9))
                  (<= current-u (+ limit 1e-9))))
        (cond
          (current-in
            (if (not previous-in)
              (setq output
                (append output
                  (list (urb:u-boundary-intersection
                          previous current previous-u current-u limit)))))
            (setq output (append output (list current))))
          (previous-in
            (setq output
              (append output
                (list (urb:u-boundary-intersection
                        previous current previous-u current-u limit))))))
        (setq previous current previous-u current-u previous-in current-in))))
  (urb:clean-polygon-points output)
)

(defun urb:clip-polygon-to-band (points umin umax angle-value / clipped)
  (setq clipped (urb:clip-polygon-u-side points umin angle-value T))
  (if clipped
    (setq clipped (urb:clip-polygon-u-side clipped umax angle-value nil)))
  (if (and clipped (> (length clipped) 2)
           (> (abs (urb:polygon-signed-area clipped)) 1e-10))
    clipped
    nil)
)

(defun urb:polygon-region (points elevation / coords poly region)
  (setq coords
    (apply 'append
      (mapcar '(lambda (p) (list (car p) (cadr p))) points)))
  (setq poly
    (vla-AddLightWeightPolyline (urb:space)
      (urb:double-array-variant coords)))
  (if (and (numberp elevation)
           (vlax-property-available-p poly 'Elevation T))
    (vla-put-Elevation poly elevation))
  (vla-put-Closed poly :vlax-true)
  (setq region (urb:add-region-from-object poly))
  (urb:safe-delete poly)
  (if (vl-catch-all-error-p region) nil region)
)

(defun urb:add-solid-hatch-detached-safe
  (boundary layer color / hatch result)
  (setq hatch
    (vl-catch-all-apply 'vla-AddHatch
      (list (urb:space) 1 "SOLID" :vlax-false)))
  (if (vl-catch-all-error-p hatch)
    nil
    (progn
      (setq result
        (vl-catch-all-apply
          '(lambda ()
             (vla-AppendOuterLoop hatch (urb:make-loop-array boundary))
             (vla-put-Layer hatch layer)
             (vla-put-Color hatch color)
             (urb:evaluate-render-hatch hatch)
             hatch)))
      (if (vl-catch-all-error-p result)
        (progn (urb:safe-delete hatch) nil)
        hatch)))
)

(defun urb:add-user-hatch-detached-safe
  (boundary layer spacing angle-value double-lines color origin
   / hatch result pattern-angle)
  (setq pattern-angle (urb:wcs-angle-to-current-ucs angle-value))
  (setq hatch
    (vl-catch-all-apply 'vla-AddHatch
      (list (urb:space) 0 "USER" :vlax-false)))
  (if (vl-catch-all-error-p hatch)
    nil
    (progn
      (setq result
        (vl-catch-all-apply
          '(lambda ()
             (vla-AppendOuterLoop hatch (urb:make-loop-array boundary))
             (vla-put-Layer hatch layer)
             (vla-put-Color hatch color)
             (vla-put-PatternDouble hatch
               (if double-lines :vlax-true :vlax-false))
             (vla-put-PatternSpace hatch spacing)
             (vla-put-PatternAngle hatch pattern-angle)
             (urb:evaluate-render-hatch hatch)
             (if origin (urb:set-hatch-origin-dxf hatch origin))
             hatch)))
      (if (vl-catch-all-error-p result)
        (progn (urb:safe-delete hatch) nil)
        hatch)))
)

(defun urb:decorate-composite-fallback-piece
  (points elevation angle-value origin parent-handle gray
   / region layer color solid joint1 joint2 success)
  (setq region (urb:polygon-region points elevation))
  (if region
    (progn
      (setq layer
        (if gray "URB-ANDEN-LOSETA-GRIS-20X20"
          "URB-ANDEN-BLOQUE-BLANCO-20X10")
            color (if gray 8 7)
            solid (urb:add-solid-hatch-detached-safe region layer color))
      (if solid
        (progn
          (urb:tag-generated-role solid parent-handle "FILL")
          (if gray
            (progn
              (setq joint1
                (urb:add-user-hatch-detached-safe
                  region layer 0.20 angle-value T 9 origin))
              (if joint1
                (urb:tag-generated-role joint1 parent-handle "JOINT")))
            (progn
              (setq joint1
                (urb:add-user-hatch-detached-safe
                  region layer 0.10 angle-value nil 8 origin))
              (setq joint2
                (urb:add-user-hatch-detached-safe
                  region layer 0.20 (+ angle-value (/ pi 2.0)) nil 8 origin))
              (if joint1
                (urb:tag-generated-role joint1 parent-handle "JOINT"))
              (if joint2
                (urb:tag-generated-role joint2 parent-handle "JOINT"))))
          (setq success T)))
      (urb:safe-delete region)))
  success
)

(defun urb:decorate-composite-band-fallback
  (triangles umin umax angle-value origin parent-handle gray elevation
   / triangle piece count)
  ;; Solo se usa para la banda que ACIS no pudo resolver. No pinta un
  ;; fondo general: cada pieza hereda el tono y la fase de ESA banda.
  (setq count 0)
  (foreach triangle triangles
    (setq piece (urb:clip-polygon-to-band triangle umin umax angle-value))
    (if (and piece
             (urb:decorate-composite-fallback-piece
               piece elevation angle-value origin parent-handle gray))
      (setq count (1+ count))))
  (> count 0)
)

(defun urb:clip-edge-wedge
  (base-region p1 p2 bis1 bis2 span
   / d1 d2 q1 q2 q3 q4 clipped wedge result box elevation
   den t1 t2 ix iy s1p s1n s2p s2n)
  ;; Extremos abiertos: la tapa la decide el contorno real, no la normal
  ;; a su primera/ultima CUERDA. Esa normal amputaba dos cunas en curvas.
  ;; Las bisectrices INTERIORES se conservan para empatar sin traslapes.
  (if (null bis1)
    (setq bis1 (+ (angle p1 p2) (* 0.5 pi))
          p1 (polar p1 (angle p2 p1) span)))
  (if (null bis2)
    (setq bis2 (+ (angle p1 p2) (* 0.5 pi))
          p2 (polar p2 (angle p1 p2) span)))
  ;; Recorta base-region con un cuadrilatero cuyos lados extremos son las
  ;; BISECTRICES en los dos extremos de la arista (junta a inglete): las
  ;; franjas de aristas vecinas empatan exactamente en la bisectriz, sin
  ;; traslaparse ni dejar cunas vacias. Los rectangulos por-arista que se
  ;; usaban antes se pisaban entre si en cada quiebre de la cadena y el
  ;; material o la guia quedaban dibujados DOS veces con angulos distintos
  ;; (la "guia cruzada en diagonal sobre la reticula" que reporto el
  ;; usuario en las transiciones de curva).
  (setq box (urb:object-box-points base-region)
        elevation (if (and box (caddr (car box))) (caddr (car box)) 0.0))
  (setq d1 (list (cos bis1) (sin bis1))
        d2 (list (cos bis2) (sin bis2)))
  ;; En una curva cerrada las dos bisectrices se CRUZAN en el centro de
  ;; curvatura: extender la cuna el span completo hacia ese lado la hace
  ;; atravesar el centro y pintar tambien el lado OPUESTO del anillo (se
  ;; vio como una malla cruzada/zigzag en el medio de un anden en abanico).
  ;; Se recorta la extension de ese lado justo antes del cruce.
  (setq den (- (* (car d1) (cadr d2)) (* (cadr d1) (car d2))))
  (setq t1 nil t2 nil)
  (if (> (abs den) 1e-9)
    (progn
      (setq t1 (/ (- (* (- (car p2) (car p1)) (cadr d2))
                     (* (- (cadr p2) (cadr p1)) (car d2)))
                  den))
      (setq ix (+ (car p1) (* t1 (car d1)))
            iy (+ (cadr p1) (* t1 (cadr d1))))
      (setq t2 (+ (* (- ix (car p2)) (car d2))
                  (* (- iy (cadr p2)) (cadr d2))))))
  (setq s1p span s1n span s2p span s2n span)
  (if (and t1 (> t1 0.0)) (setq s1p (min span (* 0.999 t1))))
  (if (and t1 (< t1 0.0)) (setq s1n (min span (* 0.999 (- t1)))))
  (if (and t2 (> t2 0.0)) (setq s2p (min span (* 0.999 t2))))
  (if (and t2 (< t2 0.0)) (setq s2n (min span (* 0.999 (- t2)))))
  (setq q1 (list (+ (car p1) (* s1p (car d1))) (+ (cadr p1) (* s1p (cadr d1))))
        q2 (list (+ (car p2) (* s2p (car d2))) (+ (cadr p2) (* s2p (cadr d2))))
        q3 (list (- (car p2) (* s2n (car d2))) (- (cadr p2) (* s2n (cadr d2))))
        q4 (list (- (car p1) (* s1n (car d1))) (- (cadr p1) (* s1n (cadr d1)))))
  (setq wedge (vl-catch-all-apply 'urb:quad-region (list q1 q2 q3 q4 elevation)))
  (if (vl-catch-all-error-p wedge)
    nil
    (progn
      (setq clipped (vla-Copy base-region))
      (setq result (vl-catch-all-apply 'vla-Boolean (list clipped 1 wedge)))
      (if (vl-catch-all-error-p result)
        (progn
          (urb:safe-delete clipped)
          (urb:safe-delete wedge)
          nil)
        clipped)))
)

(defun urb:chain-edge-bisectors (edges / n i result prev-dir cur-dir next-dir b1 b2)
  ;; Para cada arista de una cadena ABIERTA: los angulos de las lineas de
  ;; corte en sus dos extremos. En un vertice interior es la bisectriz
  ;; entre las direcciones reales de las dos aristas que se encuentran
  ;; (rotada 90 para ser linea de corte); en los extremos de la cadena es
  ;; la perpendicular a la propia arista. Se recalcula la direccion real
  ;; con (angle p1 p2) porque el (nth 3 edge) viene colapsado a medio giro
  ;; por urb:normalize-axis-angle y perderia el sentido de avance.
  (setq n (length edges) result nil i 0)
  (repeat n
    (setq cur-dir
      (urb:normalize-full-angle
        (angle (nth 0 (nth i edges)) (nth 1 (nth i edges)))))
    (setq prev-dir
      (if (> i 0)
        (urb:normalize-full-angle
          (angle (nth 0 (nth (1- i) edges)) (nth 1 (nth (1- i) edges))))
        nil))
    (setq next-dir
      (if (< i (1- n))
        (urb:normalize-full-angle
          (angle (nth 0 (nth (1+ i) edges)) (nth 1 (nth (1+ i) edges))))
        nil))
    (setq b1
      (+ (if prev-dir
           (+ prev-dir (* 0.5 (urb:turning-angle prev-dir cur-dir)))
           cur-dir)
         (* 0.5 pi)))
    (setq b2
      (+ (if next-dir
           (+ cur-dir (* 0.5 (urb:turning-angle cur-dir next-dir)))
           cur-dir)
         (* 0.5 pi)))
    (setq result (cons (list b1 b2) result))
    (setq i (1+ i)))
  (reverse result)
)

(defun urb:points-span (points / bounds)
  ;; Longitud generosa para extender las cunas de recorte mas alla de todo
  ;; el contorno (diagonal del bbox + margen).
  (setq bounds (urb:project-bounds points 0.0))
  (+ (- (nth 1 bounds) (nth 0 bounds))
     (- (nth 3 bounds) (nth 2 bounds))
     10.0)
)

(defun urb:add-solid-hatch-safe
  (boundary layer color / hatch result)
  ;; Variante transaccional para las bandas del anden. Si AppendOuterLoop,
  ;; propiedades o Evaluate fallan, elimina el HATCH parcial y devuelve nil;
  ;; asi el caller puede volver a recortar y reintentar la banda completa.
  (setq hatch
    (vl-catch-all-apply
      'vla-AddHatch
      (list (urb:space) 1 "SOLID" :vlax-true)))
  (if (vl-catch-all-error-p hatch)
    nil
    (progn
      (setq result
        (vl-catch-all-apply
          '(lambda ()
             (vla-AppendOuterLoop hatch (urb:make-loop-array boundary))
             (vla-put-Layer hatch (urb:safe-string layer "0"))
             (vla-put-Color hatch color)
             (urb:evaluate-render-hatch hatch)
             hatch)))
      (if (vl-catch-all-error-p result)
        (progn (urb:safe-delete hatch) nil)
        hatch)))
)

(defun urb:decorate-gray-stripe
  (region angle-value origin parent-handle / result joints)
  ;; Antes vivia en la capa auxiliar URB-ANDEN-AUX (no imprimible, separada
  ;; del material). Se fusiono en la capa de material real; el rol FILL
  ;; (xdata) es lo que mantiene el orden de dibujo correcto ahora.
  (vla-put-Layer region "URB-ANDEN-LOSETA-GRIS-20X20")
  (urb:tag-generated-role region parent-handle "FILL")
  (setq result
    (urb:add-solid-hatch-safe
      region "URB-ANDEN-LOSETA-GRIS-20X20" 8))
  (if result
    (progn
      (urb:tag-generated-role result parent-handle "FILL")
      (setq joints
        (urb:add-user-hatch
          region
          "URB-ANDEN-LOSETA-GRIS-20X20"
          0.20
          angle-value
          T
          9
          origin))
      (urb:tag-generated-role joints parent-handle "JOINT")
      T)
    nil)
)

(defun urb:decorate-white-stripe
  (region angle-value origin parent-handle / result joints-u joints-v)
  (vla-put-Layer region "URB-ANDEN-BLOQUE-BLANCO-20X10")
  (urb:tag-generated-role region parent-handle "FILL")
  (setq result
    (urb:add-solid-hatch-safe
      region "URB-ANDEN-BLOQUE-BLANCO-20X10" 7))
  (if result
    (progn
      (urb:tag-generated-role result parent-handle "FILL")
      ;; Bloque blanco de 0.20 x 0.10 m, alineado con el origen comun.
      (setq joints-u
        (urb:add-user-hatch
          region
          "URB-ANDEN-BLOQUE-BLANCO-20X10"
          0.10
          angle-value
          nil
          8
          origin))
      (urb:tag-generated-role joints-u parent-handle "JOINT")
      (setq joints-v
        (urb:add-user-hatch
          region
          "URB-ANDEN-BLOQUE-BLANCO-20X10"
          0.20
          (+ angle-value (/ pi 2.0))
          nil
          8
          origin))
      (urb:tag-generated-role joints-v parent-handle "JOINT")
      T)
    nil)
)

(defun urb:region-split-faces (region / exploded items faces o)
  ;; 2026-09-11 (medido en Civil real): una region con caras SEPARADAS --
  ;; la banda del anden que cruzan las aletas y la banda A-80 de un acceso
  ;; vehicular -- no sirve de borde de HATCH ("Automation Error. Invalid
  ;; input"), pero cada cara por separado si. Devuelve las caras como
  ;; regiones sueltas, o nil si la region tiene una sola cara.
  (setq exploded (vl-catch-all-apply 'vla-Explode (list region)))
  (if (not (vl-catch-all-error-p exploded))
    (progn
      (setq items (urb:variant-object-list exploded))
      (foreach o items
        (if (= (vla-get-ObjectName o) "AcDbRegion")
          (setq faces (cons o faces))
          (urb:safe-delete o)))
      (if (< (length faces) 2)
        (progn (foreach o faces (urb:safe-delete o)) (setq faces nil)))))
  (reverse faces)
)

(defun urb:decorate-stripe-region (region angle-value origin parent-handle gray)
  (if gray
    (urb:decorate-gray-stripe region angle-value origin parent-handle)
    (urb:decorate-white-stripe region angle-value origin parent-handle))
)

(defun urb:decorate-composite-stripe
  (base-region umin umax vmin vmax angle-value origin parent-handle gray
   / eps region success faces face-ok)
  ;; El exito exige DOS cosas: region con area y relleno SOLID evaluado.
  ;; Si cualquiera falla, elimina la tentativa y repite con mas solape.
  (foreach eps (urb:stripe-overlaps)
    (if (null success)
      (progn
        (setq region
          (urb:clip-stripe-once
            base-region (- umin eps) (+ umax eps)
            (- vmin eps) (+ vmax eps) angle-value))
        (if region
          (progn
            (setq success
              (urb:decorate-stripe-region
                region angle-value origin parent-handle gray))
            ;; banda partida en varias caras: se decora cara por cara con
            ;; el MISMO origen, asi la franja sigue siendo una sola banda
            ;; y no desaparece al lado de un bordillo que la corta
            (if (and (not success)
                     (setq faces (urb:region-split-faces region)))
              (progn
                (setq face-ok 0)
                (foreach f faces
                  (if (urb:decorate-stripe-region
                        f angle-value origin parent-handle gray)
                    (setq face-ok (1+ face-ok))
                    (urb:safe-delete f)))
                (if (> face-ok 0)
                  (progn (urb:safe-delete region) (setq success T region nil)))))
            (if (not success) (urb:safe-delete region)))))))
  success
)

(defun urb:create-two-axis-regions
  (base-region split-data / first second split-angle bounds margin split-v
   first-low umin umax vmin vmax first-region second-region)
  (setq first (nth 0 split-data)
        second (nth 1 split-data)
        split-angle (nth 3 split-data)
        bounds (nth 4 split-data)
        margin (nth 5 split-data)
        split-v (nth 6 split-data)
        first-low (nth 7 split-data)
        umin (- (nth 0 bounds) margin)
        umax (+ (nth 1 bounds) margin)
        vmin (- (nth 2 bounds) margin)
        vmax (+ (nth 3 bounds) margin))
  (if first-low
    (setq first-region
      (urb:clip-stripe
        base-region umin umax vmin split-v split-angle)
          second-region
      (urb:clip-stripe
        base-region umin umax split-v vmax split-angle))
    (setq first-region
      (urb:clip-stripe
        base-region umin umax split-v vmax split-angle)
          second-region
      (urb:clip-stripe
        base-region umin umax vmin split-v split-angle)))
  (if (and first-region second-region)
    (list
      (list first-region (nth 0 first))
      (list second-region (nth 0 second)))
    (progn
      (urb:safe-delete first-region)
      (urb:safe-delete second-region)
      nil))
)

(defun urb:composite-phase-state (phase-offset / gray-w white-w period phase-mod)
  ;; Dado un phase-offset (distancia global acumulada desde el arranque de
  ;; TODO el patron gris/blanco, no solo este segmento), devuelve
  ;; (gris-actual . ancho-restante-de-esa-banda): el color y cuanto falta
  ;; de la banda que ya estaba a medio camino cuando arranca este
  ;; segmento, para continuar el patron 0.80/1.00m sin reiniciar. Sin
  ;; esto, cada segmento de una curva reinicia su propia franja gris en
  ;; u=0 y el patron se ve partido/reducido a una sola hilera en las
  ;; transiciones (aristas cortas del muestreo de arco).
  (setq gray-w 0.80 white-w 1.00)
  (setq period (+ gray-w white-w))
  (setq phase-mod (- phase-offset (* period (fix (/ phase-offset period)))))
  (if (< phase-mod 0.0) (setq phase-mod (+ phase-mod period)))
  (if (< phase-mod gray-w)
    (cons T (- gray-w phase-mod))
    (cons nil (- period phase-mod))))

(defun urb:segment-phase-info
  (u1 u2 actual-umin actual-umax cumulative total reverse-pattern
   / decreasing local-reverse start-u station phase)
  ;; Fase REAL en el borde de una cuna a inglete. La cuna sobresale antes
  ;; y despues de la cuerda del tramo; usar CUMULATIVE directamente en su
  ;; umin reiniciaba el gris/blanco unos centimetros corrido y producia la
  ;; pieza triangular que se veia en andenes de curva suave. Tambien se
  ;; respeta si la cadena recorre el eje U en sentido decreciente.
  (setq decreasing (< u2 u1)
        local-reverse
          (if reverse-pattern (not decreasing) decreasing)
        start-u (if local-reverse actual-umax actual-umin)
        station
          (+ cumulative
             (if decreasing (- u1 start-u) (- start-u u1)))
        phase (if reverse-pattern (- total station) station))
  (list local-reverse phase)
)

(defun urb:decorate-composite-region
  (base-region angle-value format parent-handle reverse-pattern phase-offset
   fallback-points
   / points bounds umin umax actual-vmin actual-vmax vmin vmax
   cursor next gray count origin pattern-v-origin module layer grid
   phase-state first-band band-width iter-guard band-ok fallback-triangles
   elevation box all-bands-ok band-umin band-umax net-loops
   coverage-triangles coverage-ok ring ring-triangles)
  (setq points (urb:region-outline-points base-region))
  (if (null points)
    (setq points (urb:object-box-points base-region)))
  (setq module (urb:loseta-module format))
  (if (null points)
    (progn (urb:safe-delete base-region) nil)
    (progn
      (setq bounds (urb:project-bounds points angle-value)
            umin (nth 0 bounds)
            umax (nth 1 bounds)
            actual-vmin (nth 2 bounds)
            actual-vmax (nth 3 bounds)
            pattern-v-origin actual-vmin)
      ;; Origen UNICO de reticula para toda la zona, corrido para caer
      ;; sobre la reticula GLOBAL de la cadena (phase-offset = distancia
      ;; acumulada desde el arranque). Antes cada banda anclaba su propia
      ;; reticula en su umin local: la primera banda parcial de cada
      ;; segmento quedaba con las juntas corridas respecto al resto del
      ;; corredor, y la franja de guia/toperol (que ancla a esta misma
      ;; reticula global) no coincidia con las juntas del material.
      (setq origin
        (urb:local-to-world
          (if reverse-pattern
            (+ umax (urb:grid-phase-shift (if phase-offset phase-offset 0.0) module))
            (- umin (urb:grid-phase-shift (if phase-offset phase-offset 0.0) module)))
          pattern-v-origin angle-value))
      (if (> module 0.30)
        (progn
          ;; Cada zona conserva su propia reticula, pero sigue perteneciendo
          ;; al mismo bloque y al mismo registro de cantidades.
          (setq layer "URB-ANDEN-LOSETA-LISA-40X40")
          (vla-put-Layer base-region layer)
          (urb:tag-generated-role base-region parent-handle "FILL")
          (setq grid
            (urb:add-user-hatch
              base-region layer module angle-value T 9 origin))
          (if (not (vl-catch-all-error-p grid))
            (urb:tag-generated-role grid parent-handle "JOINT")
            ;; zona partida en varias caras (v4.94): reticula por cara
            ((lambda (faces / ok g)
               (foreach f faces
                 (vla-put-Layer f layer)
                 (urb:tag-generated-role f parent-handle "FILL")
                 (setq g (urb:add-user-hatch f layer module angle-value T 9 origin))
                 (if (not (vl-catch-all-error-p g))
                   (progn (urb:tag-generated-role g parent-handle "JOINT")
                          (setq ok T))))
               (if ok (progn (urb:safe-delete base-region) (setq grid T))))
             (urb:region-split-faces base-region)))
          (and grid (not (vl-catch-all-error-p grid))))
        (progn
          ;; Detalle 20x20: 0.80 m de loseta gris y 1.00 m de adoquin
          ;; blanco, repetidos sobre el eje local de esta zona.
          ;; El respaldo debe recortar el contorno NETO; usar el original
          ;; rellena prefabricados/obstaculos y da falsos fallos en bandas vacias.
          (setq net-loops (urb:region-polygons base-region)
                fallback-triangles
                  (if (= (length net-loops) 1)
                    (urb:triangulate-polygon (car net-loops)) nil))
          ;; Para detectar bandas VACIAS basta una cobertura de todos los
          ;; anillos, incluidos huecos. Nunca se usa esta cobertura para
          ;; dibujar: rellenaria los huecos de los contenedores.
          (setq coverage-ok (not (null net-loops)))
          (foreach ring net-loops
            (setq ring-triangles (urb:triangulate-polygon ring))
            (if ring-triangles
              (setq coverage-triangles (append coverage-triangles ring-triangles))
              (setq coverage-ok nil)))
          (setq box (urb:object-box-points base-region)
                elevation
                  (if (and box (caddr (car box)))
                    (caddr (car box)) 0.0)
                all-bands-ok T)
          (setq vmin (- actual-vmin 1.0)
                vmax (+ actual-vmax 1.0)
                cursor (if reverse-pattern umax umin)
                count 0)
          (setq phase-state (urb:composite-phase-state (if phase-offset phase-offset 0.0)))
          (setq gray (car phase-state) first-band T iter-guard 0)
          (while
            (and
              (if reverse-pattern
                (> cursor (+ umin 0.000001))
                (< cursor (- umax 0.000001)))
              ;; respaldo defensivo: con un phase-offset acumulado de
              ;; punto flotante, el ancho de la primera banda de cada
              ;; segmento podria salir negativo o casi cero por un caso
              ;; extremo no cubierto en urb:composite-phase-state -- sin
              ;; este limite duro de iteraciones, eso puede colgar el
              ;; comando en vez de simplemente fallar (se vio un
              ;; colgado real al agregar la fase continua sin este
              ;; respaldo). 20000 iteraciones alcanza sobrado para
              ;; cualquier anden real (un modulo de 1.8m en un tramo de
              ;; varios kilometros).
              (< iter-guard 20000))
            (setq iter-guard (1+ iter-guard))
            (setq band-width (if first-band (cdr phase-state) (if gray 0.80 1.00)))
            (if (< band-width 0.001) (setq band-width 0.001))
            (setq next
              (if reverse-pattern
                (max umin (- cursor band-width))
                (min umax (+ cursor band-width))))
            ;; todas las bandas comparten el origen global ya alineado.
            ;; La rutina solo devuelve T cuando tambien existe el SOLID.
            (setq band-umin (if reverse-pattern next cursor)
                  band-umax (if reverse-pattern cursor next))
            (setq band-ok
              (urb:decorate-composite-stripe
                base-region band-umin band-umax vmin vmax angle-value
                origin parent-handle gray))
            ;; Una banda que cruza un contorno concavo puede producir dos
            ;; o mas islas. Si ACIS no devuelve una region util, se recorta
            ;; geometricamente contra triangulos internos; el tono y el
            ;; origen de reticula siguen siendo los de la banda original.
            (if (and (not band-ok) coverage-ok
                     (< (urb:polygon-band-area coverage-triangles
                          band-umin band-umax angle-value) 1e-8))
              (setq band-ok T))
            (if (and (not band-ok) fallback-triangles)
              (setq band-ok
                (if (< (urb:polygon-band-area fallback-triangles
                         band-umin band-umax angle-value) 1e-8)
                  T
                  (urb:decorate-composite-band-fallback
                    fallback-triangles band-umin band-umax angle-value
                    origin parent-handle gray elevation))))
            (if band-ok (setq count (1+ count)))
            (if (not band-ok)
              (progn (setq all-bands-ok nil)
                (urb:bb-log (strcat "  losetas: fallo banda u="
                  (rtos band-umin 2 4) ".." (rtos band-umax 2 4)
                  " anillos=" (itoa (length net-loops))
                  " cobertura=" (vl-princ-to-string coverage-ok)))))
            (setq cursor next
                  gray (not gray)
                  first-band nil))
          ;; La region maestra ya no queda como fondo blanco: ocultaba el
          ;; fallo, pero convertia toda la banda ausente en adoquin blanco.
          (urb:safe-delete base-region)
          (and (> count 0) all-bands-ok)))))
)

(defun urb:turning-angle (a1 a2 / delta two-pi)
  ;; Diferencia angular real (con sentido) entre dos direcciones, normalizada
  ;; al rango -pi a pi. A diferencia de urb:axis-angle-distance (que trata un eje y
  ;; su opuesto como el mismo eje), aqui SI importa el sentido de avance:
  ;; es el angulo que se "gira" al pasar de una arista a la siguiente.
  (setq two-pi (* 2.0 pi))
  (setq delta (- a2 a1))
  (while (> delta pi) (setq delta (- delta two-pi)))
  (while (<= delta (- pi)) (setq delta (+ delta two-pi)))
  delta
)

(defun urb:polygon-corner-indices
  (points threshold / n edges i prev-a next-a delta result prev-edge next-edge)
  ;; Indices de vertices donde el contorno gira mas de "threshold": son las
  ;; esquinas reales (donde un lado largo del anden termina y empieza otro,
  ;; o donde esta la tapa corta de un extremo). Los vertices intermedios de
  ;; un tramo curvo aproximado con muchos segmentos cortos giran poco cada
  ;; uno y no cuentan como esquina.
  (setq n (length points))
  (if (< n 3)
    nil
    (progn
      (setq edges (urb:polygon-edge-records points))
      (setq result nil i 0)
      (repeat n
        ;; OJO: (nth 3 edge) viene de urb:polygon-edge-records, que lo
        ;; normaliza con urb:normalize-axis-angle (colapsa un angulo y su
        ;; opuesto a 180 grados al mismo valor - correcto para agrupar por
        ;; eje, pero aqui necesitamos el sentido real de avance). Se
        ;; recalcula el angulo direccional completo desde los propios
        ;; extremos de cada arista para no heredar ese colapso: si la
        ;; tangente de un tramo curvo pasa cerca de 0/180 grados, usar el
        ;; valor ya colapsado genera un salto falso de ~180 grados justo
        ;; ahi y parte el lado guia en dos a la mitad.
        (setq prev-edge (nth (rem (+ i (1- n)) n) edges)
              next-edge (nth i edges))
        (setq prev-a (urb:normalize-full-angle (angle (nth 0 prev-edge) (nth 1 prev-edge)))
              next-a (urb:normalize-full-angle (angle (nth 0 next-edge) (nth 1 next-edge))))
        (setq delta (urb:turning-angle prev-a next-a))
        (if (> (abs delta) threshold) (setq result (cons i result)))
        (setq i (1+ i)))
      (reverse result))))

(defun urb:polygon-chains-at-corners (points corners / n sorted k chains j start end idx chain)
  ;; Parte el contorno cerrado en tramos abiertos entre esquinas consecutivas.
  ;; Cada tramo conserva sus vertices reales tal como quedaron dibujados.
  (setq n (length points) sorted (vl-sort corners '<) k (length sorted))
  (if (< k 2)
    nil
    (progn
      (setq chains nil j 0)
      (repeat k
        (setq start (nth j sorted)
              end (nth (rem (1+ j) k) sorted))
        (setq idx start chain (list (nth idx points)))
        (while (/= idx end)
          (setq idx (rem (1+ idx) n))
          (setq chain (cons (nth idx points) chain)))
        (setq chains (cons (reverse chain) chains))
        (setq j (1+ j)))
      (reverse chains))))

(defun urb:chain-total-length (chain / total rest)
  (setq total 0.0 rest chain)
  (while (cadr rest)
    (setq total (+ total (distance (car rest) (cadr rest))))
    (setq rest (cdr rest)))
  total
)

(defun urb:longest-chain (chains / best best-length chain len)
  (setq best nil best-length -1.0)
  (foreach chain chains
    (setq len (urb:chain-total-length chain))
    (if (> len best-length) (setq best chain best-length len)))
  best
)

(defun urb:dedupe-ring-points (points / result pt)
  ;; Quita vertices consecutivos duplicados (y el cierre duplicado
  ;; ultimo==primero). Un doble click al dibujar -- o el muestreo de un
  ;; arco que cae exacto sobre el vertice siguiente -- deja una arista de
  ;; longitud CERO: urb:polygon-edge-records la salta, pero
  ;; urb:polygon-corner-indices indexa por vertice, y ese descuadre
  ;; terminaba en (angle nil nil) = "bad argument type: consp nil",
  ;; rechazando por seguridad contornos curvos perfectamente validos.
  (foreach pt points
    ;; descartar de una vez cualquier punto malformado (nil o coordenadas
    ;; no numericas) que se haya colado del muestreo
    (if (and pt (numberp (car pt)) (numberp (cadr pt))
             (or (null result) (> (distance pt (car result)) 1e-8)))
      (setq result (cons pt result))))
  (setq result (reverse result))
  (if (and (> (length result) 1)
           (<= (distance (car result) (last result)) 1e-8))
    (reverse (cdr (reverse result)))
    result)
)

(defun urb:anden-tactile-chain (points / clean corners chains ref best best-d chain mid d maxlargo largo cands)
  ;; Cadena del contorno MAS CERCANA al lado de la via marcado por el
  ;; usuario: la franja tactil debe seguir el borde de la via (p.ej. el
  ;; arco INTERIOR de un anden en abanico), no el lado mas largo del
  ;; contorno -- guiando por el lado largo, en un abanico la guia quedaba
  ;; proyectada desde el otro lado del anillo y salia fragmentada.
  (setq clean (urb:dedupe-ring-points points))
  (setq corners (urb:polygon-corner-indices clean (* pi (/ 45.0 180.0))))
  (setq chains (urb:polygon-chains-at-corners clean corners))
  (setq ref nil)
  (if *urb-current-tactile-side-choice*
    (setq ref (urb:tactile-side-point-from-choice *urb-current-tactile-side-choice* clean)))
  (if (and (null ref) *urb-current-tactile-side-anchor*)
    (setq ref *urb-current-tactile-side-anchor*))
  (if (and (null ref) *urb-current-tactile-side-point*)
    ;; Llamadas internas/pruebas que solo fijan el clic tambien reciben la
    ;; misma proteccion: proyectarlo al borde final antes de comparar cadenas.
    (progn
      (setq ref
        (urb:tactile-side-anchor clean *urb-current-tactile-side-point*))
      (if (null ref) (setq ref *urb-current-tactile-side-point*))))
  (if (or (null ref) (null chains))
    (if chains (urb:longest-chain chains) nil)
    (progn
      ;; 2026-09-12 (reporte del usuario: en un anden con curva "se pierde
      ;; la guia y el toperol"). Medido en un anden en L de 151 ml: el
      ;; contorno se partia bien en 4 cadenas -- costado de la via 151,41,
      ;; costado exterior 153,77 y dos tapas de 1,50 -- pero esta funcion
      ;; devolvia UNA TAPA. Dos motivos, los dos arreglados aqui:
      ;;   1) el filtro de tapas comparaba contra 0,5 m FIJO, y una tapa
      ;;      mide el ancho del anden (1,50 m), asi que lo pasaba. Ahora se
      ;;      compara contra el costado mas largo: una tapa nunca llega al
      ;;      25 % del costado.
      ;;   2) la cercania al clic se media con el PUNTO MEDIO de la cadena.
      ;;      En un costado largo y curvo el medio queda lejisimos del clic
      ;;      y ganaba cualquier tapa cercana. Ahora se usa la distancia
      ;;      MINIMA real de los puntos de la cadena al clic.
      ;; Con la tapa como cadena guia, el caller veia 1 sola arista, no
      ;; entraba a la ruta de offset y caia al metodo por proyeccion, que en
      ;; un anden que gira deja el toperol en una esquina.
      (setq maxlargo 0.0)
      (foreach chain chains
        (setq largo (urb:chain-total-length chain))
        (if (> largo maxlargo) (setq maxlargo largo)))
      (setq cands nil)
      (foreach chain chains
        (if (> (urb:chain-total-length chain) (max 0.5 (* 0.25 maxlargo)))
          (setq cands (cons chain cands))))
      (if (null cands) (setq cands chains))
      (setq best nil best-d nil)
      (foreach chain cands
        (setq d (urb:chain-min-distance chain ref))
        (if (or (null best-d) (< d best-d))
          (setq best chain best-d d)))
      (if best best (urb:longest-chain chains))))
)

;; 5.7.3 (reporte del usuario, foto: "el toperol y la guia quedaron
;; torcidos"). Un anden dibujado RODEANDO contenedores de raices tiene
;; entrantes rectangulares en el costado de la via; sus esquinas de 90
;; grados partian la cadena tactil en pedazos, y por eso el motor la
;; descartaba y trazaba guia y toperol como UNA franja recta para todo el
;; anden -- en un anden con quiebres esa franja queda cruzada. Aqui se
;; quitan del ANILLO los entrantes cortos (cuerda <= 6 m, profundidad <=
;; 1,6 m, alineados con los bordes vecinos a menos de 30 grados); los
;; quiebres reales del anden (lados largos) se conservan. Solo se usa para
;; hallar la cadena guia: el recorte contra el contenedor lo sigue haciendo
;; la region base.
(defun urb:ring-remove-notches
  (pts / ring p n i j k a b ok out changed guard dirprev dirnext chord
          path-length first-angle last-angle chord-angle angle-error
          best-j best-error)
  ;; Dedupe local a 1 mm: OFFSET/REGION deja a veces dos vertices separados
  ;; por decimas de milimetro y parte artificialmente la entrada rectangular.
  (setq ring nil)
  (foreach p pts
    (if (and p (numberp (car p)) (numberp (cadr p))
             (or (null ring) (> (distance p (car ring)) 0.001)))
      (setq ring (cons p ring))))
  (setq ring (reverse ring))
  (if (and (> (length ring) 1)
           (<= (distance (car ring) (last ring)) 0.001))
    (setq ring (reverse (cdr (reverse ring)))))
  (setq changed T guard 0)
  (defun urb:rn-ang (p q) (angle (list (car p) (cadr p)) (list (car q) (cadr q))))
  (defun urb:rn-dang (a1 a2 / d)
    (setq d (abs (- a1 a2)))
    (while (> d pi) (setq d (abs (- d (* 2.0 pi)))))
    d)
  (while (and changed (< guard 100) (> (length ring) 6))
    (setq changed nil guard (1+ guard) n (length ring) i 1)
    ;; No cruzar el inicio arbitrario del anillo: como maximo queda un solo
    ;; entrante partido en el cierre, en vez de confundir ambos costados.
    (while (and (not changed) (< i (- n 4)))
      (setq j (+ i 3) best-j nil best-error nil)
      (while (<= j (min (+ i 10) (- n 2)))
        (setq a (nth i ring) b (nth j ring)
              chord (distance a b)
              chord-angle (urb:rn-ang a b)
              first-angle (urb:rn-ang a (nth (1+ i) ring))
              last-angle (urb:rn-ang (nth (1- j) ring) b)
              ok (and (> chord 0.3) (<= chord 20.0)
                      (> (urb:rn-dang first-angle chord-angle) (* pi (/ 60.0 180.0)))
                      (< (urb:rn-dang first-angle chord-angle) (* pi (/ 120.0 180.0)))
                      (> (urb:rn-dang last-angle chord-angle) (* pi (/ 60.0 180.0)))
                      (< (urb:rn-dang last-angle chord-angle) (* pi (/ 120.0 180.0)))
                      (> (urb:rn-dang first-angle last-angle) (* pi (/ 165.0 180.0))))
              path-length 0.0 k i)
        (while (< k j)
          (setq path-length (+ path-length (distance (nth k ring) (nth (1+ k) ring)))
                k (1+ k)))
        (setq k (1+ i))
        (while (and ok (< k j))
          (if (> (urb:dist-point-seg (nth k ring) a b) 1.6)
            (setq ok nil))
          (setq k (1+ k)))
        (setq dirprev (urb:rn-ang (nth (1- i) ring) a)
              dirnext (urb:rn-ang b (nth (1+ j) ring))
              angle-error (+ (urb:rn-dang dirprev chord-angle)
                             (urb:rn-dang dirnext chord-angle)))
        ;; La propia forma U es prueba suficiente: entrada/salida casi
        ;; perpendiculares al cordon y opuestas entre si, poca profundidad y
        ;; recorrido mayor que su cuerda. No exigir que los vecinos ya esten
        ;; alineados: cuando hay contenedores consecutivos, el vecino puede
        ;; pertenecer al siguiente entrante y esa condicion dejaba zigzags.
        (if (and ok (> (- path-length chord) 0.5)
                 (or (null best-j) (> j best-j)))
          (setq best-j j best-error angle-error))
        (setq j (1+ j)))
      (if best-j
        (progn
          ;; Conservar los extremos sobre el costado y quitar solamente la
          ;; entrada, recorrido interior y salida del desvio ortogonal.
          (setq out nil k 0)
          (foreach p ring
            (if (not (and (> k i) (< k best-j)))
              (setq out (cons p out)))
            (setq k (1+ k)))
          (setq ring (reverse out) changed T))
        (setq i (1+ i)))))
  ring)

;; distancia minima (en planta) de los puntos de una cadena a un punto
(defun urb:chain-min-distance (chain ref / d best r prev p)
  ;; Distancia a la CADENA, no solo a sus vertices. Un costado largo y
  ;; recto puede tener vertices unicamente en los extremos; el costado
  ;; contrario puede tener un vertice intermedio y ganar erroneamente aun
  ;; cuando el clic este pegado al primer costado.
  (setq best nil r (list (car ref) (cadr ref)) prev (car chain))
  (foreach p (cdr chain)
    (setq d (urb:dist-point-seg r prev p))
    (if (or (null best) (< d best)) (setq best d))
    (setq prev p))
  ;; Cadena degenerada de un punto: conservar una distancia valida.
  (if (and (null best) prev) (setq best (distance r prev)))
  (if best best 1e12)
)

(defun urb:anden-driving-chain (points / corners chains)
  ;; Un solo lado largo del anden (tramo abierto de vertices reales) que se
  ;; usa como guia para modular segmento por segmento. Para un anden simple
  ;; de 4 vertices da un unico tramo de 1 arista (equivalente al eje unico
  ;; de siempre); para un anden curvo con muchos vertices da el lado largo
  ;; completo con todos sus quiebres reales.
  (setq points (urb:dedupe-ring-points points))
  (setq corners (urb:polygon-corner-indices points (* pi (/ 45.0 180.0))))
  (setq chains (urb:polygon-chains-at-corners points corners))
  (if chains (urb:longest-chain chains) nil)
)

(defun urb:point-in-list-p (pt lst / found)
  (setq found nil)
  (foreach p lst (if (equal p pt 1e-6) (setq found T)))
  found)

(defun urb:chain-width-samples (points driving-chain / other-points p q d best result)
  ;; Estima el ancho local en cada punto del lado largo (driving-chain)
  ;; como la distancia al punto mas cercano del RESTO del contorno (el
  ;; lado opuesto + remates). No requiere booleans/regiones -- solo sirve
  ;; para detectar una franja que se "infla" en el medio, no para medir
  ;; con precision (eso ya lo hace urb:clip-stripe en el resto del codigo).
  (setq other-points nil)
  (foreach p points
    (if (not (urb:point-in-list-p p driving-chain))
      (setq other-points (cons p other-points))))
  (if (< (length other-points) 1)
    nil
    (progn
      (setq result nil)
      (foreach p driving-chain
        (setq best nil)
        (foreach q other-points
          (setq d (distance p q))
          (if (or (null best) (< d best)) (setq best d)))
        (if best (setq result (cons best result))))
      result)))

(defun urb:anden-width-anomaly-p (points / driving-chain widths minw maxw minmax)
  ;; Detecta un contorno de anden donde el ancho local varia demasiado
  ;; (ej. una franja que se infla bastante en un tramo) -- sintoma de
  ;; clics imprecisos al dibujar, no de un cruce (eso lo cubre
  ;; urb:polygon-self-intersects-p aparte). Un anden real puede angostarse
  ;; gradualmente (una rampa, un remate) sin que eso sea un error; el
  ;; umbral (relacion Y diferencia absoluta) busca solo el caso de bulto
  ;; ancho e inesperado, no variaciones normales de diseno.
  ;;
  ;; IMPORTANTE: se usa min/max RECORTADO (urb:trimmed-min-max), no el
  ;; min/max crudo. urb:chain-width-samples mide distancia al punto mas
  ;; cercano del resto del contorno, y ese heuristico falla puntualmente
  ;; justo antes de una esquina (verificado con un caso real: de 27
  ;; muestras, 26 dieron 3.96-4.93m consistente y solo 1 punto aislado
  ;; junto a una esquina salto a 11.2m). Con min/max crudo ese unico punto
  ;; disparaba un falso positivo sobre un anden bien dibujado.
  (setq driving-chain (urb:anden-driving-chain points))
  (if (and driving-chain (>= (length driving-chain) 2))
    (progn
      (setq widths (urb:chain-width-samples points driving-chain))
      (if (and widths (>= (length widths) 2))
        (progn
          (setq minmax (urb:trimmed-min-max widths))
          (setq minw (nth 0 minmax) maxw (nth 1 minmax))
          (and (> maxw (* 2.5 (max minw 0.01))) (> (- maxw minw) 1.5)))
        nil))
    nil))

(defun urb:trimmed-min-max (widths / sorted n trim)
  ;; min/max descartando el ~10% superior e inferior (minimo 1 muestra de
  ;; cada lado si hay suficientes datos) para no dejar que UN punto atipico
  ;; (comun cerca de una esquina, ver comentario de
  ;; urb:anden-width-anomaly-p) dispare la deteccion.
  (setq sorted (vl-sort widths '<))
  (setq n (length sorted))
  (setq trim (max 1 (fix (* n 0.10))))
  (if (< n (* 2 (1+ trim)))
    (list (car sorted) (last sorted))
    (list (nth trim sorted) (nth (- n 1 trim) sorted))))

(defun urb:open-chain-edges (chain-points / result rest p1 p2 edge-length)
  ;; Igual que urb:polygon-edge-records pero para un tramo ABIERTO (no cierra
  ;; el ultimo vertice contra el primero).
  (setq rest chain-points result nil)
  (while (cadr rest)
    (setq p1 (car rest) p2 (cadr rest) edge-length (distance p1 p2))
    (if (> edge-length 1e-8)
      (setq result
        (cons (list p1 p2 edge-length (urb:normalize-axis-angle (angle p1 p2))) result)))
    (setq rest (cdr rest)))
  (reverse result)
)

(defun urb:decorate-composite-region-segmented
  (base-region driving-chain format parent-handle reverse-pattern
   / edges edge angle-value cosine sine u1 u2 umin umax
   bounds-all vmin-all vmax-all slice count points-all
   cum-offset total-length phase-offset bisectors edge-index bis span
   slice-points slice-bounds actual-umin actual-umax phase-info
   local-reverse)
  ;; Modula el anden segmento por segmento siguiendo el contorno real en vez
  ;; de un unico eje: cada arista del lado guia recorta su propia franja del
  ;; anden (el resto del ancho se recorta solo por el boolean contra el
  ;; contorno real) y se decora con SU angulo local, para que la reticula
  ;; siga la curva en lugar de desviarse a medida que uno se aleja del punto
  ;; donde se calculo el eje unico.
  ;; cum-offset/phase-offset: igual que en urb:create-accessibility-
  ;; features-segmented, para que el patron gris/blanco de 0.80/1.00m sea
  ;; una sola progresion continua a lo largo de todo el corredor en vez de
  ;; reiniciar en cada arista corta del muestreo de un arco (lo que dejaba
  ;; solo una hilera de adoquin en las transiciones de curva).
  (setq edges (urb:open-chain-edges driving-chain))
  (setq points-all (urb:region-outline-points base-region))
  (if (null points-all) (setq points-all (urb:object-box-points base-region)))
  (setq count 0 cum-offset 0.0 edge-index 0)
  (setq total-length (urb:chain-total-length driving-chain))
  ;; Cunas a inglete (bisectrices) en vez de rectangulos por-arista: los
  ;; rectangulos de aristas vecinas se traslapaban en los quiebres y el
  ;; patron quedaba pintado dos veces con angulos distintos en cada
  ;; transicion de curva. Si la cuna falla (boolean degenerado), se cae al
  ;; rectangulo de siempre para no dejar la arista sin material.
  (setq bisectors (urb:chain-edge-bisectors edges))
  (setq span (urb:points-span points-all))
  (foreach edge edges
    (setq angle-value (nth 3 edge)
          cosine (cos angle-value)
          sine (sin angle-value))
    (setq u1 (+ (* (car (nth 0 edge)) cosine) (* (cadr (nth 0 edge)) sine)))
    (setq u2 (+ (* (car (nth 1 edge)) cosine) (* (cadr (nth 1 edge)) sine)))
    (setq umin (min u1 u2) umax (max u1 u2))
    (setq bis (nth edge-index bisectors))
    (setq slice
      (urb:clip-edge-wedge
        base-region (nth 0 edge) (nth 1 edge)
        (if (= edge-index 0) nil (nth 0 bis))
        (if (= edge-index (1- (length edges))) nil (nth 1 bis)) span))
    (if (null slice)
      (progn
        (setq bounds-all (urb:project-bounds points-all angle-value)
              vmin-all (nth 2 bounds-all)
              vmax-all (nth 3 bounds-all))
        (setq slice (urb:clip-stripe base-region umin umax vmin-all vmax-all angle-value))))
    (if slice
      (progn
        ;; La cuna a inglete no empieza exactamente en p1: sus esquinas
        ;; se prolongan segun la bisectriz. Medir esos limites reales y
        ;; continuar alli la fase global evita la cuna gris/blanca
        ;; diagonal entre dos tramos visualmente rectos.
        (setq slice-points (urb:region-outline-points slice))
        (if (null slice-points)
          (setq slice-points (urb:object-box-points slice)))
        (setq slice-bounds (urb:project-bounds slice-points angle-value)
              actual-umin (nth 0 slice-bounds)
              actual-umax (nth 1 slice-bounds)
              phase-info
                (urb:segment-phase-info
                  u1 u2 actual-umin actual-umax cum-offset total-length
                  reverse-pattern)
              local-reverse (car phase-info)
              phase-offset (cadr phase-info))
        (urb:decorate-composite-region
          slice angle-value format parent-handle local-reverse phase-offset nil)
        (setq count (1+ count))))
    (setq cum-offset (+ cum-offset (nth 2 edge)))
    (setq edge-index (1+ edge-index)))
  (urb:safe-delete base-region)
  (> count 0)
)

;; 2026-09-12: cuanto gira una cadena entre su primera y su ultima arista.
;; Sirve para saber si el anden es un corredor que cambia de rumbo (y por
;; tanto no se puede modular con un solo eje) o es practicamente recto.
(defun urb:chain-direction-drift (chain / edges e1 edge drift)
  (if (null chain)
    0.0
    (progn
      (setq edges (urb:open-chain-edges chain))
      (if (< (length edges) 2)
        0.0
        (progn
          (setq e1 (car edges) drift 0.0)
          (foreach edge (cdr edges)
            (setq drift (max drift
              (urb:axis-angle-distance (nth 3 e1) (nth 3 edge)))))
          drift))))
)

(defun urb:chain-off-axis-length (chain tolerance / edges edge reference longest total)
  ;; Longitud que realmente cambia de rumbo respecto al tramo dominante.
  ;; Un vertice residual de pocos centimetros puede tener 10-40 grados de
  ;; diferencia y, con el maximo angular puro, convertia un anden recto en
  ;; dos tramos con una cuna diagonal. La longitud ponderada distingue ese
  ;; residuo de una curva o quiebre arquitectonico sostenido.
  (setq edges (urb:open-chain-edges chain)
        reference nil longest -1.0 total 0.0)
  (foreach edge edges
    (if (> (nth 2 edge) longest)
      (setq longest (nth 2 edge) reference (nth 3 edge))))
  (if reference
    (foreach edge edges
      (if (> (urb:axis-angle-distance reference (nth 3 edge)) tolerance)
        (setq total (+ total (nth 2 edge))))))
  total
)

;; 2026-09-12: une aristas consecutivas que van casi en la misma direccion,
;; para que un arco muestreado fino (decenas de aristas de 20 cm) se vuelva
;; unos pocos TRAMOS RECTOS. Asi el material se modula por tramos -- cada
;; tramo con su propia orientacion, como en el plano -- y no en un abanico
;; continuo, que es lo que el usuario rechazo el 2026-08-09.
(defun urb:chain-simplify-by-direction (chain tol / out ini prev dir d i p)
  (if (< (length chain) 3)
    chain
    (progn
      (setq out (list (car chain)) ini (car chain) prev (cadr chain))
      (setq dir (angle ini prev))
      (setq i 2)
      (while (< i (length chain))
        (setq p (nth i chain))
        (setq d (angle prev p))
        (if (> (urb:axis-angle-distance dir d) tol)
          (progn
            ;; el tramo se cierra en el punto anterior y arranca otro
            (setq out (cons prev out))
            (setq ini prev)
            (setq dir (angle ini p))))
        (setq prev p)
        (setq i (1+ i)))
      ;; AutoLISP LAST devuelve el punto completo, no una lista envolvente.
      (setq out (cons (last chain) out))
      (reverse out)))
)

;; Un anden se modula POR TRAMOS cuando es largo y gira: con un solo eje
;; las losetas del final quedan torcidas respecto al eje del anden
;; (medido en el master: 189,76 m que giran 23,3 grados).
(defun urb:anden-needs-segmented-p (chain / largo deriva longitud-girada)
  (if (null chain)
    nil
    (progn
      (setq largo (urb:chain-total-length chain)
            deriva (urb:chain-direction-drift chain)
            longitud-girada
              (urb:chain-off-axis-length chain (* pi (/ 2.0 180.0))))
      (and (> largo 0.40)
           (> deriva (* pi (/ 2.0 180.0)))
           ;; Debe existir al menos medio metro Y 1 % del recorrido fuera
           ;; del eje dominante. Un remate de 3-25 cm se recorta con el
           ;; patron recto; no merece una modulacion propia.
           (> longitud-girada (max 0.50 (* 0.01 largo)))))))

(defun urb:anden-use-segmented-p (chain forced-angle)
  (and (null forced-angle) (urb:anden-needs-segmented-p chain)))

(defun urb:anden-axis-from-user-points (p1 p2 auto-angle)
  (if (and p1 p2 (> (distance p1 p2) 1e-6))
    (angle p1 p2)
    (if auto-angle (+ auto-angle (* 0.5 pi)) nil)))

(defun urb:create-composite-loseta
  (ename format / obj copy base-region points fine-points parent-handle clusters
   split-data zones zone success angle-value pattern-mode reverse-pattern
    driving-chain forced-angle deriva tramos vb)
  (setq obj (vlax-ename->vla-object ename)
        parent-handle (vla-get-Handle obj)
        points (urb:lwpoly-points-with-arcs ename)
        fine-points (urb:lwpoly-points-with-arcs-fine ename)
        pattern-mode (urb:anden-pattern-mode ename)
        reverse-pattern (urb:anden-pattern-reversed-p pattern-mode)
        clusters (urb:dominant-anden-axis-clusters points)
         vb (urb:lwpoly-vertex-bulges ename)
         copy (urb:as-vla-object (urb:poly-chain-polyline
           (mapcar '(lambda (p b) (list (car p) (cadr p) b)) (car vb) (cadr vb)))))
  ;; REGION limpia sin XDATA ni plano interno heredado; conserva los arcos.
  (vla-put-Closed copy :vlax-true)
  (setq
         base-region (urb:anden-region-from-object copy))
  ;; Eje FORZADO de modulacion (URB_ANDEN_AXIS). Desde 5.7.18 los dos
  ;; puntos siguen el eje LONGITUDINAL y las bandas quedan perpendiculares.
  ;; Si no hay eje guardado pero el contorno tiene
  ;; arcos, se asume bandas paralelas al lado recto mas largo (la tapa
  ;; compartida con el modulo vecino): eje = ese lado + 90.
  (setq forced-angle
    (urb:parse-real
      (urb:safe-string
        (car (urb:get-xdata-strings ename "URB_ANDEN_AXIS")) "")))
  (if (and (null forced-angle) (urb:lwpoly-has-arcs-p ename))
    (progn
      (setq forced-angle (urb:anden-straight-edges-angle ename))
      (if forced-angle
        (setq forced-angle (+ forced-angle (* 0.5 pi))))))
  (urb:safe-delete copy)
  (if (not (vl-catch-all-error-p base-region))
    (setq base-region (urb:apply-anden-cutouts base-region)))
  (if (vl-catch-all-error-p base-region)
    nil
    (progn
      ;; IMPORTANTE (2026-08-09, decision del usuario con foto del plano):
      ;; el material NO se modula en abanico siguiendo la curva. Las
      ;; losetas/adoquines conservan la MISMA orientacion del tramo recto
      ;; ("como si el anden fuera recto") y el contorno curvo solo RECORTA
      ;; el patron; en un anden en L cada pierna lleva su propio eje y se
      ;; encuentran en la esquina (two-axis-split, el comportamiento
      ;; original). El modo segmentado por aristas
      ;; (urb:decorate-composite-region-segmented) queda solo como codigo
      ;; de respaldo, ya no se invoca para el material. La franja tactil
      ;; SI sigue el borde curvo (metodo offset), como en el plano.
      ;;
      ;; 2026-09-12 (reporte del usuario con el plano real: "comienza la
      ;; inclinacion bien pero al final se distorsiona y las losetas y
      ;; adoquines quedan torcidas con respecto al eje central del anden").
      ;; Medido en el anden AFA98 del master: 189,76 m de costado que
      ;; ARRANCA a 50,1 grados y TERMINA a 73,4 -- se desvia 23,3. Con UN
      ;; solo eje (el que el usuario marca con 2 puntos al crearlo, aqui
      ;; 50,1, o el automatico) las losetas del final quedan a 23 grados
      ;; del eje del anden, que es justo lo que se ve en el plano.
      ;; La decision de 2026-08-09 vale para un MODULO DE CURVA corto, que
      ;; es de lo que hablaba el U-201. En un corredor LARGO que gira hay
      ;; que modular POR TRAMOS: la cadena del costado se simplifica a unos
      ;; pocos tramos rectos (5 grados de tolerancia) y cada tramo lleva su
      ;; propia orientacion. Asi no es un abanico continuo -- cada tramo
      ;; sigue recto, como el plano -- pero tampoco se va de 23 grados.
      ;; Solo entra si el anden es largo (> 20 m) y gira (> 10 grados).
      (setq driving-chain
        (vl-catch-all-apply 'urb:anden-tactile-chain (list fine-points)))
      (if (vl-catch-all-error-p driving-chain) (setq driving-chain nil))
      (urb:bb-log (strcat "  material: eje longitudinal marcado="
        (if forced-angle (rtos forced-angle 2 8) "NO")))
      ;; El eje indicado por el usuario manda. Antes el modo segmentado se
      ;; evaluaba primero e ignoraba URB_ANDEN_AXIS, formando un abanico.
      (if (urb:anden-use-segmented-p driving-chain forced-angle)
        (progn
          (setq deriva (urb:chain-direction-drift driving-chain))
          (setq tramos
            (urb:chain-simplify-by-direction driving-chain (* pi (/ 2.0 180.0))))
          (prompt
            (strcat "\nANDEN: el costado gira "
              (rtos (/ (* deriva 180.0) pi) 2 1)
              " grados en " (rtos (urb:chain-total-length driving-chain) 2 1)
              " m; el material se modula en "
              (itoa (max 1 (1- (length tramos))))
              " tramos para que no quede torcido al final."))
          (urb:decorate-composite-region-segmented
            base-region tramos format parent-handle reverse-pattern))
      (progn
        (progn
          ;; 2026-08-12: la particion en dos ejes SOLO aplica a andenes en
          ;; L con esquinas rectas y sin eje forzado. Con eje forzado o
          ;; arcos, UN solo eje y la curva solo recorta.
          (if (and (null forced-angle)
                   (> (length clusters) 1)
                   (not (urb:lwpoly-has-arcs-p ename))
                   ;; Un entrante junto a un contenedor es un vacio, no
                   ;; una esquina en L que deba cambiar el eje del patron.
                   (not (and (urb:polygon-concave-p points)
                             (urb:anden-near-root-container-p ename))))
            (setq split-data
              (urb:two-axis-split-data
                points (car clusters) (cadr clusters))))
          (if split-data
            (progn
              (setq zones
                (urb:create-two-axis-regions base-region split-data))
              (if zones
                (progn
                  (urb:safe-delete base-region)
                  (setq success T)
                  (foreach zone zones
                    (if (not
                          (urb:decorate-composite-region
                            (car zone)
                            (urb:anden-pattern-angle
                              (cadr zone) pattern-mode)
                            format parent-handle
                            reverse-pattern 0.0 nil))
                      (setq success nil)))
                  success)
                (progn
                  ;; Si la particion geometrica falla, se conserva un resultado
                  ;; util usando el eje principal en lugar de dejar el anden vacio.
                  (setq angle-value
                    (cond
                      (forced-angle forced-angle)
                      (clusters (car (car clusters)))
                      (T (urb:anden-axis-angle points))))
                  (setq angle-value
                    (urb:anden-pattern-angle
                      angle-value pattern-mode))
                  (urb:decorate-composite-region
                    base-region angle-value format parent-handle
                    reverse-pattern 0.0 fine-points))))
            (progn
              (setq angle-value
                (cond
                  (forced-angle forced-angle)
                  (clusters (car (car clusters)))
                  (T (urb:anden-axis-angle points))))
              (setq angle-value
                (urb:anden-pattern-angle
                  angle-value pattern-mode))
              (urb:decorate-composite-region
                base-region angle-value format parent-handle
                reverse-pattern 0.0 fine-points))))))))
)

(defun urb:generated-xdata-fragment (parent-handle role)
  ;; Mismo formato que produce urb:set-xdata-strings (app URB_ANDEN_GEN,
  ;; valores string en grupo 1000) pero como fragmento DXF listo para
  ;; incrustar directo en un entmake -- evita el ciclo entget+entmod+entupd
  ;; de urb:tag-generated-role/urb:set-xdata-strings, que a escala de
  ;; miles de simbolos tactiles (decenas de miles en una franja larga
  ;; real) resulto ser un cuello de botella severo (minutos extra de
  ;; proceso). El caller debe asegurar que el APPID ya este registrado
  ;; (regapp) antes de usar esto -- entmake no registra el APPID solo.
  (list -3
    (list "URB_ANDEN_GEN"
          (cons 1000 (urb:safe-string parent-handle ""))
          (cons 1000 (urb:safe-string role ""))))
)

;;; 2026-09-08 (reporte del usuario, tercera vez: "lo del toperol sigue sin
;;; aparecer"). La franja SI se generaba -- medido en Civil real sobre un
;;; anden recto rotado: 3.840 domos, todos dentro del contorno y dentro del
;;; bloque. Lo que fallaba era que NO SE VE:
;;;   1) la franja tactil se pintaba con la MISMA alternancia gris/blanca
;;;      del anden ("la franja queda integrada al patron y se distingue
;;;      solo por la textura"), asi que a escala de plano es identica al
;;;      resto del anden;
;;;   2) la textura que debia distinguirla eran domos de radio 0,008 m
;;;      (16 mm de diametro): a la escala a la que el usuario mira el
;;;      plano no llegan ni a un pixel.
;;; La GUIA conserva el tono por banda (asi se aprobo, y su barra de 15 cm
;;; si se lee).
;;;
;;; 2026-09-10 (correccion del usuario sobre v4.83: "ya aparece la franja de
;;; toperol, pero quedo una franja gris; lo que queria era que quedaran los
;;; punticos"). El relleno gris uniforme se comia la textura: a escala de
;;; plano la franja se leia como una mancha lisa. Ahora la franja va en
;;; tono CLARO y los domos en OSCURO, que es como se lee una loseta tactil
;;; en un plano -- el punteado es la textura, no el fondo. El domo conserva
;;; su tamano real (25 mm de diametro).
(setq *urb-toperol-radio* 0.0125)

(defun urb:tactile-fill-color (feature gray)
  (if (= feature "TOPEROL") 7 (if gray 8 7)))

(defun urb:tactile-symbol-color (feature gray)
  (if (= feature "TOPEROL") 8 (if gray 7 8)))

;;; 2026-09-10. Segundo problema del mismo reporte: "los andenes no estan
;;; quedando en bloque, quedan todos los elementos por aparte". Medido en
;;; Civil real, un anden de 24 m con guia y toperol genera 3.840 CIRCLE --
;;; uno por domo -- y urb:package-anden tarda 15,2 s en empacarlo. En un
;;; anden real de cientos de metros eso son minutos, y el bloque solo se
;;; arma si el usuario aguanta la espera (si interrumpe, el material queda
;;; suelto: es el modo de fallo que ya estaba documentado en
;;; urb:package-anden). El punteado del toperol pasa a resolverse con el
;;; patron URB_TOPEROL.pat -- que este mismo motor ya escribia y nunca
;;; usaba --: UN hatch por banda en vez de un circulo por domo. Ademas de
;;; ser ~70 veces menos entidades, un punto de patron se dibuja siempre
;;; visible a cualquier zoom, que es justo lo que el usuario pide.
;;; Si el patron no se puede usar en este dibujo se vuelve solo al metodo
;;; de circulos, sin perder el toperol.
(setq *urb-toperol-pattern-state* nil)
;; piezas en las que el patron fallo aunque SI estaba disponible (contornos
;; de curva); se reporta al terminar para que se vea, en vez de degradar en
;; silencio todo el anden a circulos.
(setq *urb-toperol-fallos-pieza* 0)

;; Decide que hacer cuando el patron de toperol falla en una pieza.
(defun urb:toperol-degradar-si-primero ()
  (if (null *urb-toperol-pattern-state*)
    ;; primer intento del dibujo: el patron no esta disponible
    (setq *urb-toperol-pattern-state* "NO")
    ;; ya habia funcionado: el fallo es de ESTA pieza y no del dibujo
    (setq *urb-toperol-fallos-pieza* (1+ *urb-toperol-fallos-pieza*)))
  *urb-toperol-pattern-state*
)

(defun urb:add-toperol-hatch (boundary layer angle-value color / hatch res)
  (setq res
    (vl-catch-all-apply
      '(lambda ()
        (setq hatch (vla-AddHatch (urb:space) 2 "URB_TOPEROL" :vlax-true))
        (vla-AppendOuterLoop hatch (urb:make-loop-array boundary))
        (vla-put-Layer hatch (urb:safe-string layer "0"))
        (vla-put-Color hatch color)
        (vla-put-PatternScale hatch 1.0)
        (vla-put-PatternAngle hatch
          (urb:wcs-angle-to-current-ucs (if angle-value angle-value 0.0)))
        (urb:evaluate-render-hatch hatch)
        hatch)))
  (if (or (vl-catch-all-error-p res) (null res))
    (progn
      (if (and hatch (= (type hatch) 'VLA-OBJECT)) (urb:safe-delete hatch))
      ;; 2026-09-12 (reporte del usuario: "un anden de 188 ml se demora
      ;; muchisimo y no queda en bloque"). El estado se quedaba en "NO"
      ;; con que UNA pieza fallara -- tipicamente un contorno de curva --
      ;; y desde ahi TODO el resto del anden sembraba un circulo por domo:
      ;; decenas de miles de entidades y el empaque en bloque no alcanzaba.
      ;; Ahora "NO" solo se fija si el patron fallo en el PRIMER intento
      ;; del dibujo (o sea, el patron no esta disponible). Si ya habia
      ;; funcionado antes, el fallo es de esa pieza y no contamina el resto.
      (urb:toperol-degradar-si-primero)
      nil)
    (progn (setq *urb-toperol-pattern-state* "SI") res))
)

;; Punteado sobre una banda ya creada. Solo aplica al toperol; la guia
;; conserva sus barras, que a 15 cm si se leen.
(defun urb:toperol-texture (piece feature layer angle-value parent-handle / h)
  (if (and (= feature "TOPEROL") (/= *urb-toperol-pattern-state* "NO"))
    (progn
      (setq h (urb:add-toperol-hatch piece layer angle-value
                (urb:tactile-symbol-color feature T)))
      (if h (urb:tag-generated-role h parent-handle "FEATURE_SYMBOL"))
      h))
)

;; T cuando el punteado ya quedo resuelto por patron y no hay que sembrar
;; un circulo por domo.
(defun urb:toperol-by-pattern-p (feature)
  (and (= feature "TOPEROL") (= *urb-toperol-pattern-state* "SI")))

(defun urb:add-circle-symbol (u v radius angle-value layer parent-handle color / world-pt)
  ;; Punto tactil real (toperol): un circulo dibujado, no una marca de hatch
  ;; de longitud cero. Coincide visualmente con la loseta toperol real
  ;; (domos truncados dibujados como aros), no con un simple punteado.
  ;; El xdata URB_ANDEN_GEN va incrustado aqui mismo (ver
  ;; urb:generated-xdata-fragment) para que urb:package-anden encuentre y
  ;; empaquete el simbolo sin una llamada extra de tag por objeto.
  (setq world-pt (urb:local-to-world u v angle-value))
  (entmake
    (list
      (cons 0 "CIRCLE")
      (cons 100 "AcDbEntity")
      (cons 8 layer)
      ;; tono OPUESTO a la banda (blanco sobre gris, gris sobre blanco):
      ;; con el mismo tono de la tableta el simbolo no se veia
      (cons 62 color)
      (cons 100 "AcDbCircle")
      (cons 10 (list (car world-pt) (cadr world-pt) 0.0))
      (cons 40 radius)
      (urb:generated-xdata-fragment parent-handle "FEATURE_SYMBOL")))
  (entlast)
)

(defun urb:emit-tactile-entity (data)
  ;; Una franja de GUIA se construye directamente dentro de una definicion,
  ;; sin miles de objetos temporales en ModelSpace ni copias COM al empaquetar.
  ;; Los mismos DXF, capas, colores, bulges y recortes; no es un hatch aproximado.
  (if (and (boundp '*urb-tactile-batch*) *urb-tactile-batch*)
    (progn (setq *urb-tactile-entities* (cons data *urb-tactile-entities*)) T)
    (entmake data)))

(defun urb:flush-tactile-batch (layer parent-handle / name i ok data result caught)
  (if *urb-tactile-entities*
    (progn
      (setq i 0 name (strcat "URB_GUIA_" parent-handle "_" (itoa (getvar "MILLISECS"))))
      (while (tblsearch "BLOCK" name)
        (setq i (1+ i) name (strcat name "_" (itoa i))))
      (setq ok (entmake (list '(0 . "BLOCK") '(8 . "0") (cons 2 name)
                    '(70 . 0) '(10 0.0 0.0 0.0))))
      (if ok
        (progn
          ;; Cerrar ENDBLK incluso ante error/cancelacion: nunca dejar el
          ;; destino de entmake apuntando a una definicion incompleta.
          (setq caught (vl-catch-all-apply
            '(lambda ()
              (foreach data (reverse *urb-tactile-entities*)
                (if (not (entmake data)) (setq ok nil)))) nil))
          (if (vl-catch-all-error-p caught) (setq ok nil))
          (if (not (entmake '((0 . "ENDBLK") (8 . "0")))) (setq ok nil))))
      (if ok
        (setq result (entmake
          (list '(0 . "INSERT") (cons 2 name) (cons 8 layer)
                '(10 0.0 0.0 0.0) '(41 . 1.0) '(42 . 1.0) '(43 . 1.0)
                (urb:generated-xdata-fragment parent-handle "FEATURE_SYMBOL")))))
      (setq *urb-tactile-entities* nil)
      (if (not result)
        (progn
          (vl-catch-all-apply
            '(lambda () (vla-Delete (vla-Item (vla-get-Blocks (urb:doc)) name))) nil)
          (vl-exit-with-error "ANDEN: no se pudo completar el bloque interno de guia.")))
      (entlast))))

(defun urb:add-capsule-symbol
  (u v half-length half-width angle-value layer parent-handle color
   / p1 p2 p3 p4)
  ;; Barra tactil real (guia): una capsula (rectangulo con extremos
  ;; semicirculares, via bulge=1 en 2 de los 4 vertices) con el eje largo
  ;; a lo largo de U (direccion de avance) -antes era un simple guion recto,
  ;; sin extremos redondeados, que no se parecia a la loseta guia real.
  (setq p1 (urb:local-to-world (- u half-length) (+ v half-width) angle-value)
        p2 (urb:local-to-world (+ u half-length) (+ v half-width) angle-value)
        p3 (urb:local-to-world (+ u half-length) (- v half-width) angle-value)
        p4 (urb:local-to-world (- u half-length) (- v half-width) angle-value))
  (urb:emit-tactile-entity
    (list
      (cons 0 "LWPOLYLINE")
      (cons 100 "AcDbEntity")
      (cons 8 layer)
      ;; mismo criterio que el circulo: tono opuesto a la banda
      (cons 62 color)
      (cons 100 "AcDbPolyline")
      (cons 90 4)
      (cons 70 1)
      (cons 10 p1) (cons 42 0.0)
      (cons 10 p2) (cons 42 1.0)
      (cons 10 p3) (cons 42 0.0)
      (cons 10 p4) (cons 42 1.0)
      (urb:generated-xdata-fragment parent-handle "FEATURE_SYMBOL")))
  (entlast)
)

(defun urb:fill-tactile-symbols
  (region feature angle-value layer phase-offset parent-handle module
   / points bounds umin umax vmin vmax spacing margin v count
   radius half-length half-width global-u local-u seg-len sym-ename
   tile-k tile-g su su-step sym-color wc w1 w2 ok loops
   *urb-pip-index-enabled* *urb-pip-source* *urb-pip-index*
   *urb-tactile-batch* *urb-tactile-entities*)
  (setq *urb-pip-index-enabled* T *urb-tactile-batch* (= feature "GUIA"))
  ;; Reparte simbolos tactiles reales (circulos o capsulas) en una reticula
  ;; de 5 cm sobre el area ya recortada de la franja, en vez de depender de
  ;; un patron .pat (que solo puede construirse con familias de lineas
  ;; rectas y nunca se va a parecer a un domo truncado circular u ovalado).
  ;; phase-offset es la distancia acumulada desde el INICIO de toda la
  ;; cadena guia hasta el arranque de este segmento: sin esto, cada
  ;; segmento reinicia su propia reticula en 0 y la costura entre
  ;; segmentos vecinos queda desalineada (el patron "salta" en cada union
  ;; en vez de continuar parejo a lo largo de toda la franja).
  ;; Cada simbolo lleva su xdata URB_ANDEN_GEN incrustado directo en el
  ;; entmake (urb:generated-xdata-fragment, dentro de
  ;; urb:add-capsule-symbol/urb:add-circle-symbol): sin esto,
  ;; urb:package-anden (que arma el bloque final via urb:generated-objects)
  ;; nunca los encuentra y quedan sueltos en el dibujo, fuera del bloque.
  ;; No se usa urb:tag-generated-role aqui (entget+entmod+entupd por
  ;; objeto) porque a escala de miles/decenas de miles de simbolos por
  ;; franja resulto demasiado lento (minutos extra).
  (if (not (tblsearch "APPID" "URB_ANDEN_GEN")) (regapp "URB_ANDEN_GEN"))
  (setq loops (urb:region-polygons region)
        points (apply 'append loops))
  (if points
    (progn
      (setq bounds (urb:project-bounds points angle-value)
            umin (nth 0 bounds) umax (nth 1 bounds)
            vmin (nth 2 bounds) vmax (nth 3 bounds))
      (setq spacing 0.05 margin 0.025 count 0 sym-color 8)
      (setq seg-len (- umax umin))
      ;; Colocacion POR TABLETA sobre la reticula global de la cadena
      ;; (tabletas de "module" de largo, juntas alineadas con el material):
      ;; cada tableta lleva sus propios simbolos con margen a cada lado
  ;; (4 columnas en la de 20cm, 8 en la de 40cm), en vez de una sola
      ;; secuencia corrida de 5cm que ignoraba donde caen las juntas --
      ;; asi el simbolo nunca queda montado sobre una junta y la franja se
      ;; ve como tabletas individuales, igual que en el plano de
      ;; referencia U-201.
      (if (or (null module) (< module 0.05)) (setq module 0.20))
      ;; 2026-08-26 (reporte del usuario, "la guia esta quedando fea"):
      ;; la guia sembraba 4+ columnas de capsulas de 15cm por tableta
      ;; (paso su de 5cm con capsulas mas largas que el paso) -- quedaban
      ;; SOLAPADAS como eslabones. Ahora la guia pone UNA barra
      ;; longitudinal por tableta (centro su = module/2, largo = module
      ;; menos margen a cada lado), como la loseta guia real. El toperol
      ;; conserva su reticula de domos cada 5cm.
      (if (= feature "GUIA")
        (setq half-length (/ (- module (* 2.0 margin)) 2.0)
              half-width 0.012)
        (setq radius *urb-toperol-radio*))
      (setq tile-k (fix (/ (+ phase-offset 1e-9) module)))
      (setq tile-g (* tile-k module))
      ;; v4.86: si el punteado ya lo puso el patron URB_TOPEROL, no se
      ;; siembra un circulo por domo (miles de entidades por anden)
      (while (and (not (urb:toperol-by-pattern-p feature))
                  (< tile-g (+ phase-offset seg-len (- 1e-6))))
        ;; tono OPUESTO a la banda donde cae la tableta (blanco sobre
        ;; banda gris, gris sobre banda blanca) -- misma fase global que
        ;; el relleno por bandas de la franja
        (setq sym-color
          (urb:tactile-symbol-color feature
            (car (urb:composite-phase-state (+ tile-g (* 0.5 module))))))
        (if (= feature "GUIA") (setq sym-color 7))
        (setq su (if (= feature "GUIA") (/ module 2.0) margin))
        (setq su-step (if (= feature "GUIA") module spacing))
        (while (<= su (+ (- module margin) 1e-6))
          (setq global-u (+ tile-g su))
          ;; solo las columnas que caen dentro de ESTE segmento
          (if (and (>= (- global-u phase-offset) -1e-6)
                   (<= (- global-u phase-offset) (+ seg-len 1e-6)))
            (progn
              (setq local-u (+ umin (- global-u phase-offset)))
              (setq v (+ vmin margin))
              (while (<= v (+ (- vmax margin) 1e-6))
                ;; 2026-08-26 (reporte del usuario: toperol POR FUERA del
                ;; bloque): los bounds u/v son un rectangulo; en recortes
                ;; con cunas a inglete o curvos, parte de ese rectangulo
                ;; queda FUERA de la franja real. Cada simbolo se valida
                ;; contra el contorno de la region antes de dibujarse (la
                ;; guia ademas con sus dos extremos, para no dejar barras
                ;; colgando del borde).
                (setq wc (urb:local-to-world local-u v angle-value))
                (setq ok (urb:point-in-region-polygons-p wc loops))
                (if (and ok (= feature "GUIA"))
                  (progn
                    (setq w1 (urb:local-to-world
                               (- local-u half-length) v angle-value))
                    (setq w2 (urb:local-to-world
                               (+ local-u half-length) v angle-value))
                    (setq ok (and (urb:point-in-region-polygons-p w1 loops)
                                  (urb:point-in-region-polygons-p w2 loops)))))
                (if ok
                  (progn
                    (setq sym-ename
                      (if (= feature "GUIA")
                        (urb:add-capsule-symbol local-u v half-length half-width angle-value layer parent-handle sym-color)
                        (urb:add-circle-symbol local-u v radius angle-value layer parent-handle sym-color)))
                    (setq count (1+ count))))
                (setq v (+ v spacing)))))
          (setq su (+ su su-step)))
        (setq tile-k (1+ tile-k))
        (setq tile-g (* tile-k module)))
      (if *urb-tactile-batch* (urb:flush-tactile-batch layer parent-handle))
      (or (urb:toperol-by-pattern-p feature) (> count 0)))
    nil)
)

(defun urb:strip-phase-offset (region axis start-u / pts)
  (setq pts (urb:region-outline-points region))
  (if pts (- (car (urb:project-bounds pts axis)) start-u) 0.0))

(defun urb:decorate-accessibility-strip
  (region layer feature module angle-value origin parent-handle phase-offset
   / fill grid symbols-ok points bounds umin umax vmin vmax phase-state
   gray first-band cursor nxt bw band iter band-ok)
  ;; layer ya es la capa de guia/toperol real (antes esta pieza base vivia
  ;; aparte en URB-ANDEN-AUX); el rol FILL mantiene el orden de dibujo.
  (vla-put-Layer region layer)
  (vla-put-Color region (urb:tactile-fill-color feature T))
  (urb:tag-generated-role region parent-handle "FILL")
  ;; La franja es una sola region continua. Partirla en bandas de 0.80/1.00 m
  ;; creaba cientos de booleans y hatches por cada anden largo; la reticula
  ;; USER y la textura tactil se aplican una vez sobre el contorno completo.
  (vla-put-Layer region layer)
  (vla-put-Color region (urb:tactile-fill-color feature T))
  (urb:tag-generated-role region parent-handle "FILL")
  (setq fill
    (vl-catch-all-apply
      'urb:add-solid-hatch
      (list region layer (urb:tactile-fill-color feature T))))
  (if (not (vl-catch-all-error-p fill))
    (urb:tag-generated-role fill parent-handle "FEATURE_FILL"))
  (if (= feature "TOPEROL")
    (urb:toperol-texture region feature layer angle-value parent-handle))
  (setq grid
    (urb:add-user-hatch
      region layer module angle-value T 9 origin))
  (urb:tag-generated-role grid parent-handle "FEATURE")
  (setq symbols-ok
    (vl-catch-all-apply
      'urb:fill-tactile-symbols
      (list region feature angle-value layer (if phase-offset phase-offset 0.0) parent-handle module)))
  (if (or (vl-catch-all-error-p symbols-ok) (null symbols-ok))
    (progn
      (prompt (strcat "\nAVISO: no se generaron simbolos " feature
        (if (vl-catch-all-error-p symbols-ok)
          (strcat ": " (vl-catch-all-error-message symbols-ok))
          "; revisar ancho/contorno de la franja.")))
      nil)
    T)
)

(defun urb:point-v-coordinate (point angle-value)
  (+
    (* (- (car point)) (sin angle-value))
    (* (cadr point) (cos angle-value)))
)

(defun urb:reference-v-edge
  (points angle-value vmin vmax / reference-v reference-point)
  ;; OJO: en AutoLISP (and ...) devuelve T/nil, NO el ultimo valor como en
  ;; otros Lisp -- por eso el punto del choice se calcula en un setq
  ;; separado y no dentro de la condicion.
  (setq reference-point
    (if *urb-current-tactile-side-choice*
      (urb:tactile-side-point-from-choice
        *urb-current-tactile-side-choice* points)
      nil))
  (if (null reference-point)
    (setq reference-point
      (cond
        (*urb-current-tactile-side-anchor* *urb-current-tactile-side-anchor*)
        (*urb-current-tactile-side-point*
          (setq reference-point
            (urb:tactile-side-anchor points *urb-current-tactile-side-point*))
          (if (null reference-point)
            (setq reference-point *urb-current-tactile-side-point*))
          reference-point)
        (T (car points)))))
  (setq reference-v
    (urb:point-v-coordinate reference-point angle-value))
  (if (<= (abs (- reference-v vmin))
          (abs (- reference-v vmax)))
    vmin
    vmax)
)

;; ============================================================
;; FRANJA TACTIL POR OFFSET DE LA CURVA REAL (rediseno 2026-08-09)
;; La franja se construye como la region entre dos curvas paralelas
;; (vla-Offset) del borde de la via, en vez de rectangulos por arista:
;; con radios pequenos los rectangulos salian quebrados/doblados sin
;; remedio (verificado visualmente por PDF). Los simbolos y juntas
;; caminan la curva real con vlax-curve (posicion y tangente exactas).
;; ============================================================

(defun urb:point-in-poly-p (pt pts / prev p inside xi yi xj yj x y)
  ;; Mismo ray casting y tratamiento del borde, recorrido lineal (sin nth).
  (setq x (car pt) y (cadr pt) inside nil prev (last pts))
  (foreach p pts
    (setq xi (car p) yi (cadr p) xj (car prev) yj (cadr prev))
    (if (and (not (eq (> yi y) (> yj y)))
             (< x (+ xj (/ (* (- xi xj) (- y yj)) (- yi yj)))))
      (setq inside (not inside)))
    (setq prev p))
  inside
)

(defun urb:open-poly-from-points (pts elevation / coords poly)
  (setq coords
    (apply 'append
      (mapcar '(lambda (p) (list (car p) (cadr p))) pts)))
  (setq poly
    (vla-AddLightWeightPolyline
      (urb:space)
      (urb:double-array-variant coords)))
  (if (and (numberp elevation)
           (vlax-property-available-p poly 'Elevation T))
    (vla-put-Elevation poly elevation))
  (vlax-vla-object->ename poly)
)

(defun urb:offset-poly (ename dist / obj res lst keep)
  ;; offset de una polilinea; devuelve el ENAME del resultado o nil.
  ;; Si el offset se parte en varias piezas se descartan todas (el caller
  ;; cae al metodo por segmentos).
  (setq obj (vlax-ename->vla-object ename))
  (setq res (vl-catch-all-apply 'vla-Offset (list obj dist)))
  (if (vl-catch-all-error-p res)
    nil
    (progn
      (setq lst
        (vl-catch-all-apply
          '(lambda () (vlax-safearray->list (vlax-variant-value res)))))
      (if (vl-catch-all-error-p lst) (setq lst nil))
      (cond
        ((null lst) nil)
        ((= (length lst) 1)
          (vlax-vla-object->ename (car lst)))
        (T
          (foreach keep lst (urb:safe-delete keep))
          nil))))
)

(defun urb:curve-length (ename / r)
  (setq r
    (vl-catch-all-apply
      '(lambda ()
         (vlax-curve-getDistAtParam ename (vlax-curve-getEndParam ename)))))
  (if (vl-catch-all-error-p r) 0.0 r)
)

(defun urb:curve-pt (ename dist / r)
  (setq r (vl-catch-all-apply 'vlax-curve-getPointAtDist (list ename dist)))
  (if (or (vl-catch-all-error-p r) (null r)) nil (list (car r) (cadr r)))
)

(defun urb:curve-tangent (ename dist / p r)
  ;; angulo de la tangente en la distancia dada (0 si falla)
  (setq p (vl-catch-all-apply 'vlax-curve-getParamAtDist (list ename dist)))
  (if (vl-catch-all-error-p p)
    0.0
    (progn
      (setq r (vl-catch-all-apply 'vlax-curve-getFirstDeriv (list ename p)))
      (if (or (vl-catch-all-error-p r) (null r))
        0.0
        (atan (cadr r) (car r)))))
)

(defun urb:strip-band-region (c1 c2 elevation / pts poly region)
  ;; region cerrada entre dos curvas offset abiertas (misma direccion)
  (setq pts
    (append (urb:lwpoly-points c1) (reverse (urb:lwpoly-points c2))))
  (if (< (length pts) 3)
    nil
    (progn
      (setq poly
        (vl-catch-all-apply
          '(lambda ()
             (vla-put-Closed
               (vlax-ename->vla-object
                 (urb:open-poly-from-points pts elevation))
               :vlax-true)
             (entlast))))
      (if (vl-catch-all-error-p poly)
        nil
        (progn
          (setq region (urb:add-region-from-object (vlax-ename->vla-object poly)))
          (entdel poly)
          (if (vl-catch-all-error-p region) nil region)))))
)

(defun urb:offset-strip-tones
  (strip chain-poly len layer parent-handle elevation span feature
   / color hatch)
  ;; Una franja accesible es una sola region continua. La version anterior
  ;; la partia en bandas de 0.80/1.00 m y creaba dos HATCH por banda; en un
  ;; anden de 188 m eso eran cientos de booleans/hatches y el bloque quedaba
  ;; a medio empaquetar. La reticula de loseta ya se dibuja en un unico USER
  ;; hatch y el toperol en un unico hatch de textura; las juntas/simbolos se
  ;; generan aparte, asi que no se pierde la lectura del acabado.
  (setq color (urb:tactile-fill-color feature T))
  (vla-put-Layer strip layer)
  (vla-put-Color strip color)
  (urb:tag-generated-role strip parent-handle "FILL")
  (setq hatch
    (vl-catch-all-apply 'urb:add-solid-hatch (list strip layer color)))
  (if (not (vl-catch-all-error-p hatch))
    (progn
      (urb:tag-generated-role hatch parent-handle "FEATURE_FILL")
      (if (= feature "TOPEROL")
        (urb:toperol-texture strip feature layer
          (urb:curve-tangent chain-poly (* 0.5 len)) parent-handle))
      1)
    0)
)

(defun urb:offset-strip-symbols
  (chain-poly len d1 d2 perp-sign feature module layer parent-handle loops
   / spacing margin half-length half-width radius tile-k tile-g sym-color
     su dist pt ang normal ro wpt u v cs sn joint-p1 joint-p2
     symbol-result created e1 e2
     *urb-pip-index-enabled* *urb-pip-source* *urb-pip-index*
     *urb-tactile-batch* *urb-tactile-entities*)
  (setq *urb-pip-index-enabled* T *urb-tactile-batch* (= feature "GUIA"))
  ;; simbolos y juntas por tableta caminando la curva real
  ;; 2026-09-12 (reporte del usuario: "me salio un circulo, eso pasa es en
  ;; las curvas"). Los simbolos se colocan a una distancia PERPENDICULAR
  ;; fija del borde; en un arco cuyo radio es menor que esa distancia el
  ;; punto se pasa del CENTRO del arco y todos los simbolos del tramo se
  ;; apilan ahi en abanico -- con domos cada 5 cm, un disco. Medido en un
  ;; anden de 1,50 m por dentro de una curva de radio 1,00.
  ;; La ruta por segmentos ya validaba cada simbolo contra el contorno
  ;; desde 2026-08-26 ("toperol POR FUERA del bloque"); esta no. Ahora
  ;; tambien: todo simbolo (y la junta radial de cada tableta) tiene que
  ;; caer DENTRO de la region del anden.
  (setq spacing 0.05 margin 0.025)
  (if (= feature "GUIA")
    (setq half-length 0.075 half-width 0.012)
    (setq radius *urb-toperol-radio*))
  (if (not (tblsearch "APPID" "URB_ANDEN_GEN")) (regapp "URB_ANDEN_GEN"))
  (setq tile-k 0 created 0)
  (while (< (setq tile-g (* tile-k module)) (- len 1e-6))
    ;; junta radial en el arranque de cada tableta (excepto la primera)
    (if (> tile-k 0)
      (progn
        (setq pt (urb:curve-pt chain-poly tile-g)
              ang (urb:curve-tangent chain-poly tile-g))
        (if pt
          (progn
            (setq normal (+ ang (* 0.5 pi)))
            (setq joint-p1
              (list (+ (car pt) (* perp-sign d1 (cos normal)))
                    (+ (cadr pt) (* perp-sign d1 (sin normal))))
                  joint-p2
              (list (+ (car pt) (* perp-sign d2 (cos normal)))
                    (+ (cadr pt) (* perp-sign d2 (sin normal)))))
            (if (or (null loops)
                    (and (urb:point-in-region-polygons-p joint-p1 loops)
                         (urb:point-in-region-polygons-p joint-p2 loops)))
              (urb:emit-tactile-entity
                (list (cons 0 "LINE") (cons 8 layer) (cons 62 8)
                      (cons 10 (list (car joint-p1) (cadr joint-p1) 0.0))
                      (cons 11 (list (car joint-p2) (cadr joint-p2) 0.0))
                      (urb:generated-xdata-fragment parent-handle "FEATURE"))))))))
    ;; tono opuesto a la banda de esta tableta
    (setq sym-color
      (urb:tactile-symbol-color feature
        (car (urb:composite-phase-state
               (min (- len 1e-6) (+ tile-g (* 0.5 module)))))))
    (if (= feature "GUIA") (setq sym-color 7))
    ;; Una barra longitudinal por tableta, no cuatro capsulas solapadas.
    (setq su (if (= feature "GUIA") (/ module 2.0) margin))
    ;; con el punteado ya resuelto por patron no se siembra un circulo por
    ;; domo: solo quedan las juntas de tableta (v4.86)
    (while (and (not (urb:toperol-by-pattern-p feature))
                (<= su (+ (- module margin) 1e-6)))
      (setq dist (+ tile-g su))
      (if (<= dist len)
        (progn
          (setq pt (urb:curve-pt chain-poly dist)
                ang (urb:curve-tangent chain-poly dist))
          (if pt
            (progn
              (setq normal (+ ang (* 0.5 pi)))
              (setq cs (cos ang) sn (sin ang))
              (setq ro (+ d1 margin))
              (while (<= ro (+ (- d2 margin) 1e-6))
                (setq wpt
                  (list (+ (car pt) (* perp-sign ro (cos normal)))
                        (+ (cadr pt) (* perp-sign ro (sin normal)))))
                ;; a coordenadas locales del marco (ang) que esperan los
                ;; helpers de simbolo
                (setq u (+ (* (car wpt) cs) (* (cadr wpt) sn))
                      v (+ (* (- (car wpt)) sn) (* (cadr wpt) cs)))
                ;; fuera de la region no se dibuja (ver la nota de arriba):
                ;; la guia, ademas, con sus dos extremos, para no dejar
                ;; barras colgando del borde
                (setq symbol-result nil)
                (if (or (null loops)
                        (and (urb:point-in-region-polygons-p wpt loops)
                             (or (/= feature "GUIA")
                                 (progn
                                   (setq e1 (list (- (car wpt) (* half-length cs))
                                                  (- (cadr wpt) (* half-length sn)))
                                         e2 (list (+ (car wpt) (* half-length cs))
                                                  (+ (cadr wpt) (* half-length sn))))
                                   (and (urb:point-in-region-polygons-p e1 loops)
                                        (urb:point-in-region-polygons-p e2 loops))))))
                  (setq symbol-result
                    (if (= feature "GUIA")
                      (urb:add-capsule-symbol
                        u v half-length half-width ang layer parent-handle sym-color)
                      (urb:add-circle-symbol
                        u v radius ang layer parent-handle sym-color))))
                (if symbol-result (setq created (1+ created)))
                (setq ro (+ ro spacing)))))))
      (setq su (+ su (if (= feature "GUIA") module spacing))))
    (setq tile-k (1+ tile-k)))
  (if *urb-tactile-batch* (urb:flush-tactile-batch layer parent-handle))
  (or (urb:toperol-by-pattern-p feature) (> created 0))
)

;; 2026-09-12 (reporte del usuario: "ya despues que lo creo me salio un
;; circulo, eso pasa es en las curvas"). vla-Offset de una cadena que trae
;; un arco devuelve, cuando la distancia se acerca o pasa del radio del
;; arco, una curva que se voltea sobre el centro del arco y se vuelve un
;; LAZO GIGANTE. Ese lazo se quedaba DIBUJADO, porque las dos curvas
;; desplazadas se conservan a proposito como lineas de junta de la franja
;; (ver el foreach de c1/c2 mas abajo) -- ese es el "circulo" del reporte.
;; Aqui se exige que la curva desplazada siga pareciendose a la cadena:
;; largo del mismo orden de magnitud y sin salirse de la caja del anden.
;; Si no, la franja se declara fallida y el llamador la rehace por
;; segmentos, que con radios pequenos es el metodo que sirve.
(defun urb:offset-curve-sane-p (c base-region len / lc bc bb tol)
  (setq lc (urb:curve-length c))
  (setq tol 1.0)
  (cond
    ((<= lc 1e-6) nil)
    ((and (> len 1e-6) (> lc (* 3.0 len))) nil)
    ((and (> len 1e-6) (< lc (* 0.3 len))) nil)
    (T
      (setq bc (urb:object-box-points (vlax-ename->vla-object c)))
      (setq bb (urb:object-box-points base-region))
      (if (and bc bb)
        (and (>= (car  (nth 0 bc)) (- (car  (nth 0 bb)) tol))
             (>= (cadr (nth 0 bc)) (- (cadr (nth 0 bb)) tol))
             (<= (car  (nth 2 bc)) (+ (car  (nth 2 bb)) tol))
             (<= (cadr (nth 2 bc)) (+ (cadr (nth 2 bb)) tol)))
        T)))
)

(defun urb:build-offset-strip
  (base-region chain-poly d1 d2 off-sign perp-sign layer feature module
   parent-handle elevation span
   / c1 c2 band strip len booleaned tone-count symbols-ok area-real area-esp
     loops)
  (setq len (urb:curve-length chain-poly))
  (setq c1
    (if (< (abs d1) 1e-9)
      (urb:as-ename (vla-Copy (vlax-ename->vla-object chain-poly)))
      (urb:offset-poly chain-poly (* off-sign d1))))
  (setq c2 (urb:offset-poly chain-poly (* off-sign d2)))
  ;; offset degenerado (el lazo gigante de las curvas cerradas): se
  ;; descarta antes de que quede dibujado
  (foreach c (list c1 c2)
    (if (and c (not (urb:offset-curve-sane-p c base-region len)))
      (progn
        (prompt
          (strcat "\nANDEN: el desplazamiento de "
            (rtos (if (equal c c1) d1 d2) 2 2)
            " m se voltea en una curva de este contorno; esa franja se"
            " rehace por segmentos."))
        (entdel c)
        (if (equal c c1) (setq c1 nil) (setq c2 nil)))))
  (if (or (null c1) (null c2))
    (progn
      (urb:bb-log (strcat "  tactil " feature ": offset invalido c1="
        (vl-princ-to-string c1) " c2=" (vl-princ-to-string c2)))
      (if c1 (entdel c1))
      (if c2 (entdel c2))
      nil)
    (progn
      (setq band (urb:strip-band-region c1 c2 elevation))
      (if (null band)
        (progn
          (urb:bb-log (strcat "  tactil " feature ": no se pudo cerrar la banda"))
          (entdel c1) (entdel c2) nil)
        (progn
          (setq strip (vla-Copy base-region))
          ;; REGION exige coplanaridad exacta. Tras restar contenedores,
          ;; Civil puede conservar en base-region la elevacion original
          ;; aunque la polilinea tactil ya se haya aplanado a Z=0. Alinear
          ;; explicitamente evita "Automation Error. Non coplanar geometry"
          ;; y el falso TOPEROL=0 del caso real.
          (urb:region-align-elevation band strip)
          (setq booleaned
            (vl-catch-all-apply 'vla-Boolean (list strip 1 band)))
          (if (vl-catch-all-error-p booleaned)
            (progn
              (urb:bb-log (strcat "  tactil " feature ": booleano fallo: "
                (urb:safe-string (vl-catch-all-error-message booleaned) "?")))
              (urb:safe-delete strip)
              (urb:safe-delete band)
              (entdel c1) (entdel c2)
              nil)
            (progn
              (setq len (urb:curve-length chain-poly))
              ;; 2026-09-12 (reporte del usuario: "verifica lo referente al
              ;; toperol que no se ve"). En un contorno CON CURVA la franja
              ;; del toperol (d1 = 0, o sea su borde es la cadena misma y no
              ;; un offset) salia reducida a una sola tableta -- medido: 0,04
              ;; m2 de los 30 m2 del tramo -- y aun asi se daba por buena.
              ;; Ahora se compara el area real contra la esperada
              ;; (longitud x ancho de la franja): si no cubre ni la mitad,
              ;; el offset no sirvio en este contorno y se declara FALLO
              ;; para que el llamador la complete por segmentos.
              (setq area-real (vl-catch-all-apply 'vla-get-Area (list strip)))
              (if (not (numberp area-real)) (setq area-real 0.0))
              (setq area-esp (* len (abs (- d2 d1))))
              ;; OJO: c1 y c2 los borra abajo la rama de fallo. No hay que
              ;; borrarlos aqui tambien -- entdel es un interruptor y una
              ;; segunda llamada los REVIVE.
              (if (and (> area-esp 1e-6) (< area-real (* 0.5 area-esp)))
                (progn
                  (urb:bb-log (strcat "  tactil " feature ": area insuficiente real="
                    (rtos area-real 2 3) " esperada=" (rtos area-esp 2 3)))
                  (setq tone-count 0))
                (setq tone-count
                  (urb:offset-strip-tones
                    strip chain-poly len layer parent-handle elevation span feature)))
              ;; La franja continua es limite del hatch y area medida.
              ;; Conservarla solo si la decoracion tuvo exito.
              (if (<= tone-count 0) (urb:safe-delete strip))
              (if (<= tone-count 0)
                (progn
                  (urb:bb-log (strcat "  tactil " feature ": sin relleno/tono"))
                  (entdel c1) (entdel c2)
                  nil)
                (progn
                  ;; bordes de la franja: las dos curvas offset quedan como
                  ;; lineas de junta visibles
                  (foreach c (list c1 c2)
                    (vla-put-Layer (vlax-ename->vla-object c) layer)
                    (vla-put-Color (vlax-ename->vla-object c) 8)
                    (urb:tag-generated-role
                      (vlax-ename->vla-object c) parent-handle "FEATURE"))
                  ;; contornos del anden, para que ningun simbolo se dibuje
                  ;; fuera (vla-Explode no destruye la region original)
                  (setq loops
                    (vl-catch-all-apply 'urb:region-polygons (list base-region)))
                  (if (vl-catch-all-error-p loops) (setq loops nil))
                  (setq symbols-ok
                    (urb:offset-strip-symbols
                      chain-poly len d1 d2 perp-sign feature module
                      layer parent-handle loops))
                  (if (not symbols-ok)
                    (urb:bb-log (strcat "  tactil " feature ": sin simbolos dentro del contorno")))
                  ;; Un strip sin domos/capsulas no cuenta como terminado;
                  ;; el caller puede activar su metodo segmentado de respaldo.
                  symbols-ok))))))))
)

(defun urb:ray-ring-distances (p ang rings / ux uy a b ex ey px py den tt uu hits ring)
  (setq ux (cos ang) uy (sin ang))
  (foreach ring rings
    (setq a (last ring))
    (foreach b ring
      (setq ex (- (car b) (car a)) ey (- (cadr b) (cadr a))
            px (- (car a) (car p)) py (- (cadr a) (cadr p))
            den (- (* ux ey) (* uy ex)))
      (if (> (abs den) 1e-12)
        (progn
          (setq tt (/ (- (* px ey) (* py ex)) den)
                uu (/ (- (* px uy) (* py ux)) den))
          (if (and (> tt 1e-5) (>= uu -1e-8) (<= uu 1.00000001))
            (setq hits (cons tt hits)))))
      (setq a b)))
  (vl-sort hits '<))

(defun urb:guide-uniform-offset (chain rings goff module inward / len n step i d p ang hits cap best valid total)
  ;; Una UNICA distancia para todo el tramo. La 5.7.5 variaba el offset
  ;; cada 25 cm y produjo una guia serpenteante aunque el toperol fuera
  ;; recto. Se toma el menor espacio disponible del corredor completo;
  ;; asi la guia puede acercarse uniformemente al toperol en un anden
  ;; estrecho, pero nunca se tuerce de una estacion a la siguiente.
  (setq len (urb:curve-length chain) n (max 1 (fix (+ 1.0 (/ len 0.25))))
        step (/ len n) i 1 valid 0 total 0)
  ;; Los entrantes de contenedores no deben torcer la guia ni anularla.
  ;; Se calcula UNA distancia con las secciones utiles y luego la region
  ;; recorta los trozos ocupados. Se omiten los remates porque la normal en
  ;; una esquina no representa el ancho longitudinal del anden.
  (while (< i n)
    (setq d (* i step) p (urb:curve-pt chain d)
          ang (+ (urb:curve-tangent chain (min (- len 0.001) (max 0.001 d))) (* inward 0.5 pi))
          hits (vl-remove-if-not '(lambda (v)
            (and (urb:point-in-region-polygons-p (polar p ang (- v 0.0001)) rings)
                 (not (urb:point-in-region-polygons-p (polar p ang (+ v 0.0001)) rings))))
            (urb:ray-ring-distances p ang rings))
          cap (if hits (min (+ goff (* 0.5 module)) (- (car hits) (* 0.5 module) 0.06)) nil))
    (setq total (1+ total))
    (if (and cap (>= cap (+ (* 1.5 module) 0.04)))
      (progn
        (setq valid (1+ valid))
        (if (or (null best) (< cap best)) (setq best cap))))
    (setq i (1+ i)))
  (if (and best (> total 0) (>= (/ (float valid) total) 0.50))
    (- best (* 0.5 module))
    nil))

(defun urb:toperol-uniform-offset
  (chain rings module inward / len n step candidate limit found valid total i d p ang p1 p2)
  ;; Busca la primera fila recta con al menos 50 % de recorrido util. Los
  ;; contenedores recortan localmente el acabado, pero no deben exigir que
  ;; toda la fila este libre: esa condicion anulaba un anden real aunque
  ;; habia mas de 50 m disponibles. La distancia permanece uniforme.
  (setq len (urb:curve-length chain)
        n (max 1 (fix (+ 1.0 (/ len 0.50))))
        step (/ len n)
        candidate 0.0 limit 5.0)
  (while (and (null found) (<= candidate limit))
    (setq valid 0 total 0 i 1)
    (while (< i n)
      (setq d (* i step)
            p (urb:curve-pt chain d)
            ang (+ (urb:curve-tangent chain d) (* inward 0.5 pi))
            p1 (polar p ang (+ candidate 0.01))
            p2 (polar p ang (+ candidate module -0.01)))
      (setq total (1+ total))
      (if (and (urb:point-in-region-polygons-p p1 rings)
               (urb:point-in-region-polygons-p p2 rings))
        (setq valid (1+ valid)))
      (setq i (1+ i)))
    (if (and (> total 0) (>= (/ (float valid) total) 0.50))
      (setq found candidate)
      (setq candidate (+ candidate (* 0.5 module)))))
  found)

(defun urb:create-accessibility-features-offset
  (base-region points driving-chain guia toperol format parent-handle
   / module goff chain-poly len box elevation off-sign perp-sign
     mid-d mid-pt mid-ang cand test-off count layer span
     ok-top ok-gui rescate guide-offset guide-rings top-offset top-built guide-built)
  (setq module (urb:loseta-module format))
  (setq goff *urb-guide-offset*)
  (setq box (urb:object-box-points base-region)
        elevation (if (and box (caddr (car box))) (caddr (car box)) 0.0))
  (setq span (urb:points-span points))
  (setq chain-poly (urb:open-poly-from-points driving-chain elevation))
  (setq len (urb:curve-length chain-poly))
  (if (< len (* 2.0 module))
    (progn (entdel chain-poly) nil)
    (progn
      ;; lado hacia ADENTRO del anden: (1) signo del offset probando de
      ;; que lado cae la curva desplazada; (2) signo de la normal para
      ;; los simbolos, probando un punto desplazado a mano
      (setq mid-d (* 0.5 len))
      (setq mid-pt (urb:curve-pt chain-poly mid-d))
      (setq mid-ang (urb:curve-tangent chain-poly mid-d))
      ;; La cadena conserva el recorrido del anillo: CCW = interior izquierdo.
      ;; Probar UN punto a 30 cm falla si coincide con un contenedor/entrante
      ;; y voltea TODA la franja. El sentido geometrico no depende de huecos.
      (setq perp-sign (if (< (urb:polygon-signed-area points) 0.0) -1.0 1.0))
      (setq off-sign 1.0)
      (setq test-off (urb:offset-poly chain-poly 0.3))
      (if test-off
        (progn
          (setq cand (vlax-curve-getClosestPointTo test-off mid-pt))
          (if (or (null cand)
                  (< (* perp-sign
                       (- (* (cos mid-ang) (- (cadr cand) (cadr mid-pt)))
                          (* (sin mid-ang) (- (car cand) (car mid-pt))))) 0.0))
            (setq off-sign -1.0))
          (entdel test-off))
        (setq off-sign -1.0))
      ;; 2026-09-12 (reporte del usuario: el anden curvo salia sin toperol).
      ;; Antes bastaba con que UNA de las dos franjas saliera para dar el
      ;; trabajo por terminado: con la guia hecha y el toperol fallado, el
      ;; llamador nunca activaba su respaldo y el anden quedaba sin toperol.
      ;; Ahora se lleva cuenta POR FRANJA y la que falle se completa aqui
      ;; mismo con el metodo segmentado, sin repetir la que si salio.
      (setq count 0 ok-top (not (urb:yes-p toperol)) ok-gui (not (urb:yes-p guia)))
      (setq guide-rings (urb:region-polygons base-region))
      (if (urb:yes-p toperol)
        (progn
          (setq layer
            (if (> module 0.30)
              "URB-ANDEN-LOSETA-TOPEROL-40X40" "URB-ANDEN-LOSETA-TOPEROL-20X20"))
          (setq top-offset
            (urb:toperol-uniform-offset
              chain-poly guide-rings module perp-sign))
          (urb:bb-log (strcat "  tactil: toperol offset="
            (vl-princ-to-string top-offset) " off-sign="
            (rtos off-sign 2 0) " perp-sign=" (rtos perp-sign 2 0)
            " loops=" (itoa (length guide-rings))))
          (if top-offset
            (progn
              (setq top-built (urb:build-offset-strip
                base-region chain-poly top-offset (+ top-offset module)
                off-sign perp-sign layer "TOPEROL" module parent-handle elevation span))
              (urb:bb-log (strcat "  tactil: toperol build=" (vl-princ-to-string top-built)))
              (if top-built (setq count (1+ count) ok-top T)))
            (prompt "\nTOPEROL: no hay una fila continua libre en los primeros 5 m."))))
      (if (urb:yes-p guia)
        (progn
          (setq layer
            (if (> module 0.30)
              "URB-ANDEN-LOSETA-GUIA-40X40" "URB-ANDEN-LOSETA-GUIA-20X20"))
          (setq guide-offset (urb:guide-uniform-offset chain-poly guide-rings goff module perp-sign))
          (urb:bb-log (strcat "  tactil: guia offset="
            (vl-princ-to-string guide-offset)))
          (if guide-offset
            (progn
              (setq guide-built (urb:build-offset-strip
                base-region chain-poly guide-offset (+ guide-offset module) off-sign perp-sign
                layer "GUIA" module parent-handle elevation span))
              (urb:bb-log (strcat "  tactil: guia build=" (vl-princ-to-string guide-built)))
              (if guide-built (setq count (1+ count) ok-gui T)))
            (prompt "\nGUIA: no hay paso continuo suficiente; se verifica el respaldo segmentado."))))
      (entdel chain-poly)
      (if (or (not ok-top) (not ok-gui))
        (progn
          (prompt
            (strcat "\nANDEN: la franja de "
              (cond ((and (not ok-top) (not ok-gui)) "guia y toperol")
                    ((not ok-top) "toperol")
                    (T "guia"))
              " no se pudo desplazar sobre este contorno; se rehace por segmentos."))
          (setq rescate
            (vl-catch-all-apply 'urb:create-accessibility-features-segmented
              (list base-region points
                    (urb:chain-simplify-by-direction driving-chain
                      (* pi (/ 5.0 180.0)))
                    (if ok-gui "No" guia) (if ok-top "No" toperol)
                    format parent-handle)))
          (if (and (not (vl-catch-all-error-p rescate)) rescate)
            (setq count (1+ count)))))
      (> count 0)))
)

(defun urb:create-accessibility-features-segmented
  (base-region points driving-chain guia toperol format parent-handle
   / edges edge angle-value module cosine sine u1 u2 umin umax
   bounds-wide vmin-wide vmax-wide full-slice slice-points bounds-local
   vmin-local vmax-local width reference-edge guide-min guide-max
   top-min top-max region origin layer count cum-offset
   p1-v boundary-side side-decided prefer-boundary
   bisectors edge-index bis span grid-u into)
  ;; Igual que urb:create-accessibility-features pero por segmento real del
  ;; contorno: cada arista del lado guia recorta y mide su propia franja en
  ;; vez de usar el ancho proyectado de TODO el anden sobre un unico eje
  ;; (que en un tramo curvo da un ancho falso, inflado por vertices de otras
  ;; estaciones, y termina sembrando simbolos muy por fuera del area real).
  ;; cum-offset acumula la distancia recorrida desde el arranque de toda la
  ;; cadena hasta el inicio de este segmento: se pasa a
  ;; urb:decorate-accessibility-strip para que la reticula de simbolos de
  ;; 5cm sea UNA sola secuencia continua a lo largo de todo el corredor, en
  ;; vez de reiniciar en 0 en cada segmento (lo que dejaba la costura entre
  ;; segmentos vecinos desalineada / con huecos).
  ;; side-decided/prefer-boundary: en un anden curvo real con barrido de
  ;; tangente grande (60-90+ grados de un extremo al otro de la cadena),
  ;; *urb-current-tactile-side-point* comparado contra vmin-local/vmax-local
  ;; de CADA arista por separado (el metodo viejo, urb:reference-v-edge)
  ;; puede voltear de lado a mitad de camino aunque el punto de referencia
  ;; siga siendo fisicamente el mismo -- un punto de referencia cercano al
  ;; anden puede terminar "adelante" de la curva para las primeras aristas
  ;; y "atras" para las ultimas. Eso hacia que la guia/el toperol saltaran
  ;; al lado opuesto del corredor a mitad de curva: un corte visible en la
  ;; franja seguido de que reaparece del otro lado. Arreglo: decidir UNA
  ;; SOLA VEZ (con la primera arista) si el usuario quiere el lado donde
  ;; esta la arista misma (boundary-side) o el lado opuesto, y de ahi en
  ;; adelante usar boundary-side de cada arista (que es exacto: el vertice
  ;; p1 de la arista SIEMPRE cae casi exacto en uno de los dos bordes del
  ;; recorte local, sin la ambiguedad de comparar contra un punto lejano).
  (setq module (urb:loseta-module format))
  (setq edges (urb:open-chain-edges driving-chain))
  (setq count 0 cum-offset 0.0 side-decided nil edge-index 0)
  ;; Cunas a inglete: mismas bisectrices que usa el material, para que la
  ;; franja de guia/toperol de cada arista termine exactamente donde
  ;; empieza la de la siguiente (sin el traslape que pintaba la guia
  ;; cruzada en diagonal sobre la reticula en las transiciones).
  (setq bisectors (urb:chain-edge-bisectors edges))
  (setq span (urb:points-span points))
  (foreach edge edges
    (setq angle-value (nth 3 edge) cosine (cos angle-value) sine (sin angle-value))
    (setq u1 (+ (* (car (nth 0 edge)) cosine) (* (cadr (nth 0 edge)) sine)))
    (setq u2 (+ (* (car (nth 1 edge)) cosine) (* (cadr (nth 1 edge)) sine)))
    (setq umin (min u1 u2) umax (max u1 u2))
    (setq bis (nth edge-index bisectors))
    (setq full-slice
      (urb:clip-edge-wedge
        base-region (nth 0 edge) (nth 1 edge)
        (if (= edge-index 0) nil (nth 0 bis))
        (if (= edge-index (1- (length edges))) nil (nth 1 bis)) span))
    (if (null full-slice)
      (progn
        (setq bounds-wide (urb:project-bounds points angle-value)
              vmin-wide (nth 2 bounds-wide) vmax-wide (nth 3 bounds-wide))
        (setq full-slice (urb:clip-stripe base-region umin umax vmin-wide vmax-wide angle-value))))
    (if full-slice
      (progn
        (setq slice-points (urb:region-outline-points full-slice))
        (if (null slice-points) (setq slice-points (urb:object-box-points full-slice)))
        (if slice-points
          (progn
            (setq bounds-local (urb:project-bounds slice-points angle-value)
                  vmin-local (nth 2 bounds-local)
                  vmax-local (nth 3 bounds-local)
                  width (- vmax-local vmin-local))
            (setq p1-v (urb:point-v-coordinate (nth 0 edge) angle-value))
            (setq boundary-side
              (if (<= (abs (- p1-v vmin-local)) (abs (- p1-v vmax-local)))
                vmin-local
                vmax-local))
            (if (null side-decided)
              (progn
                (setq side-decided T)
                (setq prefer-boundary
                  (equal
                    boundary-side
                    (urb:reference-v-edge points angle-value vmin-local vmax-local)
                    1e-6))))
            (setq reference-edge
              (if prefer-boundary
                boundary-side
                (if (equal boundary-side vmin-local 1e-9) vmax-local vmin-local)))
            ;; origen de reticula en u alineado a la cadena GLOBAL (la
            ;; misma fase que usa el material), para que las juntas de la
            ;; franja tactil coincidan con las juntas de la loseta.
            (setq grid-u (- umin (urb:grid-phase-shift cum-offset module)))
            ;; Posicion medida RESPECTO A LA ARISTA de la cadena (que ES
            ;; el borde de la via, porque la cadena tactil se elige del
            ;; lado del click), no respecto a los bounds proyectados del
            ;; recorte: con las cunas a inglete esos bounds varian por
            ;; arista segun la inclinacion de las bisectrices y la guia
            ;; salia en "escalera" de barras sueltas a radios distintos
            ;; (visto en el PDF de verificacion del abanico).
            (setq into
              (if (<= (abs (- p1-v vmin-local)) (abs (- p1-v vmax-local)))
                1.0 -1.0))
            (if (urb:yes-p guia)
              (progn
                (if (< width module)
                  (setq guide-min vmin-local guide-max vmax-local)
                  (if prefer-boundary
                    ;; caso normal: via = lado de la propia cadena
                    (if (> into 0)
                      (setq guide-min (+ p1-v *urb-guide-offset*)
                            guide-max (+ p1-v *urb-guide-offset* module))
                      (setq guide-min (- p1-v *urb-guide-offset* module)
                            guide-max (- p1-v *urb-guide-offset*)))
                    ;; via al lado opuesto de la cadena: como antes
                    (if (= reference-edge vmin-local)
                      (setq guide-min (+ vmin-local *urb-guide-offset*)
                            guide-max (+ vmin-local *urb-guide-offset* module))
                      (setq guide-min (- vmax-local *urb-guide-offset* module)
                            guide-max (- vmax-local *urb-guide-offset*)))))
                (if (>= width module)
                  (setq guide-min (max vmin-local (min (- vmax-local module) guide-min))
                        guide-max (+ guide-min module)))
                ;; el rango en u va MUY holgado a lado y lado: la cuna a
                ;; inglete ya limita angularmente, y a 2.5m del borde la
                ;; cuna es mas ancha que la cuerda de la arista -- recortar
                ;; al rango de la cuerda dejaba HUECOS entre las franjas de
                ;; aristas vecinas (guia punteada en el PDF del abanico).
                (setq region
                  (urb:clip-stripe full-slice (- umin span) (+ umax span)
                    guide-min guide-max angle-value))
                ;; SIN fallback de ancho completo: cuando el recorte fino
                ;; fallaba, pintar la franja a todo el ancho del anden
                ;; dejaba un manchon diagonal cruzando las bandas (visto
                ;; en PDF); un micro-hueco puntual es mucho menos grave.
                (if region
                  (progn
                    ;; origen del grid: u alineado a la cadena global,
                    ;; v en el borde inferior de la propia fila (que tras
                    ;; el snap cae sobre la reticula del material)
                    (setq origin (urb:local-to-world grid-u guide-min angle-value))
                    (setq layer
                      (if (> module 0.30)
                        "URB-ANDEN-LOSETA-GUIA-40X40" "URB-ANDEN-LOSETA-GUIA-20X20"))
                    (urb:decorate-accessibility-strip
                      region layer "GUIA" module angle-value origin parent-handle cum-offset)
                    (setq count (1+ count))))))
            (if (urb:yes-p toperol)
              (progn
                (if prefer-boundary
                  ;; toperol pegado a la ARISTA (borde real de la via)
                  (if (> into 0)
                    (setq top-min p1-v top-max (+ p1-v module))
                    (setq top-min (- p1-v module) top-max p1-v))
                  (if (= reference-edge vmin-local)
                    (setq top-min vmin-local top-max (min vmax-local (+ vmin-local module)))
                    (setq top-min (max vmin-local (- vmax-local module)) top-max vmax-local)))
                (setq region
                  (urb:clip-stripe full-slice (- umin span) (+ umax span)
                    top-min top-max angle-value))
                ;; sin fallback de ancho completo (mismo criterio que guia)
                (if region
                  (progn
                    ;; u alineado a la cadena global; v en el borde
                    ;; inferior de la fila del toperol (pegada a la via)
                    (setq origin (urb:local-to-world grid-u top-min angle-value))
                    (setq layer
                      (if (> module 0.30)
                        "URB-ANDEN-LOSETA-TOPEROL-40X40" "URB-ANDEN-LOSETA-TOPEROL-20X20"))
                    (urb:decorate-accessibility-strip
                      region layer "TOPEROL" module angle-value origin parent-handle cum-offset)
                    (setq count (1+ count))))))))
        (urb:safe-delete full-slice)))
    (setq cum-offset (+ cum-offset (- umax umin)))
    (setq edge-index (1+ edge-index)))
  (> count 0)
)

;; 5.6.7: registro de diagnostico cuando el toperol no cabe. Escribe el
;; contorno (x y bulge por vertice) y cada cortador cercano (prefabricado,
;; contenedor, rampa) con su bloque, punto de insercion y rotacion.
(defun urb:toperol-fallo-registrar (ename / fn f ed obj en cobj ins)
  (setq fn (strcat (urb:safe-string (getenv "TEMP") "C:\\Temp") "\\urbcant_toperol_fallo.txt")
        f (open fn "a"))
  (if f
    (progn
      (write-line (strcat "=== " (urb:safe-string (menucmd "M=$(edtime,$(getvar,date),YYYY-MO-DD HH:MM:SS)") "?")
                          " | " (urb:safe-string *urb-version* "?")
                          " | " (urb:safe-string (getvar "DWGNAME") "?")
                          " | contorno " (cdr (assoc 5 (entget ename))))
                  f)
      (setq ed (entget ename))
      (foreach it ed
        (cond
          ((= (car it) 10)
            (write-line (strcat "V " (rtos (cadr it) 2 4) " " (rtos (caddr it) 2 4)) f))
          ((= (car it) 42)
            (write-line (strcat "B " (rtos (cdr it) 2 8)) f))))
      (write-line (strcat "LADO_VIA " (vl-princ-to-string *urb-current-tactile-side-point*)) f)
      (write-line (strcat "ANCLA_LADO " (vl-princ-to-string *urb-current-tactile-side-anchor*)) f)
      (setq obj (vlax-ename->vla-object ename))
      (foreach en (urb:anden-cutout-blocks)
        (setq cobj (urb:as-vla-object en))
        (if (and cobj (urb:objects-bbox-overlap-p obj cobj 2.0))
          (progn
            (setq ins (vlax-safearray->list (vlax-variant-value (vla-get-InsertionPoint cobj))))
            (write-line
              (strcat "C " (vla-get-Name cobj) " " (rtos (car ins) 2 4) " " (rtos (cadr ins) 2 4)
                      " rot " (rtos (vla-get-Rotation cobj) 2 6))
              f))))
      (close f)))
  T)

(defun urb:create-accessibility-features
  (ename guia toperol format / obj copy base-region points angle-value bounds
   umin umax vmin vmax center region parent-handle origin count limits
   reference-edge width guide-min guide-max pattern-v-origin module layer
   top-min top-max driving-chain offset-result cleaned-points
   region-loops normalized-region)
  (if (and (not (urb:yes-p guia))
           (not (urb:yes-p toperol)))
    T
    (progn
      (setq obj (vlax-ename->vla-object ename))
      (setq parent-handle (vla-get-Handle obj))
      ;; muestreo FINO solo aqui: la franja tactil sigue el arco real
      (setq points (urb:lwpoly-points-with-arcs-fine ename))
      (setq module (urb:loseta-module format))
      ;; No convertir una vla-Copy del contorno con XDATA: Civil 3D 2023
      ;; puede conservar en esa copia un plano interno incoherente y el
      ;; booleano tactil falla luego con "Non coplanar geometry". Se arma
      ;; una polilinea limpia Z=0 con el muestreo fino de los arcos; es una
      ;; copia desechable y mantiene la precision grafica del contorno.
      (setq copy (urb:open-poly-from-points points 0.0))
      (if copy
        (progn
          (setq copy (vlax-ename->vla-object copy))
          (vla-put-Closed copy :vlax-true)))
      (setq base-region (urb:anden-region-from-object copy))
      (urb:safe-delete copy)
      (if (not (vl-catch-all-error-p base-region))
        (setq base-region (urb:apply-anden-cutouts base-region)))
      ;; Normalizar el caso comun de un solo bucle a una REGION WCS Z=0.
      ;; Los booleanos de losetas toleran el plano interno que algunas
      ;; copias con XDATA heredan; ACIS lo rechaza al intersectar luego una
      ;; banda angosta. Reconstruir desde el bucle 2D elimina ese estado
      ;; oculto sin alterar el contorno neto ni sus recortes.
      (if (and base-region (not (vl-catch-all-error-p base-region)))
        (progn
          (setq region-loops (urb:region-polygons base-region))
          (if (= (length region-loops) 1)
            (progn
              (setq normalized-region
                (urb:polygon-region (car region-loops) 0.0))
              (if normalized-region
                (progn
                  (urb:safe-delete base-region)
                  (setq base-region normalized-region)))))))
      (if (vl-catch-all-error-p base-region)
        nil
        (progn
          ;; la franja tactil sigue la cadena del lado de la VIA (click
          ;; del usuario), no el lado mas largo del contorno
          (setq driving-chain (urb:anden-tactile-chain points))
          ;; El entrante de un contenedor solo recorta: no cambia el rumbo
          ;; de la guia/toperol ni genera cunas a inglete alrededor del hueco.
          ;; Un contenedor NO convierte un anden curvo en una franja recta:
          ;; conservar el eje con arcos y recortar contra base-region. Forzar
          ;; nil aqui perdia casi toda la guia/toperol fuera de la cuerda.
          ;; Conservar el respaldo anterior para contornos rectilineos entrantes.
          ;; 5.7.3: antes aqui se DESCARTABA la cadena (driving-chain nil)
          ;; y la franja salia recta y cruzada en andenes con quiebres. Ahora
          ;; se quitan los entrantes de los contenedores del anillo y se
          ;; vuelve a buscar la cadena: sigue los quiebres reales del anden.
          ;; Si el anden es recto la cadena sale de 1 arista y se usa el
          ;; metodo de eje unico de siempre.
          ;; Los entrantes no solo vienen de contenedores: los costados
          ;; prefabricados y otros recortes producen el mismo zigzag. En un
          ;; contorno rectilineo se limpian siempre para escoger el costado
          ;; semantico completo; base-region sigue haciendo el recorte fisico,
          ;; asi que no se pinta encima del obstaculo. Los arcos conservan su
          ;; geometria exacta y no pasan por este simplificador.
          (if (not (vl-some '(lambda (p)
                    (and (= (car p) 42) (not (equal (cdr p) 0.0 1e-12))))
                    (entget ename)))
            (progn
              (setq cleaned-points (urb:ring-remove-notches points))
              (if (< (length cleaned-points) (length points))
                (setq driving-chain
                  (urb:anden-tactile-chain cleaned-points)))))
          ;; 5.6.8 caja negra: que ruta toma la franja tactil y como termina
          (urb:bb-log (strcat "  tactil: cadena guia "
            (if driving-chain (itoa (length driving-chain)) "NINGUNA") " pts"
            " | area base " (rtos (vla-get-Area base-region) 2 2)
            " | lado via " (vl-princ-to-string *urb-current-tactile-side-point*)
            " | ancla " (vl-princ-to-string *urb-current-tactile-side-anchor*)
            " | eleccion " (vl-princ-to-string *urb-current-tactile-side-choice*)))
          ;; Tambien una cadena perfectamente recta (una sola arista) debe
          ;; usar la franja por offset. Mandarla al metodo global hace que los
          ;; entrantes del costado opuesto inflen el ancho proyectado y puede
          ;; dejar TOPEROL=0 aun cuando junto al borde haya espacio continuo.
          (if (and driving-chain (>= (length (urb:open-chain-edges driving-chain)) 1))
            (progn
              ;; metodo principal: franja como OFFSET de la curva real
              ;; (continua a cualquier radio); si el offset falla
              ;; (contorno con quiebres imposibles de desplazar), cae al
              ;; metodo anterior por segmentos
              (setq offset-result
                (vl-catch-all-apply
                  'urb:create-accessibility-features-offset
                  (list base-region points driving-chain guia toperol format parent-handle)))
              (urb:bb-log (strcat "  tactil: ruta OFFSET -> "
                (cond ((vl-catch-all-error-p offset-result)
                        (strcat "ERROR " (urb:safe-string (vl-catch-all-error-message offset-result) "?")))
                      (offset-result "OK")
                      (T "SIN RESULTADO"))))
              (if (and (not (vl-catch-all-error-p offset-result)) offset-result)
                offset-result
                (progn
                  (setq offset-result
                    (urb:create-accessibility-features-segmented
                      base-region points
                      (urb:chain-simplify-by-direction driving-chain
                        (* pi (/ 5.0 180.0)))
                      guia toperol format parent-handle))
                  (urb:bb-log (strcat "  tactil: ruta SEGMENTOS -> " (if offset-result "OK" "SIN RESULTADO")))
                  offset-result)))
            (progn
              (setq angle-value (urb:anden-axis-angle points))
              (setq bounds (urb:project-bounds points angle-value))
              (setq umin (nth 0 bounds))
              (setq umax (nth 1 bounds))
              (setq vmin (nth 2 bounds))
              (setq vmax (nth 3 bounds))
              (setq reference-edge
                (urb:reference-v-edge points angle-value vmin vmax))
              (setq pattern-v-origin reference-edge)
              (if (urb:yes-p guia)
                (progn
                  (setq width (- vmax vmin))
                  (if (< width module)
                    (setq guide-min vmin guide-max vmax)
                    (if (= reference-edge vmin)
                      (setq guide-min (+ vmin *urb-guide-offset*)
                            guide-max (+ vmin *urb-guide-offset* module))
                      (setq guide-min (- vmax *urb-guide-offset* module)
                            guide-max (- vmax *urb-guide-offset*))))
                  (if (>= width module)
                    (progn
                      (setq guide-min
                        (max vmin (min (- vmax module) guide-min)))
                      (setq guide-max (+ guide-min module))))
                  (setq center (/ (+ guide-min guide-max) 2.0))
                  (setq region
                    (urb:clip-stripe
                      base-region umin umax guide-min guide-max angle-value))
                  (if region
                    (progn
                      (setq origin
                        (urb:local-to-world
                          umin pattern-v-origin angle-value))
                      (setq layer
                        (if (> module 0.30)
                          "URB-ANDEN-LOSETA-GUIA-40X40"
                          "URB-ANDEN-LOSETA-GUIA-20X20"))
                      (urb:decorate-accessibility-strip
                        region layer "GUIA" module angle-value origin parent-handle
                        (urb:strip-phase-offset region angle-value umin))
                      (setq count (1+ (if count count 0)))))))
              (if (urb:yes-p toperol)
                (progn
                  (if (= reference-edge vmin)
                    (setq top-min vmin top-max (min vmax (+ vmin module)))
                    (setq top-min (max vmin (- vmax module)) top-max vmax))
                  (setq region
                    (urb:clip-stripe
                      base-region umin umax top-min top-max angle-value))
                  (if region
                    (progn
                      (setq origin
                        (urb:local-to-world umin reference-edge angle-value))
                      (setq layer
                        (if (> module 0.30)
                          "URB-ANDEN-LOSETA-TOPEROL-40X40"
                          "URB-ANDEN-LOSETA-TOPEROL-20X20"))
                      (urb:decorate-accessibility-strip
                        region layer "TOPEROL" module angle-value origin parent-handle
                        (urb:strip-phase-offset region angle-value umin))
                      (setq count (1+ (if count count 0)))))))
              (urb:safe-delete base-region)
              (> (if count count 0) 0)))))))
)

;; 5.6.3 (pedido del usuario: "me equivoco, doy ctrl z para volver a dibujar
;; el tramo que dibuje mal y se cancela lo del dibujo del contorno y me toca
;; volver a dibujar todo"). Ctrl+Z es la macro ^C^C_u: el primer ^C cancelaba
;; PLINE y el LISP del comando, y el _u deshacia la polilinea entera.
;; Ahora la cancelacion se atrapa: PLINE deja en el dibujo los tramos hechos,
;; se reabre PLINE con esos mismos vertices (arcos incluidos) y la cola de la
;; macro cae DENTRO del PLINE reabierto: el segundo ^C llega en milisegundos
;; (se vuelve a reabrir) y el "_u" es la opcion Deshacer de PLINE -> quita
;; solo el ultimo tramo. Un Esc humano reabre con todo lo dibujado; un
;; segundo Esc sin dibujar nada nuevo cancela como antes.
(defun urb:draw-polyline-interactive (old-plinewid / before r t0 after data n restored done abort-it)
  (setq before (entlast))
  (vl-cmdf "_.PLINE")
  (while (not done)
    (setq t0 (getvar "MILLISECS"))
    (setq r (vl-catch-all-apply
              '(lambda () (while (> (getvar "CMDACTIVE") 0) (command pause)))))
    (if (not (vl-catch-all-error-p r))
      (setq done T)
      (progn
        (setq after (entlast) data nil n 0)
        (if (and after (not (eq after before))
                 (= (cdr (assoc 0 (entget after))) "LWPOLYLINE"))
          (setq data (urb:lwpoly-vertex-bulges after) n (length (car data)))
          (setq after nil))
        (cond
          ;; resto de la macro de Ctrl+Z: llega sin intervencion humana
          ((and restored (< (- (getvar "MILLISECS") t0) 150))
            (urb:pline-restart after data))
          ;; Esc antes de tener un tramo, o Esc de nuevo sin dibujar nada
          ((or (and (< n 2) (null restored)) (and restored (= n restored)))
            (setq done T abort-it T))
          (T
            (urb:pline-restart after data)
            (setq restored n)
            (prompt
              (strcat "\nContorno recuperado (" (itoa n) " vertices). Siga dibujando;"
                " U o Ctrl+Z deshace el ultimo tramo, Enter termina, Esc otra vez cancela.")))))))
  (setvar "PLINEWID" old-plinewid)
  (if abort-it (exit))
)

;; Recorrido abierto de una sola pieza. En canuelas Esc debe CANCELAR de
;; inmediato: no se usa la recuperacion especial de contornos, que reabre
;; PLINE y hacia parecer que el comando nunca terminaba.
(defun urb:draw-polyline-once (before / r after)
  (vl-cmdf "_.PLINE")
  (setq r
    (vl-catch-all-apply
      '(lambda ()
        (while (> (getvar "CMDACTIVE") 0) (command pause)))))
  (if (vl-catch-all-error-p r)
    (progn
      (if (> (getvar "CMDACTIVE") 0)
        (vl-catch-all-apply 'command nil))
      (setq after (entlast))
      (if (and after (not (eq after before)) (entget after)) (entdel after))
      nil)
    T))

;; reabre PLINE con los vertices (y arcos) de una polilinea a medio dibujar
(defun urb:pline-restart (ename data / pts bulges elev i p q b len mid arc)
  (if ename
    (setq elev (cdr (assoc 38 (entget ename)))))
  (if (not elev) (setq elev 0.0))
  (if ename (entdel ename))
  (vl-cmdf "_.PLINE")
  (if (and data (car data))
    (progn
      (setq pts (mapcar '(lambda (v) (list (car v) (cadr v) elev)) (car data))
            bulges (cadr data) i 0)
      (vl-cmdf (trans (car pts) 0 1))
      (while (< i (1- (length pts)))
        (setq p (nth i pts) q (nth (1+ i) pts) b (nth i bulges))
        (if (and (numberp b) (> (abs b) 1e-9))
          (progn
            ;; punto medio del arco: centro de la cuerda + sagita a la
            ;; DERECHA del sentido p->q para bulge positivo (antihorario)
            (setq len (distance (list (car p) (cadr p)) (list (car q) (cadr q)))
                  mid (list (+ (* 0.5 (+ (car p) (car q)))
                               (* (/ (* b len) 2.0) (/ (- (cadr q) (cadr p)) len)))
                            (+ (* 0.5 (+ (cadr p) (cadr q)))
                               (* (/ (* b len) 2.0) (/ (- (car p) (car q)) len)))
                            elev))
            (if (not arc) (progn (vl-cmdf "_A") (setq arc T)))
            (vl-cmdf "_S" (trans mid 0 1) (trans q 0 1)))
          (progn
            (if arc (progn (vl-cmdf "_L") (setq arc nil)))
            (vl-cmdf (trans q 0 1))))
        (setq i (1+ i)))
      (if arc (vl-cmdf "_L"))))
)

(defun urb:cross2d (ox oy ax ay bx by)
  (- (* (- ax ox) (- by oy)) (* (- ay oy) (- bx ox))))

(defun urb:segments-cross-p (p1 p2 p3 p4 / d1 d2 d3 d4)
  ;; Cruce ESTRICTO de dos segmentos (no cuenta solo tocarse en un
  ;; extremo compartido, que es normal entre aristas consecutivas).
  (setq d1 (urb:cross2d (car p3) (cadr p3) (car p4) (cadr p4) (car p1) (cadr p1)))
  (setq d2 (urb:cross2d (car p3) (cadr p3) (car p4) (cadr p4) (car p2) (cadr p2)))
  (setq d3 (urb:cross2d (car p1) (cadr p1) (car p2) (cadr p2) (car p3) (cadr p3)))
  (setq d4 (urb:cross2d (car p1) (cadr p1) (car p2) (cadr p2) (car p4) (cadr p4)))
  (and
    (or (and (> d1 0) (< d2 0)) (and (< d1 0) (> d2 0)))
    (or (and (> d3 0) (< d4 0)) (and (< d3 0) (> d4 0))))
)

(defun urb:polygon-self-intersects-p (points / n i ring a b edges tail e f scan found)
  ;; Barrido de cajas por X: misma prueba ESTRICTA, sin NTH sobre una
  ;; lista larga en cada pareja. No simplifica puntos ni omite cruces.
  ;; Registro: minX maxX minY maxY indice punto1 punto2.
  (setq n (length points) i 0 ring (append points (list (car points))))
  (while (cdr ring)
    (setq a (car ring) b (cadr ring)
          edges (cons (list (min (car a) (car b)) (max (car a) (car b))
            (min (cadr a) (cadr b)) (max (cadr a) (cadr b)) i a b) edges)
          i (1+ i) ring (cdr ring)))
  (setq tail (vl-sort edges '(lambda (a b)
    (if (= (car a) (car b)) (< (nth 4 a) (nth 4 b)) (< (car a) (car b))))))
  (while (and tail (not found))
    (setq e (car tail) scan (cdr tail))
    (while (and scan (<= (caar scan) (cadr e)) (not found))
      (setq f (car scan) i (abs (- (nth 4 e) (nth 4 f))))
      (if (and (/= i 1) (/= i (1- n))
               (<= (nth 2 e) (nth 3 f)) (<= (nth 2 f) (nth 3 e))
               (urb:segments-cross-p (nth 5 e) (nth 6 e) (nth 5 f) (nth 6 f)))
        (setq found T))
      (setq scan (cdr scan)))
    (setq tail (cdr tail)))
  found)

(defun urb:anden-shape-ok-p (pts / selfx)
  ;; El contorno arquitectonico puede tener anchos muy variables, entrantes
  ;; y ensanchamientos. La relacion max/min NO determina su validez y el
  ;; estimador de ancho tampoco mide secciones perpendiculares al eje.
  ;; Validar cruces para todos los tipos, tanto al crear como al actualizar;
  ;; los constructores conservan sus comprobaciones de region/acabado.
  (setq pts (urb:dedupe-ring-points pts))
  (setq selfx (vl-catch-all-apply 'urb:polygon-self-intersects-p (list pts)))
  (cond
    ((vl-catch-all-error-p selfx)
      (prompt
        (strcat "\n*** No se pudo validar el contorno (error interno: "
                (vl-catch-all-error-message selfx) ") ***"
                "\nPor seguridad no se genera el acabado sobre esta forma;"
                " revise el contorno (puede tener un segmento degenerado o"
                " un arco extremo) y vuelva a intentar."))
      nil)
    (selfx
      (prompt
        (strcat
          "\n*** El contorno dibujado se cruza a si mismo (forma tipo"
          " \"moño\") ***"
          "\nEsto genera un relleno con una mancha ancha/anomala en"
          " vez de una franja pareja."
          "\nEl contorno queda dibujado para que lo revise/corrija;"
          " no se genera el acabado del anden sobre esta forma."))
      nil)
    (T T)))

(defun urb:draw-closed-polyline
  (/ before after obj old-plinewid *error* pts)
  (setq old-plinewid (getvar "PLINEWID"))
  (defun *error* (message)
    (if old-plinewid (setvar "PLINEWID" old-plinewid))
    (if (and message
             (not (member message '("Function cancelled" "quit / exit abort"))))
      (prompt (strcat "\nError al dibujar el contorno: " message)))
    (princ))
  (setvar "PLINEWID" 0.0)
  (setq before (entlast))
  (prompt
    (strcat
      "\nDibuje el contorno del anden. Enter termina y cierra el area."
      " Puede usar OSNAP sobre la arista verde interior del PREFABRICADO."))
  (urb:draw-polyline-interactive old-plinewid)
  (setq after (entlast))
  (if (and after (/= after before)
           (= (cdr (assoc 0 (entget after))) "LWPOLYLINE"))
    (progn
      (setq obj (vlax-ename->vla-object after))
      (if (vlax-property-available-p obj 'ConstantWidth T)
        (vla-put-ConstantWidth obj 0.0))
      (vla-put-Closed obj :vlax-true)
      (if (urb:closed-poly-p after)
        (progn
          (setq pts (urb:lwpoly-points-with-arcs after))
          (if (urb:anden-shape-ok-p pts) after nil))
        nil))
    nil)
)

(defun urb:prepare-anden-layers ()
  (urb:ensure-layer "URB-ANDEN-LOSETA-LISA-40X40" 8 T)
  (urb:ensure-layer "URB-ANDEN-LOSETA-GRIS-20X20" 8 T)
  (urb:ensure-layer "URB-ANDEN-BLOQUE-BLANCO-20X10" 7 T)
  (urb:ensure-layer "URB-ANDEN-LOSETA-GUIA-20X20" 2 T)
  (urb:ensure-layer "URB-ANDEN-LOSETA-TOPEROL-20X20" 2 T)
  (urb:ensure-layer "URB-ANDEN-LOSETA-GUIA-40X40" 2 T)
  (urb:ensure-layer "URB-ANDEN-LOSETA-TOPEROL-40X40" 2 T)
  (urb:ensure-layer "URB-ANDEN" 7 T)
)

;; Cuenta el punteado del toperol realmente dibujado. v4.82 solo contaba
;; CIRCLE (un domo por entidad); desde v4.86 el punteado normal es UN
;; HATCH con el patron URB_TOPEROL por banda, asi que tambien cuenta. Si
;; no contara los dos, el control de calidad de urb:build-anden-finish
;; rechazaria un acabado que en realidad si tiene su toperol.
(defun urb:count-toperol-symbols (objects / n item nombre)
  (setq n 0)
  (foreach item objects
    (if (wcmatch (strcase (vla-get-Layer item)) "*TOPEROL*")
      (cond
        ((= (vla-get-ObjectName item) "AcDbCircle") (setq n (1+ n)))
        ((= (vla-get-ObjectName item) "AcDbHatch")
          (setq nombre
            (vl-catch-all-apply 'vla-get-PatternName (list item)))
          (if (and (= (type nombre) 'STR)
                   (wcmatch (strcase nombre) "*TOPEROL*"))
            (setq n (1+ n)))))))
  n)

(defun urb:build-anden-finish
  (ename material guia toperol format
   / obj result accessibility-result elevation flattened top-count)
  ;; Fallar ANTES de dibujar si otro computador no instalo el nuevo DLL.
  (urb:ensure-anden-fast)
  (setq material (urb:safe-string material "Loseta"))
  (setq guia (urb:safe-string guia "No"))
  (setq toperol (urb:safe-string toperol "No"))
  (setq format (urb:safe-string format "40 x 40 cm"))
  (setq obj (vlax-ename->vla-object ename))
  ;; El estado del patron solo es valido para este anden. Si quedo "SI" de
  ;; una generacion anterior, un fallo del primer hatch de este anden podia
  ;; ocultar la degradacion y dejar la franja sin textura.
  (setq *urb-toperol-pattern-state* nil
        *urb-toperol-fallos-pieza* 0
        *urb-generation-parent* (vla-get-Handle obj)
        *urb-generation-start* (entlast))
  ;; Los booleanos REGION y los HATCH son mucho mas estables y rapidos en
  ;; el plano Z=0. Se conserva la elevacion en URB_ANDEN y el bloque final
  ;; se inserta nuevamente en esa cota.
  (setq elevation
    (if (vlax-property-available-p obj 'Elevation T)
      (vla-get-Elevation obj)
      0.0))
  (if (and (numberp elevation) (not (equal elevation 0.0 1e-8))
           (vlax-property-available-p obj 'Elevation T))
    (progn
      (vla-put-Elevation obj 0.0)
      (setq flattened T)))
  (urb:prepare-anden-layers)
  ;; 4.18.0: se retiro el material "Adoquin" (capa dedicada + patron propio,
  ;; sin equivalente entre las capas que se conservaron). Todo anden nuevo
  ;; es Loseta; un xdata viejo con material distinto cae aqui igual.
  (vla-put-Layer obj "URB-ANDEN")
  (vla-put-Color obj 256)
  (urb:bb-log "  INICIA losetas (bandas y regiones)")
  (setq result (urb:create-composite-loseta ename format))
  (urb:bb-log (strcat "  TERMINA losetas " (if result "OK" "SIN RESULTADO")))
  (if (not result)
    (progn
      (vl-catch-all-apply 'urb:toperol-fallo-registrar (list ename))
      (prompt "\nANDEN: fallo el acabado de losetas antes de generar guia/toperol. Se conserva el contorno; caso guardado para diagnostico.")))
  (if result
    (progn
      (urb:bb-log "  INICIA guia y toperol")
      (setq accessibility-result
        (urb:create-accessibility-features ename guia toperol format))
      (urb:bb-log "  TERMINA guia y toperol")))
  ;; 5.6.8 (segundo reporte del mismo anden: "no me volvio a dejar crear
  ;; ese anden"): si la guia/toperol no se pudieron generar, su resultado
  ;; vacio REEMPLAZABA al de las losetas y el anden se perdia completo
  ;; aunque el acabado principal estuviera bien. Ahora solo se reemplaza
  ;; cuando la franja tactil si se genero; si no, el anden se crea con sus
  ;; losetas y se avisa (el control de toperol de abajo registra el caso).
  (if (and result
           (or (urb:yes-p guia)
               (urb:yes-p toperol)))
    (if accessibility-result
      (setq result accessibility-result)
      (progn
        (urb:bb-log "  guia/toperol sin resultado: se conserva el acabado de losetas")
        (prompt
          (strcat "\nATENCION: la franja tactil (guia/toperol) no se pudo generar en"
                  " este anden; se crea con sus losetas. Revise la guia y el toperol de este tramo.")))))
  ;; La guia no puede ocultar el fallo del toperol con un count > 0.
  ;; Verificar entidades reales antes del empaquetado, no solo un T del generador.
  (if (and result (urb:yes-p toperol))
    (progn
      (setq top-count (urb:count-toperol-symbols
        (urb:generated-objects (vla-get-Handle obj))))
      (prompt (strcat "\nTOPEROL: " (itoa top-count) " domos generados."))
      ;; 5.6.7 (reporte del usuario con foto: "no me dejo crear el anden",
      ;; contorno dibujado rodeando contenedores de raices): antes 0 domos
      ;; RECHAZABA todo el acabado y el anden no se creaba. Ahora el anden
      ;; se crea SIN toperol, se avisa en voz alta y se guarda el caso
      ;; completo (contorno + contenedores/prefabricados cercanos) para
      ;; reproducirlo exacto. No se reprodujo con geometrias de prueba.
      (if (= top-count 0)
        (progn
          (urb:bb-log "  TOPEROL: fallo de construccion tactil; espacio no diagnosticado")
          (vl-catch-all-apply 'urb:toperol-fallo-registrar (list ename))
          (prompt
            (strcat
              "\nATENCION: fallo la generacion del toperol. Esto no demuestra falta"
              " de espacio; revise el diagnostico geometrico. El anden queda SIN toperol."
              "\nSe guardo el caso en " (getenv "TEMP")
              "\\urbcant_toperol_fallo.txt -- envielo para corregirlo."))))))
  ;; Si el acabado no pudo construirse, el contorno de trabajo se devuelve
  ;; a su elevacion original para que el usuario pueda repararlo o reintentar.
  (if (and flattened (not result)
           (urb:valid-vla-object-p obj))
    (vla-put-Elevation obj elevation))
  result
)

(defun urb:discard-unpacked-anden (ename / obj item)
  ;; No dejar un acabado suelto tras un fallo; conservar el contorno editable.
  (if (setq obj (urb:as-vla-object ename))
    (foreach item (urb:generated-objects (vla-get-Handle obj))
      (urb:safe-delete item)))
  nil)

(defun urb:add-invisible-attribute
  (block point tag prompt-text value / attribute)
  (setq tag (urb:safe-string tag "DATO"))
  (setq prompt-text (urb:safe-string prompt-text tag))
  (setq value (urb:safe-string value ""))
  (setq attribute
    (vla-AddAttribute
      block
      0.20
      1
      prompt-text
      (vlax-3d-point point)
      tag
      value))
  attribute
)

(defun urb:block-attribute-values (block-ref / values attribute obj has-attributes)
  (setq obj (urb:as-vla-object block-ref))
  (if obj
    (setq has-attributes
      (vl-catch-all-apply 'vla-get-HasAttributes (list obj))))
  (if (and has-attributes
           (not (vl-catch-all-error-p has-attributes))
           (= has-attributes :vlax-true))
    (foreach attribute (vlax-invoke obj 'GetAttributes)
      (setq values
        (cons
          (cons
            (strcase (vla-get-TagString attribute))
            (vla-get-TextString attribute))
          values))))
  values
)

(defun urb:set-block-attribute
  (block-ref tag value / attribute obj has-attributes attributes)
  (setq tag (urb:safe-string tag ""))
  (setq value (urb:safe-string value ""))
  (setq obj (urb:as-vla-object block-ref))
  (if obj
    (setq has-attributes
      (vl-catch-all-apply 'vla-get-HasAttributes (list obj))))
  (if (and has-attributes
           (not (vl-catch-all-error-p has-attributes))
           (= has-attributes :vlax-true))
    (progn
      (setq attributes
        (vl-catch-all-apply 'vlax-invoke (list obj 'GetAttributes)))
      (if (not (vl-catch-all-error-p attributes))
        (foreach attribute attributes
          (if (= (strcase (vla-get-TagString attribute))
                 (strcase tag))
            (progn
              (vla-put-TextString attribute value)
              (vla-Update attribute)))))))
  value
)

(defun urb:block-object-list (block / objects item)
  (vlax-for item block
    (if (= (vla-get-ObjectName item) "AcDbEntity")
      (setq objects (cons item objects))
      (if (vlax-property-available-p item 'Layer)
        (setq objects (cons item objects)))))
  (reverse objects)
)

(defun urb:sortents-table (owner / dictionary table)
  (setq dictionary (vla-GetExtensionDictionary owner))
  (setq table
    (vl-catch-all-apply
      'vla-GetObject
      (list dictionary "ACAD_SORTENTS")))
  (if (vl-catch-all-error-p table)
    (setq table
      (vla-AddObject
        dictionary "ACAD_SORTENTS" "AcDbSortentsTable")))
  table
)

;; Clasifica el rol xdata (ver urb:tag-generated-role) en grupos de
;; grupos de orden de dibujo. No depende de en que capa quedo la pieza,
;; asi que las capas se pueden consolidar sin romper el apilamiento.
(defun urb:draw-role-bucket (role)
  (cond
    ((member role '("FILL" "RELLENO")) "FILL")
    ((= role "JOINT") "JOINT")
    ((= role "FEATURE_FILL") "FEATURE_FILL")
    ;; Los domos/capsulas se separan de las juntas y bordes tactiles para
    ;; moverlos al tope en una operacion final y determinista.
    ((= role "FEATURE_SYMBOL") "FEATURE_SYMBOL")
    ((member role '("FEATURE" "INTERIOR" "EXTERIOR" "REMATE")) "FEATURE")
    (T "BOUNDARY"))
)

(defun urb:set-block-draw-order
  (block objects / fills joints feature-fills features feature-symbols
   boundaries item table result bucket)
  (foreach item objects
    (if (vlax-property-available-p item 'Layer)
      (progn
        (setq bucket (urb:draw-role-bucket (urb:generated-role item)))
        (cond
          ((= bucket "FILL") (setq fills (cons item fills)))
          ((= bucket "JOINT") (setq joints (cons item joints)))
          ((= bucket "FEATURE_FILL")
            (setq feature-fills (cons item feature-fills)))
          ((= bucket "FEATURE") (setq features (cons item features)))
          ((= bucket "FEATURE_SYMBOL")
            (setq feature-symbols (cons item feature-symbols)))
          ((= bucket "BOUNDARY")
            (setq boundaries (cons item boundaries))))))
  )
  (setq table (urb:sortents-table block))
  (if fills
    (vl-catch-all-apply
      'vla-MoveToBottom
      (list table (urb:object-array-variant fills))))
  (if boundaries
    (vl-catch-all-apply
      'vla-MoveToTop
      (list table (urb:object-array-variant boundaries))))
  (if joints
    (setq result
      (vl-catch-all-apply
        'vla-MoveToTop
        (list table (urb:object-array-variant joints)))))
  (if feature-fills
    (vl-catch-all-apply
      'vla-MoveToTop
      (list table (urb:object-array-variant feature-fills))))
  (if features
    (setq result
      (vl-catch-all-apply
        'vla-MoveToTop
        (list table (urb:object-array-variant features)))))
  ;; Ultimo movimiento: el patron material y la trama tactil nunca pueden
  ;; tapar los simbolos de toperol/guia.
  (if feature-symbols
    (setq result
      (vl-catch-all-apply
        'vla-MoveToTop
        (list table (urb:object-array-variant feature-symbols)))))
  (or (and (null joints) (null feature-fills) (null features)
           (null feature-symbols))
      (not (vl-catch-all-error-p result)))
)

(defun urb:repair-block-ref-order (block-ref / block-name block result)
  (setq block-name
    (vl-catch-all-apply 'vla-get-Name (list block-ref)))
  (if (vl-catch-all-error-p block-name)
    nil
    (progn
      (setq block
        (vl-catch-all-apply
          'vla-Item
          (list (vla-get-Blocks (urb:doc)) block-name)))
      (if (vl-catch-all-error-p block)
        nil
        (progn
          (setq result
            (vl-catch-all-apply
              'urb:set-block-draw-order
              (list block (urb:block-object-list block))))
          (not (vl-catch-all-error-p result))))))
)

(defun urb:attribute-alist-value (attributes tag default / item)
  (setq item (assoc (strcase tag) attributes))
  (urb:safe-string (if item (cdr item) nil) default)
)

;; Reconstruye el registro minimo desde los atributos cuando un bloque
;; antiguo conserva sus propiedades pero perdio XDATA al copiarse entre DWG.
(defun urb:anden-block-data (ename / data obj attributes)
  (setq data (urb:get-xdata-strings ename "URB_ANDEN_BLOCK"))
  (if data
    data
    (progn
      (setq obj (vlax-ename->vla-object ename))
      (setq attributes (urb:block-attribute-values obj))
      (list "ANDEN"
        (urb:attribute-alist-value attributes "MATERIAL" "LOSETA")
        (urb:attribute-alist-value attributes "ETAPA" "1")
        (urb:attribute-alist-value attributes "SUBETAPA" "1")
        (urb:attribute-alist-value attributes "AREA_M2" "0")
        (urb:attribute-alist-value attributes "PERIMETRO_M" "0")
        "0"
        (urb:attribute-alist-value attributes "LOSETA_GUIA" "No")
        (urb:attribute-alist-value attributes "LOSETA_TOPEROL" "No")
        (urb:attribute-alist-value attributes "FORMATO_LOSETA" "40 x 40 cm")
        "Si"
        (urb:attribute-alist-value attributes "ANDEN_SUPERFICIE" "SUP_TN")
        (urb:attribute-alist-value attributes "ANDEN_RASANTE" "Via creada")
        (urb:attribute-alist-value attributes "LOSETA_LISA_M2" "0")
        (urb:attribute-alist-value attributes "LOSETA_LISA_UND" "0")
        (urb:attribute-alist-value attributes "LOSETA_GUIA_ML" "0")
        (urb:attribute-alist-value attributes "LOSETA_TOPEROL_ML" "0")
        (urb:attribute-alist-value attributes "ADOQUIN_20X10_M2" "0")
        (urb:attribute-alist-value attributes "ADOQUIN_20X10_UND" "0")
        (urb:attribute-alist-value attributes "ANDEN_ELEVACION" "0")
        (urb:attribute-alist-value
          attributes "ANDEN_SENTIDO" "AUTOMATICO"))))
)

(defun urb:anden-block-p (ename / obj data layer name)
  (setq obj
    (vl-catch-all-apply
      'vlax-ename->vla-object
      (list ename)))
  (and
    (not (vl-catch-all-error-p obj))
    (= (vla-get-ObjectName obj) "AcDbBlockReference")
    (or
      (and
        (setq data (urb:get-xdata-strings ename "URB_ANDEN_BLOCK"))
        (urb:string-equal-p (car data) "ANDEN"))
      (progn
        (setq layer (strcase (urb:safe-string (vla-get-Layer obj) "")))
        (setq name (strcase (urb:safe-string (vla-get-Name obj) "")))
        (or (= layer "URB-ANDEN-BLOQUE") (= layer "URB-ANDEN")
            (urb:starts-with name "URB_ANDEN_")))))
)

(defun urb:clean-selector-layer (/ ss index obj deleted)
  (setq deleted 0)
  (if (setq ss
        (ssget "_X"
          '((0 . "HATCH") (8 . "URB-SEL-ANDEN"))))
    (progn
      (setq index 0)
      (repeat (sslength ss)
        (setq obj
          (vlax-ename->vla-object (ssname ss index)))
        (if (urb:safe-delete obj)
          (setq deleted (1+ deleted)))
        (setq index (1+ index)))))
  deleted
)

;; area REAL del anden: el contorno menos las huellas de prefabricados y
;; contenedores (lo que de verdad queda dibujado). Si las regiones no se
;; pueden construir devuelve el area bruta, sin castigar la creacion.
(defun urb:anden-area-neta (ename bruta / copy region neta)
  (setq copy
    (vl-catch-all-apply '(lambda () (vla-Copy (urb:as-vla-object ename)))))
  (setq region
    (if (not (vl-catch-all-error-p copy))
      (vl-catch-all-apply '(lambda () (urb:anden-region-from-object copy)))))
  (if (and copy (not (vl-catch-all-error-p copy))) (urb:safe-delete copy))
  (if (or (null region) (vl-catch-all-error-p region))
    bruta
    (progn
      (setq region (urb:apply-anden-cutouts region))
      (setq neta (vl-catch-all-apply '(lambda () (vla-get-Area region))))
      (urb:safe-delete region)
      (if (and (numberp neta) (> neta 1e-6)) neta bruta)))
)

;;; ---------------------------------------------------------------------
;;; Recorte fisico del CONTORNO del anden. 2026-09-08, pedido del usuario:
;;; "solo el bloque del anden tiene que estar entre los prefabricados".
;;; Hasta v4.77 solo se recortaba el ACABADO (losetas, juntas, tactiles) y
;;; el area; la polilinea del contorno seguia pasando por DEBAJO del
;;; bordillo y del contenedor, asi que al seleccionar el bloque sus
;;; limites no coincidian con lo que se ve. Ahora la propia polilinea se
;;; sustituye por el borde real. Se hace con entmod y no con entmake para
;;; conservar el HANDLE: de el cuelgan la xdata del anden, las piezas ya
;;; generadas y el vinculo con los costados.
;;; ---------------------------------------------------------------------

;; (p-inicio p-fin bulge) de una recta o un arco ya explotados. Devuelve
;; nil para cualquier otra curva (elipse, spline) o si el arco es un
;; circulo completo: ante lo que no sabe reconstruir prefiere no tocar el
;; contorno antes que deformarlo.
(defun urb:curve-as-segment (obj / name p1 p2 a1 a2 delta)
  (setq name (vl-catch-all-apply 'vla-get-ObjectName (list obj)))
  (if (not (member name '("AcDbLine" "AcDbArc")))
    nil
    (progn
      (setq p1 (vl-catch-all-apply
                 '(lambda ()
                    (vlax-safearray->list
                      (vlax-variant-value (vla-get-StartPoint obj))))))
      (setq p2 (vl-catch-all-apply
                 '(lambda ()
                    (vlax-safearray->list
                      (vlax-variant-value (vla-get-EndPoint obj))))))
      (cond
        ((or (vl-catch-all-error-p p1) (vl-catch-all-error-p p2)) nil)
        ((= name "AcDbLine") (list p1 p2 0.0))
        (T
          (setq a1 (vl-catch-all-apply 'vla-get-StartAngle (list obj))
                a2 (vl-catch-all-apply 'vla-get-EndAngle (list obj)))
          (if (or (not (numberp a1)) (not (numberp a2)))
            nil
            (progn
              (setq delta (- a2 a1))
              (while (<= delta 1e-12) (setq delta (+ delta (* 2.0 pi))))
              (if (> delta (- (* 2.0 pi) 1e-9))
                nil
                (list p1 p2
                  (/ (sin (/ delta 4.0)) (cos (/ delta 4.0))))))))))))

;; 2026-09-10. Recorte que puede PARTIR el elemento en varios pedazos: un
;; paso peatonal que cruza de lado a lado una zona verde la deja en DOS.
;; urb:anden-clip-contour solo sabe reescribir UN contorno (se queda con el
;; bucle mayor), asi que para esos casos hace falta la lista completa.
;; Devuelve una lista de listas de puntos (un contorno por pedazo), o nil
;; si no hubo recorte o no se pudo reconstruir con garantias.
(defun urb:clip-poly-loops (ename minimo / obj copy region area0 area1 loops out a)
  (setq obj (urb:as-vla-object ename))
  (setq copy (vl-catch-all-apply '(lambda () (vla-Copy obj))))
  (setq region
    (if (not (vl-catch-all-error-p copy))
      (vl-catch-all-apply '(lambda () (urb:add-region-from-object copy)))))
  (if (and copy (not (vl-catch-all-error-p copy))) (urb:safe-delete copy))
  (if (or (null region) (vl-catch-all-error-p region))
    nil
    (progn
      (setq area0 (vl-catch-all-apply 'vla-get-Area (list region)))
      (setq region (urb:apply-anden-cutouts region))
      (setq area1 (vl-catch-all-apply 'vla-get-Area (list region)))
      (if (or (not (numberp area0)) (not (numberp area1))
              (>= area1 (- area0 1e-6)))
        (progn (urb:safe-delete region) nil)
        (progn
          (setq loops (urb:region-loops region))
          (urb:safe-delete region)
          ;; 2026-09-10 v2 (reporte del usuario: "la zona verde cortada la
          ;; deformo con respecto a la original"): NO se puede devolver
          ;; solo los puntos. Cada vertice trae su bulge y sin el los arcos
          ;; del contorno original se vuelven cuerdas rectas -- que es
          ;; exactamente la deformacion que se vio en la zona verde de un
          ;; borde curvo. Se devuelve el bucle completo (punto . bulge).
          (foreach l loops
            (setq a (abs (urb:loop-signed-area l)))
            (if (> a (if minimo minimo 0.01))
              (setq out (cons l out))))
          (reverse out))))))

;; saca del grupo el primer segmento que continua en "cur". Devuelve
;; (hit . resto) donde hit = (punto-siguiente bulge-en-ese-sentido) o nil.
(defun urb:chain-take-next (pool cur tol / rest hit)
  (setq rest nil hit nil)
  (foreach s pool
    (cond
      (hit (setq rest (cons s rest)))
      ((<= (distance (car s) cur) tol)
        (setq hit (list (cadr s) (caddr s))))
      ((<= (distance (cadr s) cur) tol)
        (setq hit (list (car s) (- (caddr s)))))
      (T (setq rest (cons s rest)))))
  (cons hit (reverse rest)))

;; encadena segmentos (p1 p2 bulge) sueltos en bucles cerrados. Cada
;; bucle sale como lista de (punto . bulge) lista para volcarse en una
;; LWPOLYLINE (grupo 10 + grupo 42). Funcion pura: se autoprueba sin
;; dibujo abierto.
(defun urb:chain-loops-from-segments
  (segs tol / pool seg loop start cur take hit loops guard)
  (setq pool segs loops nil)
  (while pool
    (setq seg (car pool) pool (cdr pool))
    (setq loop (list (cons (car seg) (caddr seg)))
          start (car seg)
          cur (cadr seg)
          guard (1+ (length pool))
          hit T)
    (while (and hit (> (distance cur start) tol) (> guard 0))
      (setq guard (1- guard))
      (setq take (urb:chain-take-next pool cur tol))
      (setq hit (car take) pool (cdr take))
      (if hit
        (setq loop (cons (cons cur (cadr hit)) loop)
              cur (car hit))))
    (if (and (<= (distance cur start) tol) (>= (length loop) 3))
      (setq loops (cons (reverse loop) loops))))
  (reverse loops))

;; area con signo (formula del zapatero) ignorando los bulges: sirve para
;; escoger el bucle mayor y el sentido, no para medir.
(defun urb:loop-signed-area (loop / pts n i a p q)
  (setq pts (mapcar 'car loop) n (length pts) i 0 a 0.0)
  (while (< i n)
    (setq p (nth i pts) q (nth (rem (1+ i) n) pts))
    (setq a (+ a (- (* (car p) (cadr q)) (* (car q) (cadr p)))))
    (setq i (1+ i)))
  (* 0.5 a))

;; invierte un bucle conservando los arcos: al recorrer al reves, el
;; bulge de cada tramo cambia de signo y se corre un vertice.
(defun urb:loop-reverse (loop / pts bs n i out)
  (setq pts (mapcar 'car loop) bs (mapcar 'cdr loop)
        n (length loop) i 0 out nil)
  (while (< i n)
    (setq out
      (cons
        (cons (nth (- n 1 i) pts)
              (- (nth (rem (+ (- n 2 i) n) n) bs)))
        out))
    (setq i (1+ i)))
  (reverse out))

;; bucles cerrados de una REGION ya construida. nil si aparece una curva
;; que no sabemos volcar a polilinea.
(defun urb:region-polygons (region / loops loop chain poly out)
  ;; Reencadenar aristas antes de ray casting. VLA-Explode no garantiza
  ;; orden ni orientacion; cada bucle se muestrea por separado (agujeros).
  (setq loops (urb:region-loops region))
  (foreach loop loops
    (setq chain (mapcar '(lambda (v) (list (caar v) (cadar v) (cdr v))) loop))
    (setq poly (urb:poly-chain-polyline (append chain (list (car chain)))))
    (if poly
      (progn
        (setq out (cons (urb:lwpoly-points-with-arcs-fine poly) out))
        (entdel poly))))
  out)

(defun urb:pip-index-build (loops / low high n loop p prev xi yi xj yj
                          bins step rows i j edge row edges)
  ;; Indice por bandas Y de las MISMAS aristas del poligono muestreado.
  ;; No simplifica curvas ni cambia tolerancias: evita recorrer aristas
  ;; que no pueden cruzar el rayo horizontal del punto consultado.
  (setq n 0)
  (foreach loop loops
    (foreach p loop
      (setq low (if low (min low (cadr p)) (cadr p))
            high (if high (max high (cadr p)) (cadr p)) n (1+ n))))
  (if (and low high (> high low) (> n 32))
    (progn
      (setq bins (min 128 (max 8 (fix (sqrt n))))
            step (/ (- high low) bins) rows nil i 0)
      (repeat bins (setq rows (cons (list i) rows) i (1+ i)))
      (foreach loop loops
        (setq prev (last loop))
        (foreach p loop
          (setq xi (car p) yi (cadr p) xj (car prev) yj (cadr prev))
          (if (/= yi yj)
            (progn
              (setq edge (list xi yi xj yj)
                    i (max 0 (min (1- bins) (fix (/ (- (min yi yj) low) step))))
                    j (max 0 (min (1- bins) (fix (/ (- (max yi yj) low) step)))))
              (while (<= i j)
                (setq row (assoc i rows)
                      rows (subst (cons i (cons edge (cdr row))) row rows)
                      i (1+ i)))))
          (setq prev p)))
      (list low high step bins rows))))

(defun urb:pip-index-contains-p (pt index / x y row edge xi yi xj yj inside)
  (setq x (car pt) y (cadr pt))
  (if (and (>= y (car index)) (<= y (cadr index)))
    (progn
      (setq row (max 0 (min (1- (nth 3 index))
        (fix (/ (- y (car index)) (nth 2 index))))))
      (foreach edge (cdr (assoc row (nth 4 index)))
        (setq xi (car edge) yi (cadr edge) xj (caddr edge) yj (cadddr edge))
        ;; Misma expresion y semantica de borde de point-in-poly-2d.
        (if (and (/= (> yi y) (> yj y))
                 (< x (+ xi (/ (* (- xj xi) (- y yi)) (- yj yi)))))
          (setq inside (not inside))))))
  inside)

(defun urb:point-in-region-polygons-p (point loops / inside loop)
  ;; Paridad: dentro de contorno exterior pero fuera de todos sus huecos.
  ;; Cache solo durante la creacion de UNA franja. Variables ligadas
  ;; localmente por los dos generadores: no persiste entre DWG/ediciones.
  (if *urb-pip-index-enabled*
    (progn
      (if (not (eq loops *urb-pip-source*))
        (setq *urb-pip-source* loops *urb-pip-index* (urb:pip-index-build loops)))
      (if *urb-pip-index*
        (setq inside (urb:pip-index-contains-p point *urb-pip-index*))
        (foreach loop loops
          (if (urb:point-in-poly-2d point loop) (setq inside (not inside))))))
    (foreach loop loops
      (if (urb:point-in-poly-2d point loop) (setq inside (not inside)))))
  inside)

(defun urb:region-align-elevation (cutter base / a b za zb)
  (setq a (urb:object-box-points cutter) b (urb:object-box-points base)
        za (if a (caddr (car a)) 0.0) zb (if b (caddr (car b)) 0.0))
  (if (not (equal za zb 1e-8))
    (vla-Move cutter (vlax-3d-point (list 0.0 0.0 za))
                     (vlax-3d-point (list 0.0 0.0 zb))))
  cutter)

(defun urb:region-loops (region / exploded items segs seg falla o sub sueltos)
  (setq exploded (vl-catch-all-apply 'vla-Explode (list region)))
  (if (vl-catch-all-error-p exploded)
    nil
    (progn
      (setq items (urb:variant-object-list exploded) segs nil falla nil sueltos nil)
      (foreach o items
        (cond
          ;; 2026-09-10 (medido en Civil real): una region con caras
          ;; SEPARADAS -- lo que deja un paso peatonal que cruza una zona
          ;; verde de lado a lado -- NO explota en curvas: explota primero
          ;; en dos REGIONES. Sin entrar en ellas, urb:region-loops daba
          ;; nil y el recorte se perdia entero.
          ((= (vla-get-ObjectName o) "AcDbRegion")
            (setq sub (urb:region-loops o))
            (if sub
              (setq sueltos (append sueltos sub))
              (setq falla T)))
          (T
            (setq seg (urb:curve-as-segment o))
            (if seg (setq segs (cons seg segs)) (setq falla T)))))
      (foreach o items (urb:safe-delete o))
      (cond
        (falla nil)
        (segs (append sueltos
                (urb:chain-loops-from-segments (reverse segs) 1e-6)))
        (T sueltos)))))

;; sustituye el contorno del anden por su borde NETO (contorno menos
;; prefabricados y contenedores). Devuelve el area neta si recorto, nil si
;; no habia nada que recortar o si no pudo reconstruir el borde con
;; garantias -- en ese caso el contorno queda intacto y el recorte del
;; acabado (v4.76) sigue haciendo su trabajo.
(defun urb:anden-clip-contour
  (ename / obj copy region area0 area1 loops best best-a a
   verts ed head xd flag n res)
  (setq obj (urb:as-vla-object ename))
  (setq copy (vl-catch-all-apply '(lambda () (vla-Copy obj))))
  (setq region
    (if (not (vl-catch-all-error-p copy))
      (vl-catch-all-apply '(lambda () (urb:anden-region-from-object copy)))))
  (if (and copy (not (vl-catch-all-error-p copy))) (urb:safe-delete copy))
  (if (or (null region) (vl-catch-all-error-p region))
    nil
    (progn
      (setq area0 (vl-catch-all-apply 'vla-get-Area (list region)))
      (setq region (urb:apply-anden-cutouts region))
      (setq area1 (vl-catch-all-apply 'vla-get-Area (list region)))
      (if (or (not (numberp area0)) (not (numberp area1))
              (>= area1 (- area0 1e-6)))
        (progn (urb:safe-delete region) nil)
        (progn
          (setq loops (urb:region-loops region))
          (urb:safe-delete region)
          (setq best nil best-a 0.0)
          (foreach l loops
            (setq a (abs (urb:loop-signed-area l)))
            (if (> a best-a) (setq best l best-a a)))
          ;; Una polilinea no representa islas separadas ni agujeros. Nunca
          ;; descartar una isla por escoger solo el bucle mayor.
          (if (or (null best) (< (length best) 3) (< best-a 1e-6)
                  (> (length loops) 1))
            nil
            (progn
              (if (< (urb:loop-signed-area best) 0.0)
                (setq best (urb:loop-reverse best)))
              (setq verts nil)
              (foreach v best
                (setq verts
                  (cons (cons 42 (cdr v))
                    (cons (cons 10 (list (car (car v)) (cadr (car v))))
                      verts))))
              (setq verts (reverse verts))
              (setq ed (entget ename))
              (setq xd (assoc -3 ed))
              (setq flag (cdr (assoc 70 ed)))
              (setq flag (if flag (boole 7 flag 1) 1))
              (setq head
                (vl-remove-if
                  '(lambda (x) (member (car x) '(10 40 41 42 70 90 -3)))
                  ed))
              (setq n (length best))
              (setq res
                (vl-catch-all-apply 'entmod
                  (list
                    (append head
                      (list (cons 90 n) (cons 70 flag))
                      verts
                      (if xd (list xd))))))
              (if (vl-catch-all-error-p res)
                nil
                (progn (entupd ename) best-a)))))))))

(defun urb:anden-offset-safe (en width / result n i j b a z chord radius theta count points poly attempt)
  ;; Primero OFFSET exacto. Algunos costados ACIS con muchos microarcos
  ;; fallan aun siendo validos: respaldo SOLO para el contorno de tierras.
  ;; Flecha de cada cuerda <= 0.000001 m, calculada por radio/angulo;
  ;; no usar el muestreo visual (aprox. 1 m) para medir cantidades.
  (setq result (urb:offset-poly en width))
  (if (null result)
    (progn
      (setq attempt
        (vl-catch-all-apply
          '(lambda ()
             (setq i 0 n (fix (vlax-curve-getEndParam en)))
             (repeat n
               (setq a (vlax-curve-getPointAtParam en i)
                     z (vlax-curve-getPointAtParam en (1+ i))
                     b (abs (vla-GetBulge (vlax-ename->vla-object en) i))
                     count 1)
               (if (> b 1e-12)
                 (progn
                   (setq chord (distance a z)
                         radius (/ (* chord (+ 1.0 (* b b))) (* 4.0 b))
                         theta (* 4.0 (atan b))
                         count (max 1 (1+ (fix (* theta (sqrt (/ radius 0.000008)))))))))
               (if (> (+ (length points) count) 100000)
                 (vl-exit-with-error "ANDEN: arco fuera del limite de calculo seguro del sobreancho."))
               (setq j 0)
               (repeat count
                 (setq points
                   (cons (vlax-curve-getPointAtParam en (+ i (/ (float j) count))) points)
                   j (1+ j)))
               (setq i (1+ i)))
             (setq points (reverse (cons (vlax-curve-getEndPoint en) points))
                   poly (urb:open-poly-from-points points 0.0))
             (urb:offset-poly poly width))))
      (if poly (urb:safe-delete (vlax-ename->vla-object poly)))
      (if (not (vl-catch-all-error-p attempt)) (setq result attempt))))
  ;; 5.6.2: ultimo respaldo en LISP. Medido en el anden curvo DD2CA: el
  ;; costado de 247 vertices (0.25 m + microarcos) hace que OFFSET nativo
  ;; falle o se parta en piezas, y el anden recortado perdia el sobreancho.
  (if (null result)
    (progn
      (setq attempt (vl-catch-all-apply 'urb:offset-open-poly-manual (list en width)))
      (if (not (vl-catch-all-error-p attempt)) (setq result attempt))))
  result)

;; desfase de una polilinea ABIERTA calculado vertice a vertice: arcos
;; densificados (cuerda de <= 2 grados), vertices repetidos fuera, cada
;; vertice movido 'width' por la normal promedio. Signo IGUAL a vla-Offset (medido en
;; DD2CA: positivo = derecha del sentido de la polilinea).
;; Sin factor de inglete: ningun punto queda a mas de 'width' del costado
;; (lo exige urb:anden-overwidth-bounded-p).
(defun urb:offset-open-poly-manual (en width / obj end i j b count theta raw pts lastp
                                    out prev next n1 n2 nx ny len p q)
  (setq obj (vlax-ename->vla-object en)
        end (fix (+ 0.5 (vlax-curve-getEndParam en))) i 0)
  (while (< i end)
    (setq b (abs (vla-GetBulge obj i)) count 1)
    (if (> b 1e-9)
      (setq theta (* 4.0 (atan b))
            count (max 1 (fix (+ 1.0 (/ theta (/ pi 90.0)))))))
    (setq j 0)
    (repeat count
      (setq raw (cons (vlax-curve-getPointAtParam en (+ i (/ (float j) count))) raw) j (1+ j)))
    (setq i (1+ i)))
  (setq raw (reverse (cons (vlax-curve-getEndPoint en) raw)))
  (foreach p raw
    (if (or (null lastp) (> (distance (list (car p) (cadr p)) (list (car lastp) (cadr lastp))) 0.001))
      (setq pts (cons p pts) lastp p)))
  (setq pts (reverse pts))
  (if (< (length pts) 2)
    nil
    (progn
      (setq prev nil)
      (while pts
        (setq p (car pts) next (cadr pts) n1 nil n2 nil)
        (if prev
          (setq len (distance (list (car prev) (cadr prev)) (list (car p) (cadr p)))
                n1 (list (/ (- (cadr prev) (cadr p)) len) (/ (- (car p) (car prev)) len))))
        (if next
          (setq len (distance (list (car p) (cadr p)) (list (car next) (cadr next)))
                n2 (list (/ (- (cadr p) (cadr next)) len) (/ (- (car next) (car p)) len))))
        (cond
          ((and n1 n2)
            (setq nx (+ (car n1) (car n2)) ny (+ (cadr n1) (cadr n2))
                  len (sqrt (+ (* nx nx) (* ny ny))))
            (if (< len 1e-9) (setq nx (car n2) ny (cadr n2)) (setq nx (/ nx len) ny (/ ny len))))
          (n1 (setq nx (car n1) ny (cadr n1)))
          (T (setq nx (car n2) ny (cadr n2))))
        (setq out (cons (list (- (car p) (* width nx)) (- (cadr p) (* width ny))) out)
              prev p pts (cdr pts)))
      (urb:open-poly-from-points (reverse out) 0.0))))

(defun urb:anden-overwidth-bounded-p (source result width / i n p near valid)
  ;; Control independiente del area/cruces: un miter puede no cruzarse y
  ;; aun asi extenderse cientos de metros. Revisar vertices y puntos medios
  ;; exactos del resultado contra el contorno original (tolerancia 0.1 mm).
  (setq i 0 n (* 2 (fix (vlax-curve-getEndParam result))) valid T)
  (while (and valid (< i n))
    (setq p (vlax-curve-getPointAtParam result (* 0.5 i))
          near (if p (vlax-curve-getClosestPointTo source p)))
    (if (or (null near) (> (distance p near) (+ (abs width) 0.0001)))
      (setq valid nil))
    (setq i (1+ i)))
  valid)

(defun urb:anden-overwidth-contour (ename width / gap result)
  ;; SOLO tierras: union circular de radio = sobreancho, sin prolongar
  ;; aristas a un vertice lejano. Acabados/prefabricados no se modifican.
  ;; OFFSET ActiveX respeta OFFSETGAPTYPE; restaurarlo incluso ante error.
  (setq gap (getvar "OFFSETGAPTYPE"))
  (setvar "OFFSETGAPTYPE" 1)
  (setq result (vl-catch-all-apply 'urb:anden-overwidth-contour-raw (list ename width)))
  (setvar "OFFSETGAPTYPE" gap)
  (if (vl-catch-all-error-p result)
    (progn (prompt (strcat "\nANDEN: error de sobreancho: " (vl-catch-all-error-message result))) nil)
    result))

(defun urb:anden-overwidth-contour-raw (ename width / chains chain pl off a b polygon pts mid normal test sign all result check)
  ;; Dos costados desplazados; las tapas solo unen sus extremos, sin
  ;; prolongar longitudinalmente el anden. Conservar bulges verdaderos.
  (setq chains (urb:poly-costado-chains ename)
        polygon (urb:lwpoly-points-with-arcs-fine ename))
  (foreach chain chains
    (setq pl (urb:poly-chain-polyline chain))
    (setq mid (* 0.5 (urb:curve-length pl))
          pts (urb:curve-pt pl mid) normal (+ (urb:curve-tangent pl mid) (* 0.5 pi))
          test (polar pts normal 0.05))
    ;; vla-Offset no tiene signo universal por normal: comprobar ambos.
    (setq off (urb:anden-offset-safe pl width))
    (if off
      (progn
        (setq test (urb:curve-pt off (* 0.5 (urb:curve-length off))))
        (if (urb:point-in-poly-p test polygon)
          (progn (entdel off) (setq off (urb:anden-offset-safe pl (- width)))))))
    (if off
      (progn
        (setq pts (urb:lwpoly-vertex-bulges off) a (car pts) b (cadr pts))
        (setq all (append all (mapcar '(lambda (p q) (list (car p) (cadr p) q)) a b)))
        (entdel off))
      (setq check T))
    (entdel pl))
  (if (and (= (length chains) 2) (not check) (> (length all) 3))
    (progn
      (setq result (urb:poly-chain-polyline all))
      (vla-put-Closed (vlax-ename->vla-object result) :vlax-true)
      (if (or (<= (vla-get-Area (vlax-ename->vla-object result))
                  (vla-get-Area (vlax-ename->vla-object ename)))
              (urb:polygon-self-intersects-p (urb:lwpoly-points-with-arcs result))
              (not (urb:anden-overwidth-bounded-p ename result width)))
        (progn (entdel result) (setq result nil))
        result)))
  ;; 5.6.2: respaldo cuando la eleccion de lado por punto medio falla
  ;; (DD2CA: ambos lados del costado denso daban "dentro" y la union quedaba
  ;; con un costado hacia adentro, area 677.99 < 679.54).
  (if (and (null result) (= (length chains) 2))
    (setq result (urb:anden-overwidth-combos ename chains width)))
  result)

;; Ambos desfases de cada costado y las 4 combinaciones, de mayor a menor
;; area; gana la primera valida (area > base, sin cruces, acotada).
;; Los 2 segmentos que CIERRAN las puntas unen los costados desplazados: en
;; una punta oblicua su punto medio queda legitimamente a mas de 'width'
;; (F20E5: 1.42 m); de esos dos se revisan los extremos, no el punto medio.
(defun urb:anden-overwidth-combos (ename chains width / cands chain pl off pts c1 c2 combos c s
                                   poly area base best)
  (foreach chain chains
    (setq pl (urb:poly-chain-polyline chain) c1 nil)
    (foreach s (list width (- width))
      (setq off (urb:anden-offset-safe pl s))
      (if off
        (progn
          (setq pts (urb:lwpoly-vertex-bulges off))
          (setq c1 (cons (mapcar '(lambda (p q) (list (car p) (cadr p) q)) (car pts) (cadr pts)) c1))
          (entdel off))))
    (entdel pl)
    (setq cands (append cands (list c1))))
  (setq base (vla-get-Area (vlax-ename->vla-object ename)))
  (if (and (car cands) (cadr cands))
    (progn
      (foreach c1 (car cands)
        (foreach c2 (cadr cands)
          (setq poly (urb:poly-chain-polyline (append c1 c2)))
          (vla-put-Closed (vlax-ename->vla-object poly) :vlax-true)
          (setq area (vla-get-Area (vlax-ename->vla-object poly)))
          (if (> area base)
            (setq combos (cons (list area poly (length c1) (length c2)) combos))
            (entdel poly))))
      (foreach c (vl-sort combos '(lambda (x y) (> (car x) (car y))))
        (if (and (null best)
                 (not (urb:polygon-self-intersects-p (urb:lwpoly-points-with-arcs (cadr c))))
                 (urb:anden-overwidth-bounded-skip-p ename (cadr c) width
                   (list (- (nth 2 c) 0.5) (- (+ (nth 2 c) (nth 3 c)) 0.5))))
          (setq best (cadr c))
          (entdel (cadr c))))
      best)))

(defun urb:anden-overwidth-bounded-skip-p (source result width skip / i n p near valid)
  (setq i 0 n (* 2 (fix (+ 0.5 (vlax-curve-getEndParam result)))) valid T)
  (while (and valid (< i n))
    (if (not (vl-some '(lambda (s) (equal s (* 0.5 i) 1e-6)) skip))
      (progn
        (setq p (vlax-curve-getPointAtParam result (* 0.5 i))
              near (if p (vlax-curve-getClosestPointTo source p)))
        (if (or (null near) (> (distance p near) (+ (abs width) 0.0001)))
          (setq valid nil))))
    (setq i (1+ i)))
  valid)

(defun urb:regions-union-copy (items / result item copy err pending next)
  ;; Unir por pares equilibrados: no reconstruir una region creciente por
  ;; cada banda (coste cuadratico en andenes largos). Solo tocar copias.
  (foreach item items
    (if (> (vla-get-Area item) 1e-8)
      (setq pending (cons (vla-Copy item) pending))))
  (while (cdr pending)
    (setq next nil)
    (while pending
      (setq result (car pending) copy (cadr pending) pending (cddr pending))
      (if copy
        (progn
          (setq err (vl-catch-all-apply 'vla-Boolean (list result 0 copy)))
          (urb:safe-delete copy)
          (if (vl-catch-all-error-p err)
            (progn
              (foreach item (append (list result) pending next) (urb:safe-delete item))
              (vl-exit-with-error "ANDEN: union de cantidades fallida.")))))
      (setq next (cons result next)))
    (setq pending (reverse next)))
  (car pending))

(defun urb:region-list-area (items / total value)
  ;; Sumar areas ya modeladas no invoca el kernel ACIS. Es deliberado:
  ;; vla-Boolean muestra el error 18003 en la linea de comandos cuando dos
  ;; regiones solo se tocan o son disjuntas, incluso si el error se captura.
  (setq total 0.0)
  (foreach item items
    (setq value (vl-catch-all-apply 'vla-get-Area (list item)))
    (if (numberp value) (setq total (+ total value))))
  total)

(defun urb:anden-measured-finish (ename area format / objects obj layer gray white guia top a b c d module total)
  ;; Medir las regiones realmente modeladas sin volver a ejecutar booleanos
  ;; auxiliares al final. Las franjas tactiles se superponen visualmente al
  ;; acabado principal; en ese caso la suma no cierra y se usa el calculo
  ;; contractual geometrico de urb:anden-finish-quantities. Asi se conserva
  ;; precision y se evita que una edicion correcta termine mostrando el
  ;; engañoso "Modeling Operation Error 18003" durante el empaquetado.
  (setq objects (urb:generated-objects (cdr (assoc 5 (entget ename)))))
  (foreach obj objects
    (if (and (= (vla-get-ObjectName obj) "AcDbRegion") (= (urb:generated-role obj) "FILL"))
      (progn
        (setq layer (vla-get-Layer obj))
        (cond ((wcmatch layer "*TOPEROL*") (setq top (cons obj top)))
              ((wcmatch layer "*GUIA*") (setq guia (cons obj guia)))
              ((wcmatch layer "*GRIS*,*40X40*") (setq gray (cons obj gray)))
              ((wcmatch layer "*BLANCO*") (setq white (cons obj white)))))))
  (if (or gray white)
    (progn
      (setq a (urb:region-list-area gray)
            b (urb:region-list-area white)
            c (urb:region-list-area guia)
            d (urb:region-list-area top)
            total (+ a b c d)
            module (urb:loseta-module format))
      ;; Solo aceptar la medicion directa si las caras forman una particion
      ;; exacta del contorno. Con tactiles superpuestos o solapes numericos,
      ;; devolver NIL activa el calculo geometrico existente y validado.
      (if (<= (abs (- area total)) (max 0.00001 (* area 0.000001)))
        (list a (urb:unit-count-ceiling a (* module module))
          (/ c module) (/ d module)
          b (urb:unit-count-ceiling b 0.02))
        nil))))

;; 2026-09-14 (reporte del usuario: "no quedan en bloque" + "se esta
;; demorando muchisimo tiempo"). Los dos sintomas son EL MISMO problema:
;; si el empaquetado nativo -BLOCK falla, el motor cae al camino COM que
;; tarda varios minutos, el usuario interrumpe y las piezas quedan sueltas.
;; La causa mas comun de que -BLOCK falle es que alguna de las capas
;; generadas este BLOQUEADA o CONGELADA -- el comando no puede meter esos
;; objetos en la definicion y no dice nada. Se destraban antes de llamarlo
;; y se restauran despues, pase lo que pase.
(defun urb:layers-of-selection (ss / i en capas capa)
  (setq i 0 capas nil)
  (repeat (sslength ss)
    (setq en (ssname ss i)
          capa (cdr (assoc 8 (entget en))))
    (if (and capa (not (member capa capas))) (setq capas (cons capa capas)))
    (setq i (1+ i)))
  capas)

(defun urb:layers-unlock (capas / estado capa obj)
  (setq estado nil)
  (foreach capa capas
    (setq obj (vl-catch-all-apply
      '(lambda () (vla-Item (vla-get-Layers (urb:doc)) capa))))
    (if (not (vl-catch-all-error-p obj))
      (progn
        (setq estado
          (cons (list capa
                  (vl-catch-all-apply '(lambda () (vlax-get-property obj 'Lock)))
                  (vl-catch-all-apply '(lambda () (vlax-get-property obj 'Freeze))))
                estado))
        (vl-catch-all-apply '(lambda () (vlax-put-property obj 'Lock :vlax-false)))
        ;; descongelar la capa ACTUAL lanza error en AutoCAD: va con catch
        (vl-catch-all-apply '(lambda () (vlax-put-property obj 'Freeze :vlax-false))))))
  estado)

(defun urb:layers-restore (estado / e obj)
  (foreach e estado
    (setq obj (vl-catch-all-apply
      '(lambda () (vla-Item (vla-get-Layers (urb:doc)) (car e)))))
    (if (not (vl-catch-all-error-p obj))
      (progn
        (if (not (vl-catch-all-error-p (cadr e)))
          (vl-catch-all-apply '(lambda () (vlax-put-property obj 'Lock (cadr e)))))
        (if (not (vl-catch-all-error-p (caddr e)))
          (vl-catch-all-apply '(lambda () (vlax-put-property obj 'Freeze (caddr e))))))))
  (princ))

;; cuantas de esas capas estaban trabadas (solo para el aviso)
(defun urb:layers-trabadas (estado / n e)
  (setq n 0)
  (foreach e estado
    (if (or (equal (cadr e) :vlax-true) (equal (caddr e) :vlax-true))
      (setq n (1+ n))))
  n)

(defun urb:ensure-anden-fast (/ check dll result)
  ;; Carga diferida: cada PC usa su bundle local, nunca una ruta de Drive ajena.
  (setq check (vl-catch-all-apply 'URBANDENFASTVERSION553 nil))
  (if (or (vl-catch-all-error-p check) (/= check 553))
    (progn
      (setq dll (strcat (getenv "APPDATA")
        "/Autodesk/ApplicationPlugins/UrbanismoCantidades.bundle/Contents/net/"
        (if (>= (atof (getvar "ACADVER")) 25.0)
          "UrbAndenFast2025_v553.dll" "UrbAndenFast2023_v553.dll")))
      (if (findfile dll)
        (setq result (vl-catch-all-apply 'vl-cmdf (list "_.NETLOAD" dll))))
      (setq check (vl-catch-all-apply 'URBANDENFASTVERSION553 nil))))
  (if (or (vl-catch-all-error-p check) (/= check 553))
    (vl-exit-with-error
      "ANDEN: falta el acelerador 5.5.3. Ejecute INSTALAR.bat en este PC y reinicie Civil 3D.")
    T))

(defun urb:package-anden
  (ename / boundary metadata material etapa subetapa guia toperol format
   calculate surface grade-source elevation pattern-mode area area-bruta
   perimeter points finish-qty
   quantity-pattern-angle
   handle objects filtered obj block-name blocks block-definition
   copy-result point block-ref insert-result block-ename xdata-result
   fast-ok ss en cmd-result old-attreq over-poly over-area measured-qty
   capas-estado trabadas razon t-pack side-data flat-result)
  ;; Verificar antes de que -BLOCK retire las entidades originales.
  (urb:ensure-anden-fast)
  (setq boundary (vlax-ename->vla-object ename))
  (setq side-data (urb:tactile-side-data ename))
  (if (and (null side-data) *urb-current-tactile-side-anchor*)
    (setq side-data *urb-current-tactile-side-anchor*))
  (urb:ensure-layer "URB-ANDEN" 7 T)
  (setq metadata (urb:get-xdata-strings ename "URB_ANDEN"))
  (setq material
    (urb:safe-string
      (if metadata (nth 1 metadata) nil) "LOSETA"))
  (setq etapa
    (urb:safe-string
      (if metadata (nth 2 metadata) nil) "1"))
  (setq subetapa
    (urb:safe-string
      (if metadata (nth 3 metadata) nil) etapa))
  (setq guia
    (urb:safe-string
      (if (> (length metadata) 4) (nth 4 metadata) nil) "No"))
  (setq toperol
    (urb:safe-string
      (if (> (length metadata) 5) (nth 5 metadata) nil) "No"))
  (setq format
    (urb:safe-string
      (if (> (length metadata) 6) (nth 6 metadata) nil) "40 x 40 cm"))
  (setq calculate
    (urb:safe-string
      (if (> (length metadata) 7) (nth 7 metadata) nil) "Si"))
  (setq surface
    (urb:safe-string
      (if (> (length metadata) 8) (nth 8 metadata) nil) "Seleccionar en dibujo"))
  (setq grade-source
    (urb:safe-string
      (if (> (length metadata) 9) (nth 9 metadata) nil) "Via creada"))
  (setq elevation
    (if (> (length metadata) 10)
      (atof (urb:safe-string (nth 10 metadata) "0"))
      (if (vlax-property-available-p boundary 'Elevation)
        (vla-get-Elevation boundary)
        0.0)))
  (setq pattern-mode (urb:anden-pattern-mode ename))
  ;; 2026-09-08 (pedido del usuario: "el area del anden me esta cogiendo
  ;; las areas incluyendo los prefabricados"): AREA_M2 guarda el area
  ;; NETA -- el contorno menos las huellas de prefabricados y
  ;; contenedores, que es exactamente lo que queda dibujado. El area del
  ;; contorno se conserva en AREA_BRUTA_M2 y el atributo AREA_NETA le
  ;; avisa al colector del presupuesto que ya no debe volver a descontar
  ;; (los bloques viejos no lo traen y se siguen descontando como antes).
  (setq area-bruta (vla-get-Area boundary))
  (setq area (urb:anden-area-neta ename area-bruta))
  (setq perimeter (urb:poly-perimeter boundary))
  (setq over-poly (urb:anden-overwidth-contour ename 1.0))
  ;; 5.6.2: un anden recortado por una rampa/paso puede quedar sin dos
  ;; costados claros y el sobreancho no se arma. Antes eso ABORTABA el
  ;; empaquetado (el anden no se regeneraba). Ahora las tierras usan el
  ;; contorno exacto y se avisa; el acabado y las cantidades no cambian.
  (if (not over-poly)
    (progn
      (entmake (vl-remove-if '(lambda (p) (member (car p) '(-1 5 330 360 102)))
                 (entget ename)))
      (setq over-poly (entlast))
      (urb:bb-log "  sobreancho no aplicable: tierras con contorno exacto")
      (prompt "\nANDEN: el contorno no tiene dos costados claros; el movimiento de tierras se mide SIN sobreancho lateral.")))
  (setq over-area (vla-get-Area (vlax-ename->vla-object over-poly)))
  (urb:tag-generated-role (vlax-ename->vla-object over-poly)
    (vla-get-Handle boundary) "EARTHWORK_BOUNDARY")
  (vla-put-Visible (vlax-ename->vla-object over-poly) :vlax-false)
  ;; Con arcos reales (PLINE opcion Arc) hay que usar la version que sigue
  ;; el arco, no la cuerda recta: corridor-length (y por lo tanto los
  ;; metros lineales de guia/toperol) salen cortos en un anden curvo si no.
  (setq points (urb:lwpoly-points-with-arcs-fine ename))
  (setq quantity-pattern-angle
    (urb:anden-quantity-pattern-angle ename points pattern-mode))
  (setq measured-qty (urb:anden-measured-finish ename area format))
  (setq finish-qty
    (if measured-qty measured-qty
    (cond
      ((urb:string-equal-p material "Loseta")
        (urb:anden-finish-quantities
          points area format guia toperol pattern-mode
          quantity-pattern-angle))
      ((urb:string-equal-p material "Adoquin")
        (urb:adoquin-finish-quantities points area format guia toperol))
      (T
        (list 0.0 0 0.0 0.0 0.0 0)))))
  (setq handle (vla-get-Handle boundary))
  (setq objects
    (cons boundary (urb:generated-objects handle)))
  (foreach obj objects
    (if (not
          (urb:string-equal-p
            (vla-get-Layer obj) "URB-SEL-ANDEN"))
      (setq filtered (cons obj filtered))
      (urb:safe-delete obj)))
  (setq objects (reverse filtered))
  (setq point
    (if (urb:lwpoly-points ename)
      (car (urb:lwpoly-points ename))
      '(0.0 0.0 0.0)))
  (setq block-name
    (strcat
      "URB_ANDEN_"
      handle
      "_"
      (itoa (getvar "MILLISECS"))))
  (setq blocks (vla-get-Blocks (urb:doc)))
  (prompt
    (strcat
      "\nEmpaquetando el anden en un bloque ("
      (itoa (length objects))
      " objetos)..."))
  ;; EMPAQUETADO NATIVO con -BLOCK (2026-08-09): mueve todas las entidades
  ;; a la definicion en UNA operacion nativa, en vez de CopyObjects +
  ;; borrado objeto-por-objeto via COM que tardaba MINUTOS con decenas de
  ;; miles de piezas -- la causa de fondo de "el anden no queda en bloque"
  ;; (el usuario interrumpia la espera y el material quedaba suelto). Si
  ;; el comando falla por cualquier razon, se cae al camino COM anterior.
  (setq fast-ok nil)
  (setq ss (ssadd))
  (foreach obj objects
    (setq en (vl-catch-all-apply 'vlax-vla-object->ename (list obj)))
    (if (not (vl-catch-all-error-p en)) (ssadd en ss)))
  (if (> (sslength ss) 0)
    (progn
      (setq t-pack (getvar "MILLISECS"))
      ;; destrabar las capas de las piezas: es lo que hacia fallar a -BLOCK
      (setq capas-estado (urb:layers-unlock (urb:layers-of-selection ss))
            trabadas (urb:layers-trabadas capas-estado))
      (if (> trabadas 0)
        (prompt (strcat "\n  (" (itoa trabadas)
          " capa(s) estaban bloqueadas o congeladas; se destraban para"
          " empaquetar y se dejan como estaban)")))
      (setq old-attreq (getvar "ATTREQ"))
      (setvar "ATTREQ" 0)
      (setq cmd-result
        (vl-catch-all-apply 'vl-cmdf
          (list "_.-BLOCK" block-name "0,0,0" ss "")))
      (setvar "ATTREQ" old-attreq)
      (urb:bb-log (strcat "  -BLOCK " (if (vl-catch-all-error-p cmd-result) "ERROR" "OK")))
      (urb:layers-restore capas-estado)
      (if (and (not (vl-catch-all-error-p cmd-result))
               (tblsearch "BLOCK" block-name))
        (progn
          (setq block-definition
            (vl-catch-all-apply '(lambda () (vla-Item blocks block-name))))
          (if (not (vl-catch-all-error-p block-definition))
            (setq fast-ok T))))
      ;; si aun asi fallo, DECIR POR QUE: antes solo se veia "no
      ;; disponible" y despues varios minutos de espera a ciegas
      (if (not fast-ok)
        (prompt
          (strcat "\n  motivo del fallo nativo: "
            (cond
              ((/= 0 (getvar "CMDACTIVE"))
                "hay otro comando activo (CMDACTIVE distinto de 0)")
              ((vl-catch-all-error-p cmd-result)
                (strcat "-BLOCK devolvio: "
                  (vl-catch-all-error-message cmd-result)))
              ((not (tblsearch "BLOCK" block-name))
                "el comando corrio pero no quedo la definicion del bloque")
              (T "no se pudo tomar la definicion recien creada"))))
        (prompt
          (strcat "\n  empaquetado nativo OK en "
            (rtos (/ (- (getvar "MILLISECS") t-pack) 1000.0) 2 1) " s")))))
  (if (not fast-ok)
    (progn
      (prompt "\nEmpaquetado nativo no disponible; usando el metodo lento (varios minutos, no interrumpa)...")
      (setq block-definition
        (vla-Add blocks (vlax-3d-point '(0.0 0.0 0.0)) block-name))
      (setq copy-result
        (vl-catch-all-apply
          'vla-CopyObjects
          (list
            (urb:doc)
            (urb:object-array-variant objects)
            block-definition))))
    (setq copy-result nil))
  (if (and (not fast-ok) (vl-catch-all-error-p copy-result))
    (progn
      (urb:safe-delete block-definition)
      (prompt
        (strcat
          "\nERROR al crear el bloque del anden: "
          (vl-catch-all-error-message copy-result)))
      nil)
    (progn
      ;; 2026-09-14: se reporta el tiempo del ORDEN DE DIBUJO aparte. Medido
      ;; en laboratorio, el empaquetado escala peor que lineal (al doblar el
      ;; largo del anden el empaque se multiplico por 2,61 con el doble de
      ;; piezas), y esta es la fase candidata: reordenar la tabla de
      ;; sortents con decenas de miles de objetos. Sin el dato no se
      ;; optimiza a ciegas una fase que decide que tapa a que.
      (setq t-pack (getvar "MILLISECS"))
      ;; Una transaccion: copia DXF exactos de las guias al bloque final,
      ;; elimina sus INSERT internos y ordena todos los roles en una pasada.
      ;; No se simplifican curvas, simbolos, capas ni cantidades.
      (urb:bb-log "  INICIA orden de dibujo (URBANDENFLAT553)")
      (setq flat-result
        (vl-catch-all-apply 'URBANDENFLAT553 (list block-name)))
      (if (vl-catch-all-error-p flat-result)
        (progn
          ;; El bloque nativo ya existe y contiene el acabado. Un fallo al
          ;; aplanar/ordenar una franja vacia no debe borrar todo el anden;
          ;; se conserva el bloque y se deja el diagnostico explicito.
          (urb:bb-log (strcat "  URBANDENFLAT553 ERROR: "
            (vl-catch-all-error-message flat-result)))
          (prompt (strcat "\nAVISO: no se pudo aplanar el orden interno del anden: "
            (vl-catch-all-error-message flat-result)
            ". El bloque principal se conserva.")))
        (urb:bb-log "  TERMINA orden de dibujo"))
      (prompt
        (strcat "\n  orden de dibujo: "
          (rtos (/ (- (getvar "MILLISECS") t-pack) 1000.0) 2 1) " s"))
      (urb:add-invisible-attribute
        block-definition point "AREA_M2" "Area m2"
        (rtos area 2 2))
      (urb:add-invisible-attribute
        block-definition point "AREA_BRUTA_M2" "Area del contorno m2"
        (rtos area-bruta 2 2))
      (foreach pair
        (list (cons "AREA_SIN_SOBREANCHO_M2" area)
              (cons "AREA_CON_SOBREANCHO_M2" over-area)
              (cons "SOBREANCHO_IZQ_M" 1.0) (cons "SOBREANCHO_DER_M" 1.0)
              (cons "LOSETA_GUIA_M2" (* (urb:loseta-module format) (nth 2 finish-qty)))
              (cons "LOSETA_TOPEROL_M2" (* (urb:loseta-module format) (nth 3 finish-qty))))
        (urb:add-invisible-attribute block-definition point (car pair) (car pair) (rtos (cdr pair) 2 6)))
      ;; marca de esquema: el colector NO vuelve a descontar en estos
      ;; bloques (los anteriores a 2026-09-08 no la traen)
      (urb:add-invisible-attribute
        block-definition point "AREA_NETA" "Area ya descontada" "Si")
      (urb:add-invisible-attribute
        block-definition point "ETAPA" "Etapa" etapa)
      (urb:add-invisible-attribute
        block-definition point "SUBETAPA" "Subetapa" subetapa)
      (urb:add-invisible-attribute
        block-definition point "LOSETA_GUIA" "Loseta guia" guia)
      (urb:add-invisible-attribute
        block-definition point "LOSETA_TOPEROL" "Loseta toperol" toperol)
      (urb:add-invisible-attribute
        block-definition point "LOSETA_LISA_M2" "Area loseta lisa m2"
        (rtos (nth 0 finish-qty) 2 6))
      (urb:add-invisible-attribute
        block-definition point "LOSETA_LISA_UND" "Loseta lisa unidades"
        (itoa (nth 1 finish-qty)))
      (urb:add-invisible-attribute
        block-definition point "LOSETA_GUIA_ML" "Loseta guia ml"
        (rtos (nth 2 finish-qty) 2 2))
      (urb:add-invisible-attribute
        block-definition point "LOSETA_TOPEROL_ML" "Loseta toperol ml"
        (rtos (nth 3 finish-qty) 2 2))
      ;; 2026-08-19 (pedido del usuario): unidades de pieza guia/toperol
      ;; visibles en Propiedades -- ml de franja / ancho de pieza 0.20
      (urb:add-invisible-attribute
        block-definition point "LOSETA_GUIA_UND" "Loseta guia unidades"
        (itoa (fix (+ 0.5 (/ (nth 2 finish-qty) 0.20)))))
      (urb:add-invisible-attribute
        block-definition point "LOSETA_TOPEROL_UND" "Loseta toperol unidades"
        (itoa (fix (+ 0.5 (/ (nth 3 finish-qty) 0.20)))))
      (urb:add-invisible-attribute
        block-definition point "ADOQUIN_20X10_M2" "Area adoquin blanco 20x10 m2"
        (rtos (nth 4 finish-qty) 2 6))
      (urb:add-invisible-attribute
        block-definition point "ADOQUIN_20X10_UND" "Adoquin blanco 20x10 unidades"
        (itoa (nth 5 finish-qty)))
      (urb:add-invisible-attribute
        block-definition point "ANDEN_CORTE_M3" "Corte m3" "0")
      (urb:add-invisible-attribute
        block-definition point "ANDEN_RELLENO_M3" "Relleno m3" "0")
      (urb:bb-log "  atributos OK; INICIA insertar bloque")
      (setq insert-result
        (vl-catch-all-apply
          'vla-InsertBlock
          (list
            (urb:space)
            (vlax-3d-point (list 0.0 0.0 elevation))
            block-name
            1.0 1.0 1.0 0.0)))
      (if (vl-catch-all-error-p insert-result)
        (progn
          (urb:safe-delete block-definition)
          (prompt
            (strcat
              "\nERROR al insertar el bloque del anden: "
              (vl-catch-all-error-message insert-result)))
          nil)
        (progn
          (setq block-ref insert-result)
          (setq block-ename (urb:as-ename block-ref))
          (if (not block-ename)
            (progn
              (urb:safe-delete block-ref)
              (urb:safe-delete block-definition)
              (prompt
                "\nERROR: AutoCAD no devolvio una referencia de bloque valida para el anden.")
              nil)
            (progn
              (vla-put-Layer block-ref "URB-ANDEN")
              (urb:bb-log (strcat "  bloque insertado; xdata pattern-mode=" (vl-princ-to-string pattern-mode) " surface=" (vl-princ-to-string surface) " grade=" (vl-princ-to-string grade-source) " format=" (vl-princ-to-string format)))
              (setq xdata-result
                (urb:set-xdata-strings
                  block-ename
                  "URB_ANDEN_BLOCK"
                  (list
                    "ANDEN" material etapa subetapa
                    (rtos area 2 8)
                    (rtos perimeter 2 8)
                    *urb-schema-version* guia toperol format calculate surface grade-source
                     (rtos (nth 0 finish-qty) 2 8)
                     (itoa (nth 1 finish-qty))
                     (rtos (nth 2 finish-qty) 2 8)
                     (rtos (nth 3 finish-qty) 2 8)
                     (rtos (nth 4 finish-qty) 2 8)
                     (itoa (nth 5 finish-qty))
                     (rtos elevation 2 8)
                     pattern-mode)))
              (if xdata-result
                (progn
                  (urb:set-anden-pattern-mode block-ename pattern-mode)
                  (if side-data
                    (urb:set-tactile-side-data block-ename side-data))
                  ;; con -BLOCK los originales ya fueron MOVIDOS al bloque:
                  ;; no hay nada que borrar (y recorrer decenas de miles de
                  ;; objetos muertos costaba minutos extra)
                  (if (not fast-ok)
                    (foreach obj objects (urb:safe-delete obj)))
                  block-ref)
                (progn
                  (urb:safe-delete block-ref)
                  (urb:safe-delete block-definition)
                  (prompt
                    "\nERROR: no fue posible guardar los datos del bloque de anden.")
                  nil))))))))
)

;; ============================================================
;; MOVIMIENTO DE TIERRAS DE ANDENES (4.9.0)
;; Igual que en vias: opcional, integrado en ANDEN/EDITAR, sin
;; cambiar el esquema principal de datos del anden. Muestrea la superficie
;; Civil 3D mediante una malla interior adaptativa y la
;; compara contra el nivel de acabado menos el espesor de la
;; estructura (0.60 m). Se guarda en la xdata URB_ANDEN_MOV del
;; bloque.
;; ============================================================

;; Espesor total de la estructura de anden (Figura estudio de suelos):
;; 6+4+50 cm = 60 cm. Unica fuente de verdad para el calculo de tierras;
;; *urb-anden-structure* mantiene su propio valor textual igual a este.
(setq *urb-anden-depth* 0.60)
(setq *urb-anden-min-samples* 5)
(setq *urb-anden-min-coverage* 0.90)
(setq *urb-anden-max-samples* 400)

(defun urb:average-terrain-at-points (surface points / total count p z)
  (setq total 0.0 count 0)
  (foreach p points
    (setq z (urb:surface-elevation surface (car p) (cadr p)))
    (if z (setq total (+ total z) count (1+ count))))
  (if (> count 0) (list (/ total count) count) nil)
)

(defun urb:polygon-centroid (points / ring p1 p2 cross sum-cross cx cy)
  ;; Centroide real por la formula del poligono (shoelace). El promedio
  ;; de vertices se desplaza mucho en contornos irregulares.
  (if (> (length points) 2)
    (progn
      (setq ring (append points (list (car points)))
            sum-cross 0.0 cx 0.0 cy 0.0)
      (while (cadr ring)
        (setq p1 (car ring)
              p2 (cadr ring)
              cross (- (* (car p1) (cadr p2)) (* (car p2) (cadr p1)))
              sum-cross (+ sum-cross cross)
              cx (+ cx (* (+ (car p1) (car p2)) cross))
              cy (+ cy (* (+ (cadr p1) (cadr p2)) cross))
              ring (cdr ring)))
      (if (> (abs sum-cross) 1e-12)
        (list (/ cx (* 3.0 sum-cross)) (/ cy (* 3.0 sum-cross)))
        nil))
    nil)
)

(defun urb:point-in-polygon-p
  (point points / x y inside ring p1 p2 x1 y1 x2 y2 crossing-x)
  (setq x (car point) y (cadr point) inside nil)
  (if (> (length points) 2)
    (progn
      (setq ring (append points (list (car points))))
      (while (cadr ring)
        (setq p1 (car ring) p2 (cadr ring)
              x1 (car p1) y1 (cadr p1)
              x2 (car p2) y2 (cadr p2))
        (if (not (equal (> y1 y) (> y2 y)))
          (progn
            (setq crossing-x
              (+ x1 (* (- y y1) (/ (- x2 x1) (- y2 y1)))))
            (if (< x crossing-x) (setq inside (not inside)))))
        (setq ring (cdr ring)))))
  inside
)

(defun urb:point-bounds (points / p minx maxx miny maxy)
  (foreach p points
    (if (null minx)
      (setq minx (car p) maxx (car p) miny (cadr p) maxy (cadr p))
      (setq minx (min minx (car p))
            maxx (max maxx (car p))
            miny (min miny (cadr p))
            maxy (max maxy (cadr p)))))
  (if minx (list minx maxx miny maxy) nil)
)

(defun urb:point-to-local (point cosine sine)
  (list
    (+ (* (car point) cosine) (* (cadr point) sine))
    (+ (* (- (car point)) sine) (* (cadr point) cosine)))
)

(defun urb:point-from-local (point cosine sine)
  (list
    (- (* (car point) cosine) (* (cadr point) sine))
    (+ (* (car point) sine) (* (cadr point) cosine)))
)

(defun urb:add-unique-point (point points / found item)
  (foreach item points
    (if (equal point item 1e-7) (setq found T)))
  (if found points (cons point points))
)

(defun urb:anden-fallback-samples
  (points / ring p1 p2 samples centroid midpoint interior)
  ;; Respaldo para contornos tan pequenos/estrechos que no admitan malla.
  (setq samples nil centroid (urb:polygon-centroid points))
  (if (and centroid (urb:point-in-polygon-p centroid points))
    (setq samples (urb:add-unique-point centroid samples)))
  (if points
    (progn
      (setq ring (append points (list (car points))))
      (while (cadr ring)
        (setq p1 (car ring) p2 (cadr ring))
        (setq midpoint
          (list (/ (+ (car p1) (car p2)) 2.0)
                (/ (+ (cadr p1) (cadr p2)) 2.0)))
        (setq samples (urb:add-unique-point p1 samples))
        (setq samples (urb:add-unique-point midpoint samples))
        (if centroid
          (progn
            (setq interior
              (list (/ (+ (car midpoint) (car centroid)) 2.0)
                    (/ (+ (cadr midpoint) (cadr centroid)) 2.0)))
            (if (urb:point-in-polygon-p interior points)
              (setq samples (urb:add-unique-point interior samples)))))
        (setq ring (cdr ring)))))
  (reverse samples)
)

(defun urb:anden-sample-points
  (points area / angle-value cosine sine local-points bounds
   minx maxx miny maxy width height bbox-area spacing x y
   local-point point samples fallback)
  ;; Malla de centros de celda: las muestras interiores tienen pesos
  ;; aproximadamente uniformes por area y no sobrerrepresentan el perimetro.
  ;; Se orienta con el borde principal para no perder cobertura en andenes
  ;; largos y diagonales por culpa de una caja global X/Y sobredimensionada.
  (setq angle-value (urb:anden-axis-angle points)
        cosine (cos angle-value)
        sine (sin angle-value)
        local-points
          (mapcar
            '(lambda (item) (urb:point-to-local item cosine sine))
            points)
        bounds (urb:point-bounds local-points))
  (if (and bounds (> area 1e-8))
    (progn
      (setq minx (nth 0 bounds) maxx (nth 1 bounds)
            miny (nth 2 bounds) maxy (nth 3 bounds)
            width (- maxx minx) height (- maxy miny)
            bbox-area (* width height))
      (if (and (> width 1e-8) (> height 1e-8))
        (progn
          (setq spacing
            (max 0.25
              (min 5.0
                (sqrt (/ area 160.0))
                (/ (min width height) 2.0))))
          ;; Limita tanto el total estimado como el numero de columnas/filas.
          (setq spacing
            (max spacing
              (/ (max width height) 200.0)
              (sqrt (/ bbox-area (float *urb-anden-max-samples*)))))
          (setq x (+ minx (min (/ spacing 2.0) (/ width 2.0))))
          (while (and (< x maxx)
                      (< (length samples) *urb-anden-max-samples*))
            (setq y (+ miny (min (/ spacing 2.0) (/ height 2.0))))
            (while (and (< y maxy)
                        (< (length samples) *urb-anden-max-samples*))
              (setq local-point (list x y))
              (if (urb:point-in-polygon-p local-point local-points)
                (progn
                  (setq point
                    (urb:point-from-local local-point cosine sine))
                  (setq samples (cons point samples))))
              (setq y (+ y spacing)))
            (setq x (+ x spacing)))))))
  (setq samples (reverse samples))
  (if (< (length samples) *urb-anden-min-samples*)
    (progn
      (setq fallback (urb:anden-fallback-samples points))
      (foreach point fallback
        (setq samples (urb:add-unique-point point samples)))))
  samples
)

(setq *urb-anden-road-crossfall* 0.02)
(setq *urb-anden-crossfall* 0.02)
;; 5.6.5: alcance maximo de la pendiente transversal desde el borde (m)
(setq *urb-anden-crossfall-run* 6.0)
(setq *urb-anden-curb-height* 0.15)

;; ---------- 5.6.5 SOBREEXCAVACION Y ESPONJAMIENTO ----------
;; Pedido del usuario: "la sobreexcavacion corresponde al material que no
;; es portante; desde la cota del terreno natural la altura para llegar al
;; suelo portante puede estar a los 50 cm o el parametro que pueda meter.
;; Cuando son cortes de altura mayor a esos 50 cm no hay problema; si son
;; menores, igual me toca excavar esos 50 del suelo portante, y eso afecta
;; los llenos porque al excavar esos 50 los llenos hasta la cota que
;; quiero se afectan".
;; Por eso, en CADA punto de muestreo, con c = terreno - subrasante:
;;   excavacion = max(c, altura no portante)
;;   relleno    = max(0, altura no portante - c)
;; Con altura 0 el resultado es el clasico (corte = c, relleno = -c).
;; Los coeficientes NO cambian el volumen geometrico: se reportan aparte
;; (corte suelto para acarreo, material necesario para el lleno).
(setq *urb-overexc-depth* 0.50)   ; m de material no portante bajo el TN
(setq *urb-cut-expansion* 0.25)   ; expansion del material excavado
(setq *urb-fill-shrinkage* 0.20)  ; sobreconsumo del relleno compactado

;; corte y relleno de UN punto, con sobreexcavacion incluida
(defun urb:cut-fill-at (delta / h)
  (setq h (if (numberp *urb-overexc-depth*) (max 0.0 *urb-overexc-depth*) 0.0))
  (list (max delta h) (max 0.0 (- h delta))))

(defun urb:cut-loose (volume)
  (* volume (+ 1.0 (if (numberp *urb-cut-expansion*) *urb-cut-expansion* 0.0))))

(defun urb:fill-material (volume)
  (* volume (+ 1.0 (if (numberp *urb-fill-shrinkage*) *urb-fill-shrinkage* 0.0))))

(defun urb:overexc-text ()
  (strcat "sobreexcavacion " (rtos *urb-overexc-depth* 2 2) " m"
          " | expansion " (rtos (* 100.0 *urb-cut-expansion*) 2 0) "%"
          " | relleno +" (rtos (* 100.0 *urb-fill-shrinkage*) 2 0) "%"))

(defun urb:read-lisp-safe (text / value)
  (if (/= (urb:safe-string text "") "")
    (progn
      (setq value (vl-catch-all-apply 'read (list text)))
      (if (vl-catch-all-error-p value) nil value))
    nil)
)

(defun urb:grade-records-valid-p (records / valid record)
  (setq valid (and (listp records) (> (length records) 1)))
  (foreach record (if valid records nil)
    (if (not
          (and (listp record)
               (> (length record) 1)
               (numberp (nth 0 record))
               (numberp (nth 1 record))))
      (setq valid nil)))
  valid
)

;; XDATA limita cada cadena a 255 caracteres. Conserva hasta diez puntos
;; repartidos a lo largo de la rasante, suficientes para que los andenes
;; asociados reproduzcan sus cambios sin exceder ese limite.
(defun urb:compact-road-grade-samples
  (samples / total step index item result)
  (setq total (length samples))
  (setq step (max 1 (fix (+ (/ (max 0 (- total 1)) 9.0) 0.999999))))
  (setq index 0)
  (foreach item samples
    (if (or (= 0 (rem index step)) (= index (1- total)))
      (setq result
        (append result
          (list (list
            (atof (rtos (nth 0 item) 2 3))
            (atof (rtos (nth 2 item) 2 3)))))))
    (setq index (1+ index)))
  result
)

;; Recupera las cotas de una via antigua que no tenga muestras de rasante
;; guardadas. Primero intenta la capa registrada por VIA; si el XREF perdio
;; su calibracion al recargar el LSP, solicita un solo texto de referencia.
(defun urb:road-grade-records-from-layer
  (axis data / layer texts axis-start span station-start interval direction records info)
  ;; URB_VIA[7] guarda el MODO (Pendiente/Textos por capa);
  ;; la capa de cotas real esta en [8].
  (setq layer (urb:safe-string (nth 8 data) ""))
  (setq axis-start (atof (urb:safe-string (nth 21 data) "0")))
  (setq span (atof (urb:safe-string (nth 18 data) "0")))
  (setq station-start (urb:station-number (urb:safe-string (nth 10 data) "0")))
  (setq interval (atof (urb:safe-string (nth 11 data) "5")))
  (setq direction (urb:safe-string (nth 12 data) "Inicio"))
  (if (<= interval 1e-6) (setq interval 5.0))
  (if (and axis (/= layer ""))
    (progn
      (setq texts (urb:collect-cota-texts layer))
      (setq records
        (if texts
          (urb:cota-stations-on-axis axis texts axis-start span 15.0)
          nil))
      (setq records (urb:cota-best-per-source records))
      (setq records
        (urb:cota-snap-to-project-grid records axis-start span
          station-start interval direction))
      (setq records (urb:cota-deduplicate-stations records 0.05))))
  ;; La busqueda automatica recorre TODAS las vias candidatas. Una via
  ;; antigua sin rasante no debe abrir nentsel a mitad de ese barrido.
  (if (and (< (length records) 2) (not *urb-road-grade-silent*))
    (progn
      (prompt
        "\nLa via es anterior a la rasante guardada. Seleccione una cota de su capa para reconstruirla: ")
      (setq info (urb:road-cota-reference "Textos por capa"))
      (if (urb:string-equal-p (urb:safe-string (car info) "") "PICKED")
        ;; auto-detect: cotas seleccionadas una a una (via/etiqueta/texto)
        (setq records
          (urb:cota-deduplicate-stations
            (urb:picked-cotas-to-stations (cadr info) axis) 0.05))
        (progn
          (setq layer (urb:safe-string (car info) layer))
          (setq texts (if (/= layer "") (urb:collect-cota-texts layer) nil))
          (setq records
            (if texts
              (urb:cota-stations-on-axis axis texts axis-start span 15.0)
              nil))
          (setq records (urb:cota-best-per-source records))
          (setq records
            (urb:cota-snap-to-project-grid records axis-start span
              station-start interval direction))
          (setq records (urb:cota-deduplicate-stations records 0.05))))))
  records
)

;; Referencia: (eje registros inicio-eje longitud sentido modo metodo).
;; En una via nueva, registros contiene las muestras de rasante guardadas.
;; Las vias antiguas sin muestras pueden releerlas desde su capa de cotas;
;; el eje siempre se recupera o selecciona entre entidades ya existentes.
;; 5.6.1 (reporte del usuario: "cuando le doy editar un anden porque me
;; pide seleccionar una polilinea del eje" + "que me reconozca todo el
;; alineamiento, actualmente me reconoce solo una cota"). La vía que
;; controla el anden se DETECTA sola: la via creada mas cercana al contorno
;; (<= 10 m). Solo si no hay ninguna cerca se pide el clic.
(defun urb:anden-road-autodetect (points / ss i e road seen best bestd d p near step k)
  (if (and points (> (length points) 2))
    (progn
      ;; contornos curvos traen miles de vertices (un anden real: 1272);
      ;; para decidir cual via esta al lado bastan ~80 repartidos
      (if (> (length points) 80)
        (setq step (/ (length points) 80) k 0
              points (vl-remove-if
                       '(lambda (p) (/= 0 (rem (setq k (1+ k)) step)))
                       points)))
      ;; 5.6.5 (reporte del usuario: "hay tramos de andenes que me estaba
      ;; dando rellenos donde me tenia que dar corte"). La distancia se
      ;; medía al BLOQUE de la via, y para un bloque
      ;; urb:point-to-entity-distance usa su CAJA ENVOLVENTE: una via
      ;; diagonal y larga "toca" a distancia 0 andenes que estan a cientos
      ;; de metros de su eje. Medido en F20E5: gano AB370 (eje a 220 m), su
      ;; estacion salio -220 m, la rasante se EXTRAPOLO y la cota de diseno
      ;; quedo 4.79 m sobre el terreno -> relleno de 2427 m3 en 367 m2.
      ;; Ahora se mide al EJE real, se descartan las vias cuya estacion
      ;; queda fuera del tramo (no se extrapola) y gana la via cuyo borde
      ;; de calzada coincide mejor con el borde del anden.
      (setq ss (ssget "_X" '((-3 ("URB_VIA")))) i 0)
      (if ss
        (repeat (sslength ss)
          (setq e (ssname ss i)
                road (vl-catch-all-apply 'urb:road-parent-from-entity (list e)))
          (if (and road (not (vl-catch-all-error-p road))
                   (not (member road seen)))
            (progn
              (setq seen (cons road seen))
              (setq d (vl-catch-all-apply
                        'urb:anden-road-score (list road points)))
              (if (vl-catch-all-error-p d) (setq d nil))
              (if (and d (or (null bestd) (< d bestd)))
                (setq bestd d best road))))
          (setq i (1+ i))))
      best)
    nil))

;; Puntaje de una via como referencia de un anden: |distancia al eje -
;; media calzada|. nil si la via no sirve (sin eje/rasante, lejos, o el
;; anden cae fuera del tramo y habria que extrapolar la rasante).
(defun urb:anden-road-grade-for-quiet (road / *urb-road-grade-silent*)
  (setq *urb-road-grade-silent* T)
  (urb:anden-road-grade-for road))

(defun urb:anden-road-score (road points / ref axis mov half dmin dmax dists med p c d est span start modo)
  (setq ref (vl-catch-all-apply 'urb:anden-road-grade-for-quiet (list road)))
  (if (or (vl-catch-all-error-p ref) (null ref)) (setq ref nil))
  (setq axis (if ref (nth 0 ref)))
  (if (and axis (urb:curve-entity-p axis))
    (progn
      (setq mov (vl-catch-all-apply 'urb:road-movement-data (list road)))
      (setq half
        (if (and (not (vl-catch-all-error-p mov)) mov (> (length mov) 5))
          (* 0.5 (atof (urb:safe-string (nth 5 mov) "0")))
          0.0))
      (setq start (nth 2 ref) span (nth 3 ref) modo (nth 5 ref))
      (foreach p points
        (setq c (vl-catch-all-apply 'vlax-curve-getClosestPointTo
                  (list axis (list (car p) (cadr p) 0.0))))
        (if (not (vl-catch-all-error-p c))
          (progn
            (setq d (distance (list (car p) (cadr p)) (list (car c) (cadr c)))
                  dists (cons d dists))
            (if (or (null dmin) (< d dmin)) (setq dmin d))
            ;; estacion del punto en el tramo de la via
            (setq est (vlax-curve-getDistAtPoint axis c))
            (if (urb:string-equal-p modo "LOCAL")
              (setq est (if (urb:string-equal-p (nth 4 ref) "Final")
                          (- (+ start span) est) (- est start))))
            (if (or (null dmax) (> (abs (- est (/ span 2.0))) dmax))
              (setq dmax (abs (- est (/ span 2.0))))))))
      ;; La MEDIANA de las distancias, no la minima: F20E5 tocaba AB174 solo
      ;; en su arranque (minima 2.9 m) pero se aleja hasta 104 m del eje, y
      ;; la pendiente transversal aplicada sobre esa distancia inventaba
      ;; 2 m de rasante. Un anden que de verdad acompaña a la via tiene
      ;; casi todos sus puntos a media calzada del eje.
      (setq dists (vl-sort dists '<)
            med (if dists (nth (/ (length dists) 2) dists)))
      ;; fuera del tramo (mas de 5 m por fuera en cualquier punto): la
      ;; rasante tendria que extrapolarse -> esta via no gobierna el anden
      (if (and med (< med (+ half 8.0))
               (or (null span) (<= span 0.0)
                   (and dmax (<= dmax (+ (/ span 2.0) 5.0)))))
        (abs (- med half))))))

;; distancia en planta de un punto a una entidad: curva exacta; bloque u
;; otro objeto por su caja envolvente (0 si el punto cae dentro)
(defun urb:point-to-entity-distance (ename p / near r lo hi dx dy obj)
  (if (urb:curve-entity-p ename)
    (progn
      (setq near (vl-catch-all-apply 'vlax-curve-getClosestPointTo
                   (list ename (list (car p) (cadr p) 0.0))))
      (if (vl-catch-all-error-p near) nil
        (distance (list (car p) (cadr p)) (list (car near) (cadr near)))))
    (progn
      (setq obj (vlax-ename->vla-object ename)
            r (vl-catch-all-apply 'vla-GetBoundingBox (list obj 'lo 'hi)))
      (if (vl-catch-all-error-p r) nil
        (progn
          (setq lo (vlax-safearray->list lo) hi (vlax-safearray->list hi))
          (setq dx (max 0.0 (- (car lo) (car p)) (- (car p) (car hi)))
                dy (max 0.0 (- (cadr lo) (cadr p)) (- (cadr p) (cadr hi))))
          (sqrt (+ (* dx dx) (* dy dy))))))))

;; puntos del contorno del anden en calculo (los fija urb:run-anden-earthworks)
(setq *urb-anden-grade-points* nil)

(defun urb:select-anden-road-grade (/ road)
  (setq road (urb:anden-road-autodetect *urb-anden-grade-points*))
  (if (null road)
    (progn
      (setq road (entsel "\nSeleccione la via creada que controla este anden: "))
      (if road (setq road (urb:road-parent-from-entity (car road))))))
  (if road (urb:anden-road-grade-for-safe road) nil))

(defun urb:anden-road-grade-for-safe (road / ref)
  (setq ref (vl-catch-all-apply 'urb:anden-road-grade-for (list road)))
  (if (vl-catch-all-error-p ref)
    (progn
      (prompt (strcat "\nNo se pudo leer la rasante de la via: "
        (vl-catch-all-error-message ref)
        ". El movimiento queda pendiente; revise esa via con EDITAR."))
      nil)
    ref))

;; referencia de rasante de UNA via creada: (eje records inicio longitud
;; sentido modo metodo via-id nombre). nil si la via no tiene rasante.
(defun urb:anden-road-grade-for
  (road / data mov axis axis-handle via-id records c0 c1 span
   record-mode method axis-start)
  (if (and road (setq data (urb:get-xdata-strings road "URB_VIA")))
    (progn
      (setq via-id (if (> (length data) 22) (nth 22 data) ""))
      ;; El eje se identifica SOLO entre entidades existentes: handle,
      ;; cache o vinculo via-id. Nunca se reconstruye uno nuevo del bloque.
      (setq axis (urb:road-axis-recover road data via-id))
      (if axis
        (urb:remember-road-axis road data via-id axis))
      (setq mov (urb:road-movement-data road))
      (setq records (urb:road-design-grade-records road data))
      (if (not (urb:grade-records-valid-p records)) (setq records nil))
      (if records
        (setq record-mode "LOCAL" method "Via creada - rasante guardada"))
      (setq span
        (atof
          (urb:safe-string
            (if (> (length data) 18) (nth 18 data) nil) "0")))
      (if (and (null records) mov (> (length mov) 8))
        (progn
          (setq c0 (urb:parse-real (nth 7 mov)))
          (setq c1 (urb:parse-real (nth 8 mov)))
           (if (and c0 c1 (> span 1e-6))
             (setq records (list (list 0.0 c0) (list span c1))
                   record-mode "LOCAL" method "Via creada"))))
      (if (and axis (null records))
        (progn
          (setq records (urb:road-grade-records-from-layer axis data))
          (if (urb:grade-records-valid-p records)
            (setq record-mode "RAW"
                  method "Via creada - cotas reconstruidas")
            (setq records nil))))
      (setq axis-start
        (atof
          (urb:safe-string
            (if (> (length data) 21) (nth 21 data) nil) "0")))
      (if (and axis (urb:curve-entity-p axis)
               (urb:grade-records-valid-p records))
        (list axis records
          axis-start span
          (urb:safe-string
            (if (> (length data) 12) (nth 12 data) nil) "Inicio")
          record-mode method
          (urb:safe-string via-id "")
          (urb:safe-string (if (> (length data) 1) (nth 1 data) nil) ""))
        (progn
          (if (not *urb-road-grade-silent*)
            (prompt
              (if axis
                (strcat "\nLa via " (urb:safe-string (nth 1 data) "seleccionada")
                  " no tiene rasante guardada. Use EDITAR para asignarle cotas"
                  " y pendiente antes de usarla como referencia.")
                "\nLa via no conserva un eje vinculado. Edite esa via una vez; no se creara ni se pedira un eje duplicado.")))
          nil)))
    (progn (prompt "\nEl objeto seleccionado no es una via cuantificable.") nil))
)

(defun urb:select-anden-alignment-grade
  (/ axis info layer texts axis-length records)
  (setq axis (urb:select-or-draw-road-axis "Existente"))
  (if axis
    (progn
      (setq info (urb:road-cota-reference "Textos por capa"))
      (setq axis-length
        (vlax-curve-getDistAtParam axis (vlax-curve-getEndParam axis)))
      (if (urb:string-equal-p (urb:safe-string (car info) "") "PICKED")
        ;; auto-detect: cotas seleccionadas una a una (via/etiqueta/texto)
        (setq records
          (urb:cota-deduplicate-stations
            (urb:picked-cotas-to-stations (cadr info) axis) 0.05))
        (progn
          (setq layer (car info))
          (setq texts (if (/= layer "") (urb:collect-cota-texts layer) nil))
          (setq records
            (if texts (urb:cota-stations-on-axis axis texts 0.0 axis-length 15.0) nil))
          (setq records (urb:cota-best-per-source records))
          (setq records (urb:cota-deduplicate-stations records 0.05))))
      (if (urb:grade-records-valid-p records)
        (list axis records 0.0 axis-length "Inicio" "RAW"
          "Alineamiento + cotas" "" "")
        (progn
          (prompt "\nNo se encontraron suficientes cotas cerca del alineamiento.") nil))))
)

;; "Cotas seleccionadas" (2026-08-12, pedido del usuario: rasante del
;; anden SIN via creada y SIN depender de una capa de cotas): se
;; selecciona o dibuja el eje de referencia y luego se clickean N cotas
;; una a una con el mismo picker auto-detect de las vias (texto/etiqueta
;; en CUALQUIER capa o xref, o una via ya creada, o digitada). Cada cota
;; se proyecta al eje en el punto del click -> rasante por tramos.
(defun urb:select-anden-picked-grade (/ axis picks records axis-length)
  (setq axis (urb:select-or-draw-road-axis "Existente"))
  (if axis
    (progn
      (prompt
        (strcat "\nSeleccione las cotas de rasante sobre el eje "
                "(textos en cualquier capa/xref, vias creadas o digitadas)."))
      (setq picks (urb:pick-road-cotas))
      (if picks
        (progn
          (setq records (urb:picked-cotas-to-stations picks axis))
          (setq axis-length
            (vlax-curve-getDistAtParam axis (vlax-curve-getEndParam axis)))
          (if (urb:grade-records-valid-p records)
            (list axis records 0.0 axis-length "Inicio" "RAW"
              "Cotas seleccionadas" "" "")
            (progn
              (prompt "\nNo se pudieron proyectar las cotas al eje.") nil)))
        nil)))
)

(defun urb:select-anden-grade-reference (source / road)
  (cond
    ((urb:string-equal-p source "Via creada")
      (urb:select-anden-road-grade))
    ;; 5.6.1: andenes guardados con "Cotas seleccionadas" o "Alineamiento +
    ;; cotas" pedian la polilinea del eje al EDITAR aunque hubiera una via
    ;; creada al lado. Si la hay, manda su rasante completa; si no, sigue
    ;; el modo guardado como antes.
    ((setq road (urb:anden-road-autodetect *urb-anden-grade-points*))
      (urb:anden-road-grade-for-safe road))
    ((urb:string-equal-p source "Cotas seleccionadas")
      (urb:select-anden-picked-grade))
    (T (urb:select-anden-alignment-grade)))
)

(defun urb:anden-axis-edge-offset (points axis / p closest offset minimum)
  (if (and axis (urb:curve-entity-p axis))
    (foreach p points
      (setq closest (vlax-curve-getClosestPointTo axis p))
      (setq offset (distance p closest))
      (if (or (null minimum) (< offset minimum)) (setq minimum offset))))
  minimum
)

(defun urb:anden-grade-at-point
  (point reference edge-offset / axis records axis-start span direction mode
   closest raw-distance station zaxis offset)
  (setq axis (nth 0 reference) records (nth 1 reference)
        axis-start (nth 2 reference) span (nth 3 reference)
        direction (nth 4 reference) mode (nth 5 reference))
  (setq closest (vlax-curve-getClosestPointTo axis point))
  (setq raw-distance (vlax-curve-getDistAtPoint axis closest))
  (setq station
    (if (urb:string-equal-p mode "LOCAL")
      (if (urb:string-equal-p direction "Final")
        (- (+ axis-start span) raw-distance)
        (- raw-distance axis-start))
      raw-distance))
  (setq zaxis (urb:cota-at-axis-distance station records))
  (setq offset (distance point closest))
  ;; 5.6.5: el anden DRENA HACIA LA VIA -- su punto mas bajo es el borde
  ;; del bordillo y sube alejandose de la calzada. Antes bajaba (signo
  ;; invertido): en un anden de 2 m eran 4 cm de diferencia, siempre del
  ;; lado del relleno.
  ;; 5.6.5: la pendiente transversal se aplica como maximo sobre
  ;; *urb-anden-crossfall-run* metros. Mas alla el elemento se toma plano:
  ;; sin este tope, un elemento ancho (o un contorno mal referenciado)
  ;; acumulaba metros de rasante inventada (F20E5: 2 m en 104 m).
  (if zaxis
    (+ (- zaxis (* *urb-anden-road-crossfall* edge-offset))
       *urb-anden-curb-height*
       (* *urb-anden-crossfall*
          (min *urb-anden-crossfall-run* (max 0.0 (- offset edge-offset)))))
    nil)
)

(defun urb:grade-slope-at-distance
  (axis-distance records / ordered first-record last-record ring p1 p2)
  ;; Pendiente firmada del segmento de rasante que contiene la estacion.
  ;; En los extremos usa el primer o ultimo segmento, evitando pendientes
  ;; artificiales iguales a cero por extrapolacion constante.
  (setq ordered
    (vl-sort
      records
      '(lambda (a b) (< (car a) (car b)))))
  (if (> (length ordered) 1)
    (progn
      (setq first-record (car ordered)
            last-record (last ordered))
      (cond
        ((<= axis-distance (car first-record))
          (setq p1 first-record p2 (cadr ordered)))
        ((>= axis-distance (car last-record))
          (setq p1 (nth (- (length ordered) 2) ordered)
                p2 last-record))
        (T
          (setq ring ordered)
          (while (and (cadr ring) (null p1))
            (if (and
                  (<= (car (car ring)) axis-distance)
                  (<= axis-distance (car (cadr ring))))
              (setq p1 (car ring) p2 (cadr ring))
              (setq ring (cdr ring))))))
      (if (and p1 p2 (> (- (car p2) (car p1)) 1e-9))
        (* 100.0
          (/ (- (cadr p2) (cadr p1))
             (- (car p2) (car p1))))
        nil))
    nil)
)

(defun urb:anden-longitudinal-slope-at-point
  (point reference / axis records axis-start span direction mode
   closest raw-distance station)
  (setq axis (nth 0 reference) records (nth 1 reference)
        axis-start (nth 2 reference) span (nth 3 reference)
        direction (nth 4 reference) mode (nth 5 reference))
  (setq closest (vlax-curve-getClosestPointTo axis point))
  (setq raw-distance (vlax-curve-getDistAtPoint axis closest))
  (setq station
    (if (urb:string-equal-p mode "LOCAL")
      (if (urb:string-equal-p direction "Final")
        (- (+ axis-start span) raw-distance)
        (- raw-distance axis-start))
      raw-distance))
  (urb:grade-slope-at-distance station records)
)

(defun urb:percent-range-text (minimum maximum)
  (cond
    ((and (numberp minimum) (numberp maximum)
          (equal minimum maximum 1e-6))
      (strcat (rtos minimum 2 2) "%"))
    ((and (numberp minimum) (numberp maximum))
      (strcat (rtos minimum 2 2) "% a " (rtos maximum 2 2) "%"))
    (T "sin calcular"))
)

(defun urb:mark-anden-earthworks-status (block-ref status / obj)
  (if (setq obj (urb:as-vla-object block-ref))
    (progn
      (if (wcmatch (strcase status) "PENDIENTE*")
        (progn
          (urb:set-block-attribute obj "ANDEN_CORTE_M3" "")
          (urb:set-block-attribute obj "ANDEN_RELLENO_M3" "")
          (urb:set-xdata-strings (urb:as-ename obj) "URB_ANDEN_MOV"
            (list "ANDEN_MOV" status "0" "0"))))
      (urb:set-block-attribute obj "ANDEN_METODO" status)
      (vla-Update obj)))
  nil
)

(defun urb:run-anden-earthworks
  (block-ref points area surface-name grade-source
   / block-object ename surface reference axis samples total edge-result
   edge-offset p terrain finish-result finish delta cut-depth fill-depth
   count corte relleno method coverage required coverage-text via-id via-name
   slope-result long-slope long-min long-max total-slope total-min total-max
   slope-count transverse-percent pend-long-text pend-trans-text pend-total-text
   edge-points sample weight total-weight)
  (setq *urb-anden-earthwork-stage* "validacion del bloque")
  (setq block-object (urb:as-vla-object block-ref))
  (setq ename (urb:as-ename block-object))
  (setq edge-points points)
  (if block-object
    (progn
      (setq points (urb:anden-earthwork-points block-object))
      (setq area (if points (urb:anden-earthwork-area block-object) 0.0))))
  (cond
    ((or (not block-object) (not ename))
      (prompt
        "\nNo se calculo el movimiento: la referencia del bloque de anden no es valida.")
      nil)
    ((or (not (listp points)) (< (length points) 3) (<= area 1e-8))
      (urb:mark-anden-earthworks-status block-object "PENDIENTE - contorno invalido")
      (prompt "\nNo se calculo el movimiento: el contorno del anden no es valido.")
      nil)
    (T
      (setq *urb-anden-earthwork-stage* "seleccion de superficie")
      (setq surface (urb:select-surface-object surface-name))
      (if (not (urb:valid-vla-object-p surface))
        (progn
          (urb:mark-anden-earthworks-status
            block-object "PENDIENTE - superficie no disponible")
          (prompt "\nNo se calculo el movimiento: superficie no disponible.")
          nil)
        (progn
          (setq *urb-anden-earthwork-stage* "seleccion de rasante")
          ;; 5.6.1: el contorno permite detectar sola la via que controla
          (setq *urb-anden-grade-points* (if edge-points edge-points points))
          (setq reference (urb:select-anden-grade-reference grade-source))
          (setq *urb-anden-grade-points* nil)
          (setq axis (if (and (listp reference) (> (length reference) 6))
                       (nth 0 reference) nil))
          (if (or (not axis)
                  (not (urb:curve-entity-p axis))
                  (not (urb:grade-records-valid-p (nth 1 reference))))
            (progn
              (urb:mark-anden-earthworks-status
                block-object "PENDIENTE - rasante no disponible")
              (prompt "\nNo se calculo el movimiento: rasante no disponible.")
              nil)
            (progn
              (setq *urb-anden-earthwork-stage* "generacion de malla interior")
              (urb:bb-log (strcat "TIERRAS: malla interior, vertices=" (itoa (length points))))
              (setq samples (urb:earthwork-area-samples points)
                    total-weight 0.0)
              (foreach sample samples (setq total-weight (+ total-weight (cadr sample))))
              (urb:bb-log (strcat "TIERRAS: malla lista, muestras=" (itoa (length samples))))
              (setq total (length samples))
              (setq edge-result
                (vl-catch-all-apply
                  'urb:anden-axis-edge-offset (list (if edge-points edge-points points) axis)))
              (setq edge-offset
                (if (vl-catch-all-error-p edge-result) nil edge-result))
              (if (or (null edge-offset) (= total 0))
                (progn
                  (urb:mark-anden-earthworks-status
                    block-object "PENDIENTE - geometria no evaluable")
                  (prompt
                    "\nNo se calculo el movimiento: no fue posible evaluar la geometria.")
                  nil)
                (progn
                  (setq *urb-anden-earthwork-stage* "muestreo de superficie y rasante")
                  (urb:bb-log "TIERRAS: inicia consulta TN/rasante")
                  (setq cut-depth 0.0 fill-depth 0.0 count 0 slope-count 0
                        transverse-percent (* 100.0 *urb-anden-crossfall*))
                  (foreach sample samples
                    (setq p (car sample) weight (cadr sample))
                    (setq terrain
                      (urb:surface-elevation surface (car p) (cadr p)))
                    (setq finish-result
                      (vl-catch-all-apply
                        'urb:anden-grade-at-point
                        (list p reference edge-offset)))
                    (setq finish
                      (if (vl-catch-all-error-p finish-result)
                        nil
                        finish-result))
                    (if (and (numberp terrain) (numberp finish))
                      (progn
                        ;; 5.6.5: sobreexcavacion del material no portante
                        (setq delta
                          (urb:cut-fill-at (- terrain (- finish *urb-anden-depth*))))
                        (setq cut-depth (+ cut-depth (* weight (car delta)))
                              fill-depth (+ fill-depth (* weight (cadr delta))))
                        (setq count (1+ count))
                        (setq slope-result
                          (vl-catch-all-apply
                            'urb:anden-longitudinal-slope-at-point
                            (list p reference)))
                        (setq long-slope
                          (if (vl-catch-all-error-p slope-result)
                            nil
                            slope-result))
                        (if (numberp long-slope)
                          (progn
                            (setq total-slope
                              (sqrt
                                (+ (* long-slope long-slope)
                                   (* transverse-percent transverse-percent))))
                            (if (or (null long-min) (< long-slope long-min))
                              (setq long-min long-slope))
                            (if (or (null long-max) (> long-slope long-max))
                              (setq long-max long-slope))
                            (if (or (null total-min) (< total-slope total-min))
                              (setq total-min total-slope))
                            (if (or (null total-max) (> total-slope total-max))
                              (setq total-max total-slope))
                            (setq slope-count (1+ slope-count)))))))
                  (setq coverage
                    (if (> total 0) (/ (float count) (float total)) 0.0))
                  (setq required total)
                  (setq coverage-text
                    (strcat (rtos (* 100.0 coverage) 2 1) "%"))
                  (if (or (< count required)
                          (> (abs (- total-weight area)) (max 0.001 (* area 0.0001))))
                    (progn
                      (urb:set-block-attribute
                        block-object "ANDEN_MUESTRAS"
                        (strcat (itoa count) "/" (itoa total)))
                      (urb:set-block-attribute
                        block-object "ANDEN_COBERTURA" coverage-text)
                      (urb:mark-anden-earthworks-status
                        block-object "PENDIENTE - cobertura insuficiente")
                      (prompt
                        (strcat
                          "\nNo se calculo el movimiento: cobertura de superficie "
                          coverage-text " (" (itoa count) "/" (itoa total)
                          " muestras; minimo " (itoa required) ")."))
                      nil)
                    (progn
                      (setq *urb-anden-earthwork-stage* "guardado de resultados")
                      (setq corte (* area (/ cut-depth total-weight)))
                      (setq relleno (* area (/ fill-depth total-weight)))
                      (setq pend-long-text
                        (urb:percent-range-text long-min long-max))
                      (setq pend-trans-text
                        (strcat (rtos transverse-percent 2 2) "%"))
                      (setq pend-total-text
                        (urb:percent-range-text total-min total-max))
                      (setq method
                        (strcat "OK - " (urb:safe-string (nth 6 reference) "Rasante")
                          " - triangulos ponderados con sobreancho"
                          " | pendientes automaticas"
                          " | estructura " (rtos *urb-anden-depth* 2 2) " m"
                          " | " (urb:overexc-text)))
                      (setq via-id
                        (urb:safe-string
                          (if (> (length reference) 7) (nth 7 reference) nil) ""))
                      (setq via-name
                        (urb:safe-string
                          (if (> (length reference) 8) (nth 8 reference) nil) ""))
                      (urb:set-xdata-strings ename "URB_ANDEN_MOV"
                        (list "ANDEN_MOV" method
                          (rtos corte 2 6) (rtos relleno 2 6)
                          (itoa count) (urb:safe-string surface-name "")
                          (itoa total) (rtos coverage 2 6)
                          via-id via-name
                          pend-long-text pend-trans-text pend-total-text))
                      (urb:set-block-attribute
                        block-object "ANDEN_PEND_LONG" pend-long-text)
                      (urb:set-block-attribute
                        block-object "ANDEN_PEND_TRANS" pend-trans-text)
                      (urb:set-block-attribute
                        block-object "ANDEN_PEND_TOTAL" pend-total-text)
                      (urb:set-block-attribute
                        block-object "ANDEN_CORTE_M3" (rtos corte 2 2))
                      (urb:set-block-attribute
                        block-object "ANDEN_RELLENO_M3" (rtos relleno 2 2))
                      (urb:set-block-attribute block-object "ANDEN_METODO" method)
                      (urb:set-block-attribute
                        block-object "ANDEN_MUESTRAS"
                        (strcat (itoa count) "/" (itoa total)))
                      (urb:set-block-attribute
                        block-object "ANDEN_COBERTURA" coverage-text)
                      (urb:set-block-attribute
                        block-object "ANDEN_VIA_ID" via-id)
                      (urb:set-block-attribute
                        block-object "ANDEN_VIA_NOMBRE" via-name)
                      (vla-Update block-object)
                      (prompt
                        (strcat "\nMovimiento de tierras (anden): corte "
                          (rtos corte 2 2) " m3 | relleno "
                          (rtos relleno 2 2) " m3 | cobertura "
                          coverage-text " | pendiente longitudinal "
                          pend-long-text " | transversal "
                          pend-trans-text " | resultante "
                          pend-total-text "."))
                      T)))))))))))

;; 2026-09-07 (pedido del usuario: MT implicito, "solo espichar una o
;; varias cotas de implantacion"): corte/relleno del anden con el MISMO
;; motor de plano de zonas verdes/senderos (urb:earthworks-from-picks)
;; sobre su contorno. La superficie es automatica (SUP_TN); 1 cota =
;; plano horizontal, 2 = rasante lineal, 3+ = plano ajustado. Enter sin
;; cotas = queda PENDIENTE (se puede recalcular con EDITAR).
;; Muestrear los arcos en coordenadas del bloque y transformar a WCS.
;; En AutoLISP OR retorna T: nunca usarlo como alternativa entre puntos.
(defun urb:anden-earthwork-raw-points
  (item / en data pair verts pt bulge tail v next p q b chord theta k n out normal elevation
   radius h phi halfsin along across ux uy)
  (setq en (urb:as-ename item) data (entget en))
  (setq normal (cdr (assoc 210 data)) elevation (cdr (assoc 38 data)))
  (if (not normal) (setq normal '(0.0 0.0 1.0)))
  (if (not elevation) (setq elevation 0.0))
  (foreach pair data
    (cond
      ((= (car pair) 10)
        (if pt (setq verts (cons (list pt bulge) verts)))
        (setq pt (list (cadr pair) (caddr pair) elevation) bulge 0.0))
      ((= (car pair) 42) (setq bulge (cdr pair)))))
  (if pt (setq verts (reverse (cons (list pt bulge) verts))))
  (setq tail verts)
  (while tail
    (setq v (car tail) next (if (cdr tail) (cadr tail) (car verts))
          p (car v) q (car next) b (cadr v) chord (distance p q))
    ;; TRANS por ename devuelve nil para entidades dentro de una definicion.
    ;; Su normal OCS explicita funciona en ModelSpace y dentro del bloque.
    (setq out (cons (trans p normal 0) out))
    (if (and (> (abs b) 1e-10) (> chord 1e-10))
      (progn
        ;; Coordenadas locales estables: no restar centro/radio gigantes
        ;; en microarcos. El minimo fijo de8 sobremuestreaba cada microarco.
        ;; Flecha de cuerda <=0.00001m (0.01mm), conservando arco en el DWG.
        (setq theta (* 4.0 (atan b))
              radius (/ (* chord (+ 1.0 (* b b))) (* 4.0 (abs b)))
              h (/ (* chord (- 1.0 (* b b))) (* 4.0 b))
              ux (/ (- (car q) (car p)) chord)
              uy (/ (- (cadr q) (cadr p)) chord)
              n (max 1 (1+ (fix (* (abs theta) (sqrt (/ radius 0.00008)))))) k 1)
        (repeat (1- n)
          (setq phi (* theta (/ (float k) n)) halfsin (sin (* 0.5 phi))
                along (+ (* chord halfsin halfsin) (* h (sin phi)))
                across (- (* 2.0 h halfsin halfsin) (* 0.5 chord (sin phi)))
                out (cons
                  (trans (list (+ (car p) (* along ux) (* (- across) uy))
                               (+ (cadr p) (* along uy) (* across ux)) elevation) normal 0) out)
                k (1+ k)))))
    (setq tail (cdr tail)))
  (reverse out))

(defun urb:anden-earthwork-points (block-ref / obj def item transform raw base)
  (setq obj (urb:as-vla-object block-ref))
  (if obj
    (progn
      (setq def (vla-Item (vla-get-Blocks (urb:doc)) (vla-get-Name obj))
            transform (urb:block-instance-transform obj)
            base (cdr (assoc 10 (tblsearch "BLOCK" (vla-get-Name obj)))))
      (if (not base) (setq base '(0.0 0.0 0.0)))
      ;; 5.6.2: el rol vive en XDATA y leerlo en cada loseta costaba ~40 s
      ;; en un anden real; solo una polilinea puede ser el contorno
      (vlax-for item def
        (if (and (null raw)
                 (= (vla-get-ObjectName item) "AcDbPolyline")
                 (= (urb:generated-role item) "EARTHWORK_BOUNDARY"))
          (setq raw (urb:anden-earthwork-raw-points item))))
      (mapcar '(lambda (p)
        (urb:xref-local-to-world (mapcar '- (urb:point3d-list p) base) transform))
        raw))))

(defun urb:anden-earthwork-area (block-ref / obj def item area)
  (setq obj (urb:as-vla-object block-ref)
        def (vla-Item (vla-get-Blocks (urb:doc)) (vla-get-Name obj)))
  (vlax-for item def
    (if (and (null area)
             (= (vla-get-ObjectName item) "AcDbPolyline")
             (= (urb:generated-role item) "EARTHWORK_BOUNDARY"))
      (setq area (* (vla-get-Area item)
        (abs (* (vla-get-XScaleFactor obj) (vla-get-YScaleFactor obj)))))))
  (if area area 0.0))

(defun urb:anden-earthworks-por-cotas (block-ref points / picks pts pl mov exact-area sampled-area)
  (prompt (strcat "\nCotas de IMPLANTACION del anden"
    " (via/pozo/etiqueta o Digitar; Enter sin cotas = pendiente):"))
  (setq picks (urb:pick-design-cotas))
  (if (and picks (>= (length picks) 1))
    (progn
      (setq points (urb:anden-earthwork-points block-ref))
      (if (not points)
        (vl-exit-with-error "ANDEN: falta la huella de sobreancho; regenere el bloque antes de calcular tierras."))
      (setq pts (mapcar '(lambda (p) (list (car p) (cadr p))) points))
      (entmake (append
        (list '(0 . "LWPOLYLINE") '(100 . "AcDbEntity")
              '(100 . "AcDbPolyline") (cons 90 (length pts)) '(70 . 1))
        (mapcar '(lambda (p) (cons 10 p)) pts)))
      (setq pl (entlast))
      (setq exact-area (urb:anden-earthwork-area block-ref)
            sampled-area (vla-get-Area (vlax-ename->vla-object pl)))
      ;; anden: se excava hasta la subrasante (terminado - 0.60 de estructura)
      (setq mov (vl-catch-all-apply 'urb:earthworks-from-picks
        (list pl picks *urb-anden-depth*)))
      (if (and pl (entget pl)) (entdel pl))
      (if (and mov (not (vl-catch-all-error-p mov)))
        (progn
          (setq mov (mapcar '(lambda (v) (* v (/ exact-area sampled-area))) mov))
          (urb:set-xdata-strings (urb:as-ename block-ref) "URB_ANDEN_MOV"
            (list "ANDEN_MOV" "OK - cotas con sobreancho"
              (rtos (car mov) 2 6) (rtos (cadr mov) 2 6)))
          (urb:set-block-attribute block-ref "ANDEN_CORTE_M3"
            (rtos (car mov) 2 2))
          (urb:set-block-attribute block-ref "ANDEN_RELLENO_M3"
            (rtos (cadr mov) 2 2))
          (urb:mark-anden-earthworks-status block-ref
            "OK - cotas de implantacion")
          (prompt (strcat "\nCorte: " (rtos (car mov) 2 2)
            " m3 | Relleno: " (rtos (cadr mov) 2 2) " m3"))
          T)
        (progn
          (urb:mark-anden-earthworks-status block-ref
            "PENDIENTE - sin superficie SUP_TN")
          nil)))
    (progn
      (urb:mark-anden-earthworks-status block-ref
        "PENDIENTE - sin cotas de implantacion")
      T)))

(defun urb:prompt-anden-earthworks
  (block-ref points area calculate surface grade-source / result)
  (if (urb:yes-p calculate)
    (progn
      (setq result
        (vl-catch-all-apply
          'urb:run-anden-earthworks
          (list block-ref points area surface grade-source)))
      (if (vl-catch-all-error-p result)
        (progn
          (urb:mark-anden-earthworks-status
            block-ref "PENDIENTE - error de calculo")
          (prompt
            (strcat
              "\nERROR al calcular movimiento del anden: "
              (vl-catch-all-error-message result)
              " | etapa: "
              (urb:safe-string *urb-anden-earthwork-stage* "desconocida")))
          nil)
        result))
    T)
)

(defun urb:anden-earthworks-totals (/ ss index ename data cut fill count)
  (setq cut 0.0 fill 0.0 count 0)
  (if (setq ss (ssget "_X" '((-3 ("URB_ANDEN_MOV")))))
    (progn
      (setq index 0)
      (repeat (sslength ss)
        (setq ename (ssname ss index))
        (setq data (urb:get-xdata-strings ename "URB_ANDEN_MOV"))
        (if (and (listp data)
                 (> (length data) 3)
                 (urb:string-equal-p (car data) "ANDEN_MOV"))
          (progn
            (setq cut (+ cut (atof (urb:safe-string (nth 2 data) "0"))))
            (setq fill (+ fill (atof (urb:safe-string (nth 3 data) "0"))))
            (setq count (1+ count))))
        (setq index (1+ index)))))
  (list cut fill count)
)

(defun urb:valid-anden-earthworks-data-p (data)
  (and
    (listp data)
    (> (length data) 7)
    (urb:string-equal-p (car data) "ANDEN_MOV")
    (> (atoi (urb:safe-string (nth 4 data) "0")) 0)
    (>= (atof (urb:safe-string (nth 7 data) "0"))
        *urb-anden-min-coverage*))
)

(defun urb:create-sidewalk-command
  (/ data material format etapa subetapa guia toperol calculate surface
   grade-source ename result block-ref anden-points anden-area
   earthworks-ok orientation-choice start-choice pattern-mode
   old-fillmode doc undo-open undo-result *error* mod-p1 mod-p2 mod-angle
   costados-res anillo-refs anillo-pos clip-area)
  (setq doc (urb:doc) old-fillmode (getvar "FILLMODE"))
  (defun *error* (message)
    (if (and ename (not block-ref))
      (vl-catch-all-apply 'urb:discard-unpacked-anden (list ename)))
    (setq *urb-current-tactile-side-point* nil
          *urb-current-tactile-side-anchor* nil
          *urb-current-tactile-side-choice* nil)
    (if old-fillmode
      (progn (setvar "FILLMODE" old-fillmode) (vla-Regen doc 1)))
    (if undo-open
      (progn
        (vl-catch-all-apply 'vla-EndUndoMark (list doc))
        (setq undo-open nil)))
    (if (and message
             (not (member message '("Function cancelled" "quit / exit abort"))))
      (prompt (strcat "\nERROR EN ANDEN: " message)))
    (princ))
  (setq undo-result
    (vl-catch-all-apply 'vla-StartUndoMark (list doc)))
  (setq undo-open (not (vl-catch-all-error-p undo-result)))
  (setq *urb-current-tactile-side-point* nil
        *urb-current-tactile-side-anchor* nil
        *urb-current-tactile-side-choice* nil)
  ;; Orientacion y extremo viven DENTRO del dialogo. El lado de la via
  ;; (toperol) se marca con UN click despues de dibujar: con andenes
  ;; diagonales una palabra tipo "arriba/abajo" es ambigua, el click sobre
  ;; el lado real no.
  (setq data
    (if (urb:confirm-meter-units)
      (urb:dialog-anden "Loseta" "40 x 40 cm" "1" "1" "No" "No"
        "Si" "SUP_TN" "Via creada"
        "Automatico" "Normal"
        '("Automatico" "Girar90") '("Normal" "Opuesto"))
      nil))
  ;; 2026-09-07: mismo icono para todas las areas -- la variante viaja
  ;; como CODIGO de *urb-send-tipos* en nth 14 ("" = anden en loseta).
  ;; Cualquier codigo delega al flujo de poligono+receta con sus capas,
  ;; colores y capitulo de presupuesto propios.
  (if (and data (> (length data) 14)
           (= (type (nth 14 data)) 'STR) (/= (nth 14 data) ""))
    (progn
      (urb:poly-element-draw
        (assoc (nth 14 data) *urb-send-tipos*)
        (nth 2 data) (nth 3 data)
        (nth 11 data) (nth 12 data) (nth 13 data)
        "URB_SENDERO")
      (setq data nil)))
  (if data
    (progn
      (setq material (nth 0 data))
      (setq format (nth 1 data))
      (setq etapa (nth 2 data))
      (setq subetapa (nth 3 data))
      (setq guia (nth 4 data))
      (setq toperol (nth 5 data))
      (setq calculate (nth 6 data))
      (setq surface (nth 7 data))
      (setq grade-source (nth 8 data))
      (setq orientation-choice (nth 9 data))
      (setq start-choice (nth 10 data))
      (setq ename (urb:draw-closed-polyline)))
  )
  (if ename
    (progn
      (setq pattern-mode
        (urb:compose-anden-pattern-mode
          (= orientation-choice "Girar90")
          (= start-choice "Opuesto")))
      (setq anden-points (urb:lwpoly-points ename))
      (setq anden-area (vla-get-Area (vlax-ename->vla-object ename)))
      (setq *urb-current-tactile-side-point* nil
            *urb-current-tactile-side-anchor* nil
            *urb-current-tactile-side-choice* nil)
      ;; 5.7.18: los dos puntos marcan el EJE LONGITUDINAL (direccion del
      ;; recorrido); las bandas quedan perpendiculares. Antes se pedia la
      ;; direccion de las bandas y se sumaban 90 grados: si el usuario
      ;; marcaba el eje visual, el patron quedaba girado. Enter conserva
      ;; la deteccion automatica historica.
      (if (urb:lwpoly-has-arcs-p ename)
        (progn
          (setq mod-p1
            (getpoint
              (strcat "\nContorno con curva -- marque 2 puntos sobre el EJE"
                      " LONGITUDINAL del anden (Enter = automatico): ")))
          (if mod-p1
            (setq mod-p2
              (getpoint mod-p1 "\nSegundo punto sobre el eje longitudinal: ")))
          (setq mod-angle
            (urb:anden-axis-from-user-points mod-p1 mod-p2
              (urb:anden-straight-edges-angle ename)))
          (if mod-angle
            (urb:set-xdata-strings ename "URB_ANDEN_AXIS"
              (list (rtos mod-angle 2 8))))))
      (urb:set-anden-data
        ename material etapa subetapa guia toperol format calculate surface grade-source)
      (if *urb-current-tactile-side-anchor*
        (urb:set-tactile-side-data ename
          *urb-current-tactile-side-anchor*))
      (if (or (urb:yes-p guia) (urb:yes-p toperol))
        (urb:confirm-tactile-side ename))
      (urb:set-anden-pattern-mode ename pattern-mode)
      ;; 2026-08-24 (pedido del usuario): prefabricado por COSTADOS igual
      ;; que el sendero -- se construyen solos sobre los dos lados largos
      ;; del contorno (data 11 = tipo derecha, 12 = tipo izquierda,
      ;; 13 = posicion), cada uno como bloque independiente. Se construye
      ;; ANTES del acabado y del empaquetado: v4.76 resta su huella fisica
      ;; de las losetas/tactiles, en vez de limitarse a ponerlo al frente.
      ;; 5.6.2 (pedido del usuario): el prefabricado ya no sale de la
      ;; ventana -- costado por costado, como en las vias (tipo, sentido
      ;; Interno/Externo y tramos sin prefabricado). Cada bloque guarda SU
      ;; sentido en URB_PREFAB_ANILLO, porque un anden puede llevar un
      ;; costado interno y el otro externo.
      (setq anillo-refs nil anillo-pos nil)
      (setq costados-res
        (vl-catch-all-apply 'urb:poly-costados-interactive
          (list ename etapa subetapa "Anden")))
      (if (vl-catch-all-error-p costados-res)
        (progn
          (prompt (strcat "\nPrefabricado por costados omitido: "
            (vl-catch-all-error-message costados-res)))
          (setq costados-res nil)))
      (setq anillo-refs (cadr costados-res)
            anillo-pos (nth 5 costados-res))
      ;; Vinculo temporal al contorno: permite que el generador de acabado
      ;; encuentre los costados recién creados. Tras empaquetar se sustituye
      ;; por el handle definitivo del bloque de anden.
      (if anillo-refs
        (foreach aref anillo-refs
          (vl-catch-all-apply
            '(lambda ()
              (urb:set-xdata-strings
                (vlax-vla-object->ename aref) "URB_PREFAB_ANILLO"
                (list (vla-get-Handle (urb:as-vla-object ename))
                      (urb:safe-string (cdr (assoc aref anillo-pos)) "Externo")))))))
      ;; 2026-09-08 (pedido del usuario: "solo el bloque del anden tiene
      ;; que estar entre los prefabricados"): el CONTORNO se recorta
      ;; fisicamente contra los prefabricados recien creados y contra los
      ;; contenedores, de modo que el bloque del anden TERMINE donde
      ;; empieza el bordillo, no por debajo. El acabado, el area y el
      ;; perimetro se calculan ya sobre ese contorno neto; si el recorte
      ;; no es posible el contorno queda intacto y todo sigue como en
      ;; v4.77 (el acabado se recorta igual).
      ;; 5.6.2: caja negra (ver urb:bb-log) en cada etapa pesada
      (urb:bb-log (strcat "CREAR anden: contorno "
        (itoa (length (urb:lwpoly-points ename))) " vertices, arcos "
        (if (urb:lwpoly-has-arcs-p ename) "SI" "NO")
        ", area " (rtos (vla-get-Area (vlax-ename->vla-object ename)) 2 2)
        ", guia " guia ", toperol " toperol ", formato " format))
      (urb:bb-log "INICIA recorte del contorno")
      (setq clip-area
        (vl-catch-all-apply (function urb:anden-clip-contour) (list ename)))
      (urb:bb-log "TERMINA recorte del contorno")
      (if (and (not (vl-catch-all-error-p clip-area)) (numberp clip-area))
        (prompt
          (strcat "\nContorno del anden recortado a " (rtos clip-area 2 2)
                  " m2: queda entre los prefabricados.")))
      (urb:bb-log "INICIA acabado (losetas, guia, toperol)")
      (setq result
        (urb:build-anden-finish ename material guia toperol format))
      (urb:bb-log (strcat "TERMINA acabado " (if result "OK" "SIN RESULTADO")))
      (if result
        (progn
          (urb:bb-log "INICIA empaquetado en bloque")
          (setq block-ref (urb:package-anden ename))
          (urb:bb-log (strcat "TERMINA empaquetado " (if block-ref "OK" "FALLO")))))
      ;; vinculo costado->anden para el descuento de area cuando es
      ;; Interno: la MISMA xdata URB_PREFab_ANILLO de siempre (handle del
      ;; anden + posicion) sobre CADA bloque de costado -- el descuento
      ;; lo sigue haciendo urb:anden-area-anillos leyendo el AREA_M2 de
      ;; cada bloque, sin cambios.
      (if (and anillo-refs block-ref)
        (foreach aref anillo-refs
          (vl-catch-all-apply
            '(lambda ()
              (urb:set-xdata-strings
                (vlax-vla-object->ename aref)
                "URB_PREFAB_ANILLO"
                (list
                  (vla-get-Handle (urb:as-vla-object block-ref))
                  (urb:safe-string (cdr (assoc aref anillo-pos)) "Externo")))
              ;; 2026-08-26 (reporte del usuario: el anden quedaba POR
              ;; ENCIMA del bordillo): el bloque del anden se inserta
              ;; DESPUES de los costados y su achurado tapaba la franja
              ;; interna -- el costado pasa al frente.
              (command "_.DRAWORDER"
                (vlax-vla-object->ename aref) "" "_Front")))))
      (setvar "FILLMODE" 1)
      (vla-Regen (urb:doc) 1)
      (if block-ref
        (progn
          ;; 2026-09-15: usar el perfil completo de la via cuando el usuario
          ;; activa movimiento. Esto interpola las cotas guardadas en cada
          ;; estacion; no reduce una via con pendientes variables a un solo
          ;; punto clickeado. El calculo generico por cotas queda disponible
          ;; para senderos/zonas sin via mediante EDITAR.
          (setq earthworks-ok
            (if (urb:yes-p calculate)
              (urb:prompt-anden-earthworks
                block-ref anden-points anden-area calculate surface grade-source)
              T))
          (prompt
            (strcat
              "\nAnden creado: " (strcase material)
              " | Etapa " etapa
              " | Subetapa " subetapa
              (if (and (urb:yes-p calculate) (not earthworks-ok))
                " | Movimiento de tierras PENDIENTE."
                "."))))
        (progn
          (urb:discard-unpacked-anden ename)
          (prompt "\nNo se creo el bloque del anden. Se retira el acabado incompleto y se conserva el contorno para reintentar."))))
    (if data
      (prompt "\nNo se creo una polilinea valida.")
        (prompt "\nComando cancelado.")))
  (setq *urb-current-tactile-side-point* nil
        *urb-current-tactile-side-anchor* nil
        *urb-current-tactile-side-choice* nil)
  ;; Restaurar FILLMODE al valor original del usuario no alcanza si no se
  ;; regenera despues: el REGEN de mas arriba (FILLMODE=1, para que se vea
  ;; el relleno del anden) deja en pantalla TODO objeto rellenable del
  ;; dibujo mostrado solido -- incluidas regiones/hatches de otras partes
  ;; del proyecto que no tienen nada que ver con este anden (ej. lotes de
  ;; LOTEO FINAL). La variable vuelve a su valor, pero la vista se queda
  ;; regenerada con FILLMODE=1 hasta el proximo REGEN. Con este regen
  ;; final la vista vuelve a coincidir con el FILLMODE real del usuario.
  (if old-fillmode
    (progn (setvar "FILLMODE" old-fillmode) (vla-Regen doc 1)))
  (if undo-open
    (progn
      (vl-catch-all-apply 'vla-EndUndoMark (list doc))
      (setq undo-open nil)))
  (princ)
)

(defun urb:parent-anden-ename
  (ename / metadata generated parent parent-handle obj layer)
  (cond
    ((urb:anden-block-p ename)
      ename)
    ((setq metadata
       (urb:get-xdata-strings ename "URB_ANDEN"))
      (if (urb:string-equal-p (car metadata) "ANDEN") ename nil))
    ((setq generated
       (urb:get-xdata-strings ename "URB_ANDEN_GEN"))
      (setq parent-handle
        (urb:safe-string (car generated) ""))
      (setq parent
        (if (> (strlen parent-handle) 0)
          (vl-catch-all-apply 'handent (list parent-handle))))
      (if (vl-catch-all-error-p parent) (setq parent nil))
      (if (and parent
               (setq metadata
                 (urb:get-xdata-strings parent "URB_ANDEN"))
               (urb:string-equal-p (car metadata) "ANDEN"))
        parent
        nil))
    ((and
       (setq obj
         (vl-catch-all-apply
           'vlax-ename->vla-object
           (list ename)))
       (not (vl-catch-all-error-p obj))
       (setq layer (strcase (vla-get-Layer obj)))
       ;; "URB-Q-ANDEN-*" es el nombre viejo del contorno (antes de
       ;; consolidar capas); "URB-ANDEN" es el nombre actual.
       (or (urb:starts-with layer "URB-Q-ANDEN-") (= layer "URB-ANDEN"))
       (urb:closed-poly-p ename))
      ename)
    (T nil))
)

(defun urb:selected-anden-parents
  (selection / index ename parent handle handles parents)
  (setq index 0)
  (repeat (sslength selection)
    (setq ename (ssname selection index))
    (setq parent (urb:parent-anden-ename ename))
    (if parent
      (progn
        (setq handle
          (vla-get-Handle (vlax-ename->vla-object parent)))
        (if (not (member handle handles))
          (progn
            (setq handles (cons handle handles))
            (setq parents (cons parent parents))))))
    (setq index (1+ index)))
  (reverse parents)
)

(defun urb:prefab-block-p (ename)
  (if (urb:get-xdata-strings ename "URB_PREFAB_BLOCK") T nil)
)

(defun urb:prefab-data (ename / data)
  ;; or de AutoLISP devuelve T, no el valor -- cadena if explicita
  (setq data (urb:get-xdata-strings ename "URB_PREFAB_BLOCK"))
  (if data data (urb:get-xdata-strings ename "URB_PREFAB"))
)

(defun urb:selected-prefabs (selection / index ename data result)
  (setq index 0)
  (repeat (sslength selection)
    (setq ename (ssname selection index))
    (setq data (urb:prefab-data ename))
    (if data (setq result (cons ename result)))
    (setq index (1+ index)))
  (reverse result)
)

(defun urb:selected-mp-entities (selection / index ename result)
  (setq index 0)
  (repeat (sslength selection)
    (setq ename (ssname selection index))
    (if (mp:editable-entity-p ename)
      (setq result (cons ename result)))
    (setq index (1+ index)))
  (reverse result)
)

(defun urb:extract-prefab-reference
  (ename prefab mode / obj exploded objects item layer reference side-edge
   reference-layer side-layer reference-role side-role side-point role)
  (setq obj (vlax-ename->vla-object ename))
  (setq exploded (vl-catch-all-apply 'vla-Explode (list obj)))
  (if (vl-catch-all-error-p exploded)
    nil
    (progn
      (setq objects (urb:variant-object-list exploded))
      (if (urb:string-equal-p mode "Interior")
        (setq reference-role "EXTERIOR" side-role "INTERIOR")
        (setq reference-role "INTERIOR" side-role "EXTERIOR"))
      ;; 4.18.0: identifica interior/exterior por rol xdata (independiente
      ;; de la capa, ya consolidada). Bloques prefabricados de antes de
      ;; este cambio no tienen ese rol -- se cae al nombre de capa viejo
      ;; (URB-PREFAB-<TIPO>-INTERIOR/EXTERIOR) como respaldo.
      (foreach item objects
        (if (member (vla-get-ObjectName item)
              '("AcDbPolyline" "AcDb2dPolyline"))
          (progn
            (setq role (urb:generated-role item))
            (if (= role reference-role) (setq reference item))
            (if (= role side-role) (setq side-edge item)))))
      (if (not (and reference side-edge))
        (progn
          (setq reference-layer
            (strcat "URB-PREFAB-" (urb:prefab-token prefab) "-" reference-role))
          (setq side-layer
            (strcat "URB-PREFAB-" (urb:prefab-token prefab) "-" side-role))
          (foreach item objects
            (if (member (vla-get-ObjectName item)
                  '("AcDbPolyline" "AcDb2dPolyline"))
              (progn
                (setq layer (vla-get-Layer item))
                (if (urb:string-equal-p layer reference-layer)
                  (setq reference item))
                (if (urb:string-equal-p layer side-layer)
                  (setq side-edge item)))))))
      (if side-edge
        (setq side-point
          (vlax-curve-getStartPoint
            (vlax-vla-object->ename side-edge))))
      (foreach item objects
        (if (not (eq item reference)) (urb:safe-delete item)))
      (if (and reference side-point)
        (list (vlax-vla-object->ename reference) side-point)
        (progn
          (if reference (urb:safe-delete reference))
          nil))))
)

(defun urb:flip-side-point (reference-ename side-point / closest)
  (setq closest
    (vlax-curve-getClosestPointTo reference-ename side-point))
  (list
    (- (* 2.0 (car closest)) (car side-point))
    (- (* 2.0 (cadr closest)) (cadr side-point))
    (- (* 2.0 (if (caddr closest) (caddr closest) 0.0))
       (if (caddr side-point) (caddr side-point) 0.0)))
)

(defun urb:update-prefab-block-data
  (ename prefab width etapa subetapa mode destino / obj data length-value area-value)
  (setq obj (vlax-ename->vla-object ename))
  (setq data (urb:prefab-data ename))
  (setq length-value (urb:safe-string (nth 4 data) "0"))
  (setq area-value (* width (atof length-value)))
  (urb:set-xdata-strings
    ename "URB_PREFAB_BLOCK"
    (list prefab etapa subetapa (rtos width 2 8)
          length-value mode *urb-prefab-schema-version* destino))
  (urb:set-block-attribute obj "TIPO" (strcase prefab))
  (urb:set-block-attribute obj "ANCHO_M" (rtos width 2 3))
  (urb:set-block-attribute obj "AREA_M2" (rtos area-value 2 2))
  (urb:set-block-attribute obj "ETAPA" etapa)
  (urb:set-block-attribute obj "SUBETAPA" subetapa)
  (urb:set-block-attribute obj "MODELADO" mode)
  (urb:set-block-attribute obj "DESTINO_PPTO" destino)
  T
)

(defun urb:edit-prefabs
  (prefabs / first-data dialog-data prefab width etapa subetapa mode destino
   ename data old-prefab old-width old-mode extracted reference side-point
   new-block new-ename obj copy-obj copy-ename updated failed deleted)
  (setq first-data (urb:prefab-data (car prefabs)))
  (setq prefab (urb:safe-string (nth 0 first-data) "Bordillo"))
  (setq width (atof (urb:safe-string (nth 3 first-data) "0.20")))
  (setq etapa (urb:safe-string (nth 1 first-data) "1"))
  (setq subetapa (urb:safe-string (nth 2 first-data) etapa))
  (setq mode (urb:safe-string (nth 5 first-data) "Interior"))
  (setq destino
    (urb:safe-string (nth 7 first-data)
      (urb:prefab-destino-default prefab)))
  (setq dialog-data
    (urb:dialog-prefab prefab width etapa subetapa mode destino))
  (if dialog-data
    (progn
      (setq prefab (nth 0 dialog-data))
      (setq width (nth 1 dialog-data))
      (setq etapa (nth 2 dialog-data))
      (setq subetapa (nth 3 dialog-data))
      (setq mode (nth 4 dialog-data))
      (setq destino (nth 5 dialog-data))
      (setq updated 0 failed 0 deleted 0)
      (foreach ename prefabs
        (setq new-block nil extracted nil reference nil side-point nil)
        (setq data (urb:prefab-data ename))
        (setq old-prefab (urb:safe-string (nth 0 data) "Bordillo"))
        (setq old-width (atof (urb:safe-string (nth 3 data) "0.20")))
        (setq old-mode (urb:safe-string (nth 5 data) "Interior"))
        (if (urb:prefab-block-p ename)
          (if (and (urb:string-equal-p old-prefab prefab)
                   (equal old-width width 0.0000001)
                   (urb:string-equal-p old-mode mode))
            (progn
              (urb:update-prefab-block-data
                ename prefab width etapa subetapa mode destino)
              (setq updated (1+ updated)))
            (progn
              (setq extracted
                (urb:call-edit-stage
                  "extraer prefabricado"
                  'urb:extract-prefab-reference
                  (list ename old-prefab old-mode)))
              (if extracted
                (progn
                  (setq reference (car extracted))
                  (setq side-point (cadr extracted))
                  (if (not (urb:string-equal-p old-mode mode))
                    (setq side-point
                      (urb:flip-side-point reference side-point)))
                  (setq new-block
                    (urb:call-edit-stage
                      "reconstruir prefabricado"
                      'urb:build-prefab-from-reference
                       (list reference side-point prefab width
                            etapa subetapa mode destino)))
                  (if new-block
                    (progn
                      (urb:copy-quantity-scope ename new-block)
                      (if
                      (urb:call-edit-stage
                        "reemplazar prefabricado anterior"
                        'urb:delete-anden-block
                        (list ename))
                      (setq updated (1+ updated))
                      (progn
                        (setq new-ename (urb:as-ename new-block))
                         (if new-ename
                           (urb:delete-anden-block new-ename))
                         (setq failed (1+ failed)))))
                    (setq failed (1+ failed))))
                (setq failed (1+ failed)))))
          (progn
            (setq obj (vlax-ename->vla-object ename))
            (setq copy-obj (vla-Copy obj))
            (if (vlax-property-available-p copy-obj 'ConstantWidth T)
              (vla-put-ConstantWidth copy-obj 0.0))
            (setq copy-ename (vlax-vla-object->ename copy-obj))
            (setq side-point
              (getpoint
                (strcat
                  "\nMarque el lado " mode
                  " para convertir el prefabricado anterior: ")))
            (if side-point
              (setq new-block
                (urb:build-prefab-from-reference
                  copy-ename side-point prefab width
                  etapa subetapa mode destino)))
            (if new-block
              (progn
                (urb:copy-quantity-scope ename new-block)
                (if (urb:safe-delete obj)
                  (progn
                    (setq updated (1+ updated))
                    (setq deleted (1+ deleted)))
                  (progn
                    (setq new-ename (urb:as-ename new-block))
                    (if new-ename (urb:delete-anden-block new-ename))
                    (setq failed (1+ failed)))))
              (progn
                (urb:safe-delete copy-obj)
                (setq failed (1+ failed))))))
      )
      (vla-Regen (urb:doc) 1)
      (prompt
        (strcat
          "\nPrefabricados actualizados: " (itoa updated)
          " | Fallidos: " (itoa failed)
          " | Anteriores convertidos: " (itoa deleted) "."))))
  T
)

(defun urb:variant-object-list (value / raw)
  (cond
    ((= (type value) 'LIST) value)
    ((= (type value) 'VARIANT)
      (setq raw (vlax-variant-value value))
      (if (= (type raw) 'SAFEARRAY)
        (vlax-safearray->list raw)
        nil))
    ((= (type value) 'SAFEARRAY)
      (vlax-safearray->list value))
    (T nil))
)

(defun urb:objects-bbox-overlap-p (first second tolerance / a1 a2 b1 b2 r1 r2)
  (setq tolerance (if (numberp tolerance) tolerance 0.0)
        r1 (vl-catch-all-apply 'vla-GetBoundingBox (list first 'a1 'a2))
        r2 (vl-catch-all-apply 'vla-GetBoundingBox (list second 'b1 'b2)))
  (if (and (not (vl-catch-all-error-p r1))
           (not (vl-catch-all-error-p r2)))
    (progn
      (setq a1 (vlax-safearray->list a1) a2 (vlax-safearray->list a2)
            b1 (vlax-safearray->list b1) b2 (vlax-safearray->list b2))
      (and (<= (- (car a1) tolerance) (+ (car b2) tolerance))
           (>= (+ (car a2) tolerance) (- (car b1) tolerance))
           (<= (- (cadr a1) tolerance) (+ (cadr b2) tolerance))
           (>= (+ (cadr a2) tolerance) (- (cadr b1) tolerance))))
    nil)
)

(defun urb:block-footprint-region (block-ref / obj exploded items curves result
                                    regions candidate area best best-area)
  ;; Explota una COPIA logica de la referencia y reconstruye la huella
  ;; cerrada mayor. Funciona para prefabricados (2 polilineas abiertas +
  ;; remates) y para contenedores (marcos rectangulares cerrados).
  (setq obj (urb:as-vla-object block-ref)
        exploded
          (if obj (vl-catch-all-apply 'vla-Explode (list obj))))
  (if (and exploded (not (vl-catch-all-error-p exploded)))
    (progn
      (setq items (urb:variant-object-list exploded))
      (foreach candidate items
        (if (member (vla-get-ObjectName candidate)
              '("AcDbLine" "AcDbPolyline" "AcDb2dPolyline" "AcDbArc"))
          (setq curves (cons candidate curves))))
      (if curves
        (setq result
          (vl-catch-all-apply 'vla-AddRegion
            (list (urb:space) (urb:object-array-variant curves)))))
      (if (and result (not (vl-catch-all-error-p result)))
        (setq regions (urb:variant-object-list result)))
      (foreach candidate regions
        (setq area (vl-catch-all-apply 'vla-get-Area (list candidate)))
        (if (and (numberp area) (> area (if best-area best-area 0.0)))
          (setq best candidate best-area area)))
      (foreach candidate regions
        (if (not (eq candidate best)) (urb:safe-delete candidate)))
      (foreach candidate items (urb:safe-delete candidate))))
  best
)

(defun urb:anden-cutout-blocks (/ filter ss i en result)
  ;; 2026-09-10 (pedido del usuario: "si dibujo un paso peatonal sobre algo
  ;; que ya esta dibujado, que me borre lo que quedaria por debajo, para
  ;; que no quede doble area"): los modulos de rampa / paso peatonal
  ;; (URB_RAMPA_*) entran como CORTADORES igual que los prefabricados y
  ;; los contenedores. Con esto un anden nuevo ya nace recortado bajo el
  ;; paso, y urb:recut-vecinos-bajo recorta los que ya existian.
  (foreach filter
    '(((0 . "INSERT") (-3 ("URB_PREFAB_BLOCK")))
      ((0 . "INSERT") (2 . "URB_MOB_CONT*"))
      ((0 . "INSERT") (2 . "URB_RAMPA_*")))
    (if (setq ss (ssget "_X" filter))
      (progn
        (setq i 0)
        (repeat (sslength ss)
          (setq en (ssname ss i))
          ;; 2026-09-11: el ACCESO VEHICULAR es una superposicion sobre el
          ;; anden (asi esta en el plano): el modulo entero NO corta. Lo que
          ;; corta son sus bordillos (aletas curvas y banda A-80), que ya
          ;; son prefabricados y entran por el primer filtro.
          (if (and (not (member en result))
                   (not (urb:string-equal-p
                          (car (urb:get-xdata-strings en "URB_RAMPA_BLOCK"))
                          "RAMPA-VEHICULAR")))
            (setq result (cons en result)))
          (setq i (1+ i))))))
  result
)

(defun urb:apply-anden-cutouts (base-region / en obj cutter candidate operation
                                old-area new-area removed)
  ;; Resta fisicamente prefabricados y contenedores ANTES de crear losetas,
  ;; juntas, guia o toperol. El patron conserva su origen y orientacion: el
  ;; obstaculo es un vacio, no una frontera que haga "rodear" las piezas.
  (foreach en (urb:anden-cutout-blocks)
    (setq obj (urb:as-vla-object en))
    (if (and obj (urb:objects-bbox-overlap-p base-region obj 0.02))
      (progn
        (setq cutter (urb:block-footprint-region obj))
        (if cutter
          (progn
            ;; El acabado se construye en Z=0; la huella puede venir de
            ;; Civil con una cota topografica. Boolean exige coplanaridad.
            (urb:region-align-elevation cutter base-region)
            (setq old-area (vl-catch-all-apply 'vla-get-Area (list base-region))
                  candidate (vl-catch-all-apply 'vla-Copy (list base-region)))
            (if (and (numberp old-area)
                     (not (vl-catch-all-error-p candidate)))
              (progn
                (setq operation
                  (vl-catch-all-apply 'vla-Boolean
                    (list candidate 2 cutter))) ; acSubtraction
                (setq new-area
                  (if (not (vl-catch-all-error-p operation))
                    (vl-catch-all-apply 'vla-get-Area (list candidate))))
                (if (and (numberp new-area)
                         (> new-area 1e-10)
                         (< new-area (- old-area 1e-8)))
                  (progn
                    (urb:safe-delete base-region)
                    (setq base-region candidate
                          removed (1+ (if removed removed 0))))
                  (urb:safe-delete candidate))))
            (urb:safe-delete cutter))))))
  (if removed
    (prompt (strcat "\nAnden: " (itoa removed)
      " prefabricado(s)/contenedor(es) omitidos fisicamente del acabado.")))
  base-region
)

(defun urb:anden-near-root-container-p (ename / obj ss i ce found)
  (setq obj (urb:as-vla-object ename)
        ss (ssget "_X" '((0 . "INSERT") (2 . "URB_MOB_CONT*")))
        i 0)
  (if (and obj ss)
    (while (and (< i (sslength ss)) (not found))
      (setq ce (urb:as-vla-object (ssname ss i)))
      (if (and ce (urb:objects-bbox-overlap-p obj ce 0.10)) (setq found T))
      (setq i (1+ i))))
  found
)

(defun urb:update-anden-block-data
  (ename material etapa subetapa guia toperol format calculate surface grade-source
   / obj data area perimeter smooth-area smooth-count guide-ml toperol-ml
   adoquin-area adoquin-count elevation pattern-mode)
  (setq material (urb:safe-string material "Loseta"))
  (setq etapa (urb:safe-string etapa "1"))
  (setq subetapa (urb:safe-string subetapa etapa))
  (setq guia (urb:safe-string guia "No"))
  (setq toperol (urb:safe-string toperol "No"))
  (setq format (urb:safe-string format "40 x 40 cm"))
  (setq obj (vlax-ename->vla-object ename))
  (setq data (urb:get-xdata-strings ename "URB_ANDEN_BLOCK"))
  (setq area (if data (nth 4 data) ""))
  (setq perimeter (if data (nth 5 data) ""))
  (setq smooth-area (if (> (length data) 13) (nth 13 data) "0"))
  (setq smooth-count (if (> (length data) 14) (nth 14 data) "0"))
  (setq guide-ml (if (> (length data) 15) (nth 15 data) "0"))
  (setq toperol-ml (if (> (length data) 16) (nth 16 data) "0"))
  (setq adoquin-area (if (> (length data) 17) (nth 17 data) "0"))
  (setq adoquin-count (if (> (length data) 18) (nth 18 data) "0"))
  (setq pattern-mode (urb:anden-pattern-mode ename))
  (setq elevation
    (if (> (length data) 19)
      (nth 19 data)
      (rtos
        (if (vlax-property-available-p obj 'InsertionPoint)
          (caddr
            (vlax-safearray->list
              (vlax-variant-value (vla-get-InsertionPoint obj))))
          0.0)
        2 8)))
  (urb:set-xdata-strings
    ename
    "URB_ANDEN_BLOCK"
    (list "ANDEN" (strcase material) etapa subetapa area perimeter
          *urb-schema-version* guia toperol format calculate surface grade-source
          smooth-area smooth-count guide-ml toperol-ml adoquin-area adoquin-count
          elevation pattern-mode))
  (urb:set-block-attribute obj "MATERIAL" (strcase material))
  (urb:set-block-attribute obj "ETAPA" etapa)
  (urb:set-block-attribute obj "SUBETAPA" subetapa)
  (urb:set-block-attribute obj "LOSETA_GUIA" guia)
  (urb:set-block-attribute obj "LOSETA_TOPEROL" toperol)
  (urb:set-block-attribute obj "FORMATO_LOSETA" format)
  (urb:set-block-attribute obj "ANDEN_SUPERFICIE" surface)
  (urb:set-block-attribute obj "ANDEN_RASANTE" grade-source)
  (urb:set-block-attribute obj "ADOQUIN_20X10_M2" adoquin-area)
  (urb:set-block-attribute obj "ADOQUIN_20X10_UND" adoquin-count)
  (urb:set-block-attribute obj "ANDEN_ELEVACION" elevation)
  (urb:set-block-attribute obj "ANDEN_SENTIDO" pattern-mode)
  (urb:repair-block-ref-order obj)
  T
)

(defun urb:migrate-anden-block (ename / data schema obj)
  (setq data (urb:anden-block-data ename))
  (setq schema
    (urb:safe-string
      (if (> (length data) 6) (nth 6 data) nil) "0"))
  (if (/= schema *urb-schema-version*)
    (progn
      (setq obj (vlax-ename->vla-object ename))
      (urb:repair-block-ref-order obj)))
  schema
)

;; Puntos del contorno de un anden YA empacado, SIN desempacarlo. El
;; bloque se arma con -BLOCK y punto base 0,0,0, asi que las coordenadas de
;; la definicion son las mismas del dibujo. Permite rehacer el movimiento
;; de tierras en segundos, en vez de reconstruir el anden entero (minutos).
(defun urb:anden-block-points (ename / obj bdef item capa candidatos mejor pts)
  (setq obj (vl-catch-all-apply 'urb:as-vla-object (list ename)))
  (if (or (vl-catch-all-error-p obj) (null obj))
    nil
    (progn
      (setq bdef
        (vl-catch-all-apply 'vla-Item
          (list (vla-get-Blocks (urb:doc)) (vla-get-Name obj))))
      (if (vl-catch-all-error-p bdef)
        nil
        (progn
          (setq candidatos nil)
          (vlax-for item bdef
            (setq capa (strcase (urb:safe-string (vla-get-Layer item) "")))
            (if (and (member (vla-get-ObjectName item)
                             '("AcDbPolyline" "AcDb2dPolyline"))
                     (or (urb:starts-with capa "URB-Q-ANDEN-")
                         (= capa "URB-ANDEN")))
              (setq candidatos (cons item candidatos))))
          (setq mejor (urb:largest-closed-polyline (reverse candidatos)))
          ;; Los vertices se leen del DXF directo, SIN (trans pt ename 0):
          ;; medido en Civil real, trans devuelve nil para una entidad que
          ;; vive dentro de la definicion de bloque (no tiene contexto de
          ;; insercion) y urb:lwpoly-points regresaba una lista de nils.
          ;; El bloque se arma con punto base 0,0,0 y el contorno es plano,
          ;; asi que el DXF ya viene en coordenadas del dibujo.
          (if mejor
            (progn
              (setq pts nil)
              (foreach item (entget (vlax-vla-object->ename mejor))
                (if (= (car item) 10)
                  (setq pts
                    (cons (list (cadr item) (caddr item)) pts))))
              (reverse pts))))))))

(defun urb:explode-anden-block-boundary
  (ename / obj exploded objects item boundary layer candidatos side-data)
  (setq side-data (urb:tactile-side-data ename))
  (setq obj (vlax-ename->vla-object ename))
  (setq exploded
    (vl-catch-all-apply 'vla-Explode (list obj)))
  (if (vl-catch-all-error-p exploded)
    nil
    (progn
      (setq objects (urb:variant-object-list exploded))
      ;; 2026-09-10: misma correccion que en la via -- entre los candidatos
      ;; de la capa del contorno se toma el de MAYOR area cerrada, no el
      ;; ultimo que aparezca; los demas se borran tres lineas mas abajo.
      (setq candidatos nil)
      (foreach item objects
        (setq layer
          (strcase
            (urb:safe-string (vla-get-Layer item) "")))
        (if (and
              (member
                (vla-get-ObjectName item)
                '("AcDbPolyline" "AcDb2dPolyline"))
              (or (urb:starts-with layer "URB-Q-ANDEN-") (= layer "URB-ANDEN")))
          (setq candidatos (cons item candidatos))))
      (setq boundary (urb:largest-closed-polyline (reverse candidatos)))
      (foreach item objects
        (if (not (eq item boundary))
          (urb:safe-delete item)))
      (if boundary
        (progn
          (if side-data
            (urb:set-tactile-side-data
              (vlax-vla-object->ename boundary) side-data))
          (vlax-vla-object->ename boundary))
        nil)))
)

;; 2026-09-10 (pedido del usuario: "cuando le doy editar elemento me sale
;; la ventana de configuracion inicial, pero quiero que dentro de esa
;; ventana o despues de darle ok me de la opcion de editar el movimiento de
;; tierras"). Se pregunta DESPUES de aceptar la ventana, en la linea de
;; comandos, para vias y andenes. Por defecto NO, para que un Enter deje la
;; edicion como estaba.
(defun urb:ask-edit-movimiento (que / kw)
  (initget "Si No")
  (setq kw
    (getkword
      (strcat "\nEditar tambien el movimiento de tierras de " que
              " (volver a tomar cotas)? [Si/No] <No>: ")))
  (urb:yes-p (urb:safe-string kw "No"))
)

;; ---------- 5.6.2 CAJA NEGRA de la generacion de andenes ----------
;; Reporte del usuario: "al crear andenes con curvas se traba y se cierra el
;; AutoCAD". Un cierre duro (violacion de acceso en accore.dll) no se puede
;; atrapar desde LISP y no deja rastro. Cada etapa se escribe -y el archivo
;; se CIERRA- antes de ejecutarla: si AutoCAD muere, la ultima linea dice
;; exactamente donde. Archivo: %TEMP%\urbcant_anden_etapas.log (se recorta
;; solo cuando supera ~200 KB).
;; La caja negra JAMAS puede romper el flujo: verificado en 5.6.2 que
;; menucmd devuelve nil justo despues del empaquetado (-BLOCK) y el strcat
;; abortaba el recorte del anden con "stringp nil". Todo va protegido y la
;; hora sale de CDATE, no de menucmd.
(defun urb:bb-log (texto)
  (vl-catch-all-apply 'urb:bb-log-write (list texto))
  T)

(defun urb:bb-log-write (texto / fn f cd)
  (setq fn (strcat (urb:safe-string (getenv "TEMP") "C:\\Temp") "\\urbcant_anden_etapas.log"))
  (if (and (findfile fn) (> (vl-file-size fn) 200000))
    (vl-file-delete fn))
  (setq cd (rtos (getvar "CDATE") 2 6))
  (setq f (open fn "a"))
  (if f
    (progn
      (write-line
        (strcat (substr cd 1 4) "-" (substr cd 5 2) "-" (substr cd 7 2) " "
                (substr cd 10 2) ":" (substr cd 12 2) ":" (substr cd 14 2)
                " | " (urb:safe-string (if (boundp '*urb-version*) *urb-version*) "?")
                " | " (urb:safe-string (getvar "DWGNAME") "?")
                " | " (urb:safe-string texto ""))
        f)
      (close f))))

;; 5.6.2: vl-exit-with-error deja un error SIN mensaje (nil). Antes el
;; strcat del aviso reventaba con "stringp nil" FUERA de la proteccion y
;; tumbaba todo el recorte/regeneracion del anden (medido con DD2CA).
(defun urb:call-edit-stage (stage function arguments / result msg)
  (urb:bb-log (strcat "INICIA " (urb:safe-string stage "?")))
  (setq result (vl-catch-all-apply function arguments))
  (if (vl-catch-all-error-p result)
    (setq msg (urb:safe-string (vl-catch-all-error-message result)
                "error sin mensaje (vl-exit-with-error)")))
  (urb:bb-log (strcat "TERMINA " (urb:safe-string stage "?")
                      (if msg (strcat " ERROR " msg) " OK")))
  (if msg
    (progn
      (prompt
        (strcat
          "\nNo se completo la etapa "
          (urb:safe-string stage "desconocida")
          ": " msg))
      nil)
    result)
)

(defun urb:cleanup-working-boundary (ename / obj handle)
  (if (and ename (entget ename))
    (progn
      (setq obj
        (vl-catch-all-apply
          'vlax-ename->vla-object
          (list ename)))
      (if (not (vl-catch-all-error-p obj))
        (progn
          (setq handle
            (vl-catch-all-apply 'vla-get-Handle (list obj)))
          (if (not (vl-catch-all-error-p handle))
            (urb:delete-generated handle))
          (urb:safe-delete obj)))))
  nil
)

(defun urb:delete-anden-block
  (ename / obj block-name block-definition deleted)
  (setq obj (urb:as-vla-object ename))
  (if (not obj)
    nil
    (progn
      (setq block-name
        (vl-catch-all-apply 'vla-get-Name (list obj)))
      (setq deleted (urb:safe-delete obj))
      (if (and deleted (not (vl-catch-all-error-p block-name)))
        (progn
          (setq block-definition
            (vl-catch-all-apply
              'vla-Item
              (list (vla-get-Blocks (urb:doc)) block-name)))
          (if (not (vl-catch-all-error-p block-definition))
            (urb:safe-delete block-definition))))
      deleted))
)

(defun urb:rebuild-working-boundary
  (boundary material etapa subetapa guia toperol format calculate surface grade-source
   / saved result block-ref pattern-mode pts clip-result)
  (setq pattern-mode (urb:anden-pattern-mode boundary))
  ;; Las versiones 4.17.3 preliminares guardaban el sentido en otra APPID.
  ;; Se retira antes de escribir URB_ANDEN para evitar dos XDATA separadas.
  (urb:clear-xdata-app boundary "URB_ANDEN_PATTERN")
  ;; Misma validacion que urb:draw-closed-polyline (moño/ancho anomalo):
  ;; este es el OTRO camino (edicion, no dibujo nuevo) que regenera el
  ;; acabado sobre un contorno -- sin este chequeo aqui, una polilinea que
  ;; llegue deformada (edicion de grips, seleccion manual, etc.) generaba
  ;; el acabado sin ningun aviso, igual que pasaba antes en el flujo de
  ;; dibujo nuevo.
  (setq pts (urb:lwpoly-points-with-arcs boundary))
  (if (urb:anden-shape-ok-p pts)
    (setq saved
      (urb:call-edit-stage
        "guardar datos"
        'urb:set-anden-data
        (list boundary material etapa subetapa guia toperol format calculate surface grade-source)))
    (setq saved nil))
  (if saved
    (urb:set-anden-pattern-mode boundary pattern-mode))
  ;; 2026-09-08: este camino tambien se usa al insertar un contenedor
  ;; DESPUES de haber modelado el anden. Se recorta la polilinea antes de
  ;; regenerar el acabado; si el obstaculo queda completamente interior y
  ;; el contorno simple no puede representar un hueco, build-anden-finish
  ;; conserva el borde exterior y resta igualmente la huella de las piezas.
  (if saved
    (setq clip-result
      (vl-catch-all-apply 'urb:anden-clip-contour (list boundary))))
  ;; En EDITAR el clic se pide antes de extraer cada contorno. Resolver aqui
  ;; su ancla sobre la geometria final hace que una seleccion multiple y los
  ;; recortes posteriores no puedan reutilizar el costado equivocado.
  (if saved
    (progn
      ;; Un clic nuevo manda. En regeneraciones silenciosas se recupera
      ;; SIEMPRE el ancla de este bloque (sobrescribe la del anterior en
      ;; una seleccion multiple) para no invertir el lado por estado global.
      (setq *urb-current-tactile-side-anchor*
        (if *urb-current-tactile-side-point*
          (urb:tactile-side-anchor
            (urb:lwpoly-points-with-arcs-fine boundary)
            *urb-current-tactile-side-point*)
          (urb:tactile-side-data boundary)))
      (if *urb-current-tactile-side-anchor*
        (urb:set-tactile-side-data boundary
          *urb-current-tactile-side-anchor*))))
  (if (and saved *urb-confirm-tactile-side*
           (or (urb:yes-p guia) (urb:yes-p toperol)))
    (urb:confirm-tactile-side boundary))
  (if saved
    (setq result
      (urb:call-edit-stage
        "crear geometria"
        'urb:build-anden-finish
        (list boundary material guia toperol format))))
  (if result
    (setq block-ref
      (urb:call-edit-stage
        "crear bloque"
        'urb:package-anden
        (list boundary))))
  (if (not block-ref)
    (urb:cleanup-working-boundary boundary))
  block-ref
)

(defun urb:prepare-green-layers ()
  (urb:ensure-layer "URB-ZONA-VERDE" 3 T)
)

(defun urb:draw-green-boundary
  (/ option selected source object copy before after old-plinewid)
  (initget "Dibujar Seleccionar")
  (setq option
    (getkword
      "\nDefinir contorno de zona verde [Dibujar/Seleccionar] <Dibujar>: "))
  (if (null option) (setq option "Dibujar"))
  (if (= option "Seleccionar")
    (progn
      (setq selected
        (entsel "\nSeleccione una polilinea cerrada existente: "))
      (if (and selected
               (setq source (car selected))
               (urb:closed-poly-p source))
        (progn
          ;; La geometria original se conserva; la zona verde trabaja con
          ;; una copia propia para no alterar el plano base.
          (setq object (vlax-ename->vla-object source)
                copy (vla-Copy object))
          (if (vlax-property-available-p copy 'ConstantWidth T)
            (vla-put-ConstantWidth copy 0.0))
          (vlax-vla-object->ename copy))
        (progn
          (prompt "\nLa seleccion no es una polilinea cerrada valida.")
          nil)))
    (progn
      (setq old-plinewid (getvar "PLINEWID")
            before (entlast))
      (setvar "PLINEWID" 0.0)
      (prompt
        "\nDibuje el contorno de la zona verde. Enter termina y cierra el area.")
      (urb:draw-polyline-interactive old-plinewid)
      (setq after (entlast))
      (if (and after (/= after before)
               (= (cdr (assoc 0 (entget after))) "LWPOLYLINE"))
        (progn
          (setq object (vlax-ename->vla-object after))
          (vla-put-Closed object :vlax-true)
          (if (urb:closed-poly-p after) after nil))
        nil)))
)

;; ------------------------------------------------------------------
;; Corte/relleno de un POLIGONO contra SUP_TN (2026-09-02, pedido del
;; usuario para zonas verdes): la rasante de diseno sale de las cotas que
;; el usuario CLICKEA con el mismo picker universal del modo Pendiente
;; (via creada, pozo del modelo, etiqueta de cota o digitada):
;;  - 3 o mas cotas: plano por minimos cuadrados
;;  - 2 cotas: rasante lineal entre ambas, extendida perpendicular
;; Malla de muestreo 2.5 m dentro del contorno; corte = TN sobre diseno,
;; relleno = diseno sobre TN.
;; 5.6.1: si alguna cota vino de una VIA creada, la cota de diseno sale de
;; la rasante de esa via en la estacion del punto (todo el alineamiento);
;; si no, el plano / rasante lineal de siempre.
;; 5.7.15: un flujo comun para CREAR y EDITAR zonas/senderos. Las referencias
;; contienen el perfil completo, no una cota plana en el sitio del clic.
(defun urb:area-grade-auto (pts / road ref anden)
  (if (and pts (> (length pts) 2))
    (progn
      (setq road (urb:anden-road-autodetect pts))
      (if road (setq ref (urb:anden-road-grade-for-safe road)))
      (if ref
        (prompt (strcat "\nTierras: VIA " (urb:safe-string (nth 8 ref) "")
          " [" (cdr (assoc 5 (entget road))) "] detectada; rasante completa por estaciones."))
        (progn
          (setq anden (urb:anden-near-points pts))
          (if anden (setq ref (urb:anden-design-reference anden)))
          (if ref (prompt (strcat "\nTierras: ANDEN ["
            (cdr (assoc 5 (entget anden))) "] detectado; cotas de su borde, no una cota fija.")))))
      (if ref (list (list 0.0 (car pts) ref))))))

(defun urb:area-grade-from-pick (sel / ref)
  (if (listp sel)
    (progn
      (setq ref (urb:anden-reference-from-pick sel))
      (if (null ref) (setq ref (urb:road-reference-from-pick sel)))
      (if ref (list (list 0.0 (cadr sel) ref))))))

(defun urb:area-earthwork-picks (boundary editing / mode picks sel)
  (setq *urb-anden-pts-cache* nil)
  (urb:anden-ref-curves-clear)
  (initget (if editing "Automatico Referencia Cotas Conservar" "Automatico Referencia Cotas Sin"))
  (setq mode (getkword (strcat "\nTierras [Automatico/Referencia/Cotas/"
    (if editing "Conservar" "Sin") "] <Automatico>: ")))
  (if (null mode) (setq mode "Automatico"))
  (if (= mode "Automatico")
    (progn
      (setq picks (urb:area-grade-auto (urb:anden-earthwork-raw-points boundary)))
      (if (null picks)
        (progn
          (prompt "\nNo hay una via/anden cercano con rasante recuperable. Seleccione UNA referencia o Enter para dejar pendiente.")
          (setq mode "Referencia")))))
  (cond
    ((= mode "Referencia")
      (setq sel (nentsel "\nSeleccione UNA VIA o ANDEN completo (Enter cancela; cotas sueltas: opcion Cotas): "))
      (setq picks (urb:area-grade-from-pick sel))
      (if picks
        (prompt "\nReferencia tomada: se usa todo su perfil, sin pedir puntos adicionales.")
        (if sel (prompt "\nEl objeto no tiene una rasante recuperable. No se inventa una cota."))))
    ((= mode "Cotas") (setq picks (urb:pick-design-cotas))))
  (if (null picks) (urb:anden-ref-curves-clear))
  picks)

(defun urb:area-earthwork-clear (ename app / obj)
  (setq obj (urb:as-vla-object ename))
  (urb:set-xdata-strings ename app nil)
  (if (= (cdr (assoc 0 (entget ename))) "INSERT")
    (progn
      (urb:set-block-attribute obj "CORTE_M3" "0")
      (urb:set-block-attribute obj "RELLENO_M3" "0"))))

;; Solo se llama DESPUES de empaquetar. El MT es opcional: un error o Esc
;; nunca debe deshacer el bloque ni sus atributos geometricos.
(defun urb:area-created-earthworks (ename kind thickness / result)
  (prompt "\nBloque creado con propiedades. Ahora se configura el movimiento de tierras (opcional).")
  (setq result
    (if (= kind "ZONA_VERDE")
      (vl-catch-all-apply 'urb:green-earthworks-run (list ename thickness nil))
      (vl-catch-all-apply 'urb:sendero-earthworks-run (list ename nil))))
  (if (vl-catch-all-error-p result)
    (progn
      (prompt (strcat "\nTierras interrumpidas: " (vl-catch-all-error-message result)))
      (setq result nil)))
  (if (null result)
    (progn
      (urb:area-earthwork-clear ename
        (if (= kind "ZONA_VERDE") "URB_GREEN_MOV" "URB_SEND_MOV"))
      (prompt "\nBloque conservado y editable. Tierras PENDIENTES; use EDITAR para calcularlas.")))
  result)

(defun urb:design-z-from-picks (picks x y / ref arefs best bd d q)
  ;; 5.6.2: referencias de ANDEN (ANDEN ref-via borde contorno). Si hay
  ;; varias (sendero entre dos andenes) manda la del anden mas cercano.
  (setq arefs (vl-remove-if-not
                '(lambda (r) (and (listp r) (eq (car r) 'ANDEN)))
                (mapcar '(lambda (p) (if (> (length p) 2) (caddr p))) picks)))
  (setq ref (vl-some '(lambda (p) (if (and (> (length p) 2) (not (eq (car (caddr p)) 'ANDEN))) (caddr p))) picks))
  (if (and arefs (null ref))
    (progn
      (foreach r arefs
        (setq q (if (cdr arefs)
                  (vl-catch-all-apply 'vlax-curve-getClosestPointTo
                    (list (urb:anden-ref-curve r) (list x y 0.0)))))
        (if (vl-catch-all-error-p q) (setq q nil))
        (if q (setq d (distance (list x y) (list (car q) (cadr q)))))
        (if (and q (or (null bd) (< d bd))) (setq bd d best r)))
      (setq ref (if best best (car arefs)))))
  (cond
    ((and ref (eq (car ref) 'ANDEN)) (urb:anden-reference-design-z ref x y))
    ((null ref) (urb:design-z-from-picks-plane picks x y))
    ;; con el borde conocido (lo fija urb:earthworks-from-picks) se usa la
    ;; MISMA cota de diseno que el recalculo completo del anden
    ;; (urb:anden-grade-at-point: bombeo de via hasta el borde + bordillo +
    ;; pendiente transversal). Verificado: con la version simple las dos
    ;; rutas daban 454 y 280 m3 para el mismo anden.
    ((numberp *urb-picks-edge-offset*)
      (urb:anden-grade-at-point (list x y 0.0) ref *urb-picks-edge-offset*))
    (T (urb:road-reference-design-z ref x y))))

(setq *urb-picks-edge-offset* nil)
(setq *urb-picks-base-points* nil)

(defun urb:design-z-collinear-picks (picks x y / origin far span dx dy records p d)
  ;; El orden de clic no define los extremos. Ordenar por proyeccion y
  ;; conservar cada cota intermedia, en vez de inventar una sola pendiente.
  (setq origin (cadr (car picks)) span 0.0)
  (foreach p picks
    (setq d (distance origin (cadr p)))
    (if (> d span) (setq span d far (cadr p))))
  (if (> span 1e-8)
    (progn
      (setq dx (/ (- (car far) (car origin)) span)
            dy (/ (- (cadr far) (cadr origin)) span))
      (foreach p picks
        (setq records (cons (list
          (+ (* (- (car (cadr p)) (car origin)) dx)
             (* (- (cadr (cadr p)) (cadr origin)) dy)) (car p)) records)))
      (setq records (vl-sort records '(lambda (a b) (< (car a) (car b)))))
      (urb:cota-at-axis-distance
        (+ (* (- x (car origin)) dx) (* (- y (cadr origin)) dy)) records))
    (car (car picks))))

(defun urb:design-z-from-picks-plane (picks x y / n sx sy sz sxx syy sxy sxz syz
   det a b c p p1 p2 z1 z2 dx dy len2 t0 ox oy)
  (setq n (length picks))
  (cond
    ((>= n 3)
      ;; Coordenadas locales evitan cancelacion numerica en coordenadas DWG.
      (setq ox (car (cadr (car picks))) oy (cadr (cadr (car picks)))
            x (- x ox) y (- y oy)
            picks (mapcar '(lambda (v) (list (car v)
                      (list (- (car (cadr v)) ox) (- (cadr (cadr v)) oy)))) picks))
      (setq sx 0.0 sy 0.0 sz 0.0 sxx 0.0 syy 0.0 sxy 0.0 sxz 0.0 syz 0.0)
      (foreach p picks
        (setq sx (+ sx (car (cadr p))) sy (+ sy (cadr (cadr p)))
              sz (+ sz (car p))
              sxx (+ sxx (* (car (cadr p)) (car (cadr p))))
              syy (+ syy (* (cadr (cadr p)) (cadr (cadr p))))
              sxy (+ sxy (* (car (cadr p)) (cadr (cadr p))))
              sxz (+ sxz (* (car (cadr p)) (car p)))
              syz (+ syz (* (cadr (cadr p)) (car p)))))
      ;; normal: resolver [sxx sxy sx; sxy syy sy; sx sy n][a b c]=[sxz syz sz]
      (setq det (+ (* sxx (- (* syy n) (* sy sy)))
                   (* (- sxy) (- (* sxy n) (* sy sx)))
                   (* sx (- (* sxy sy) (* syy sx)))))
      (if (< (abs det) 1e-9)
        (urb:design-z-collinear-picks picks x y)
        (progn
          (setq a (/ (+ (* sxz (- (* syy n) (* sy sy)))
                        (* (- sxy) (- (* syz n) (* sy sz)))
                        (* sx (- (* syz sy) (* syy sz)))) det))
          (setq b (/ (+ (* sxx (- (* syz n) (* sz sy)))
                        (* (- sxz) (- (* sxy n) (* sy sx)))
                        (* sx (- (* sxy sz) (* syz sx)))) det))
          (setq c (/ (+ (* sxx (- (* syy sz) (* syz sy)))
                        (* (- sxy) (- (* sxy sz) (* syz sx)))
                        (* sxz (- (* sxy sy) (* syy sx)))) det))
          (+ (* a x) (* b y) c))))
    ((= n 2)
      (setq p1 (cadr (car picks)) p2 (cadr (cadr picks))
            z1 (car (car picks)) z2 (car (cadr picks))
            dx (- (car p2) (car p1)) dy (- (cadr p2) (cadr p1))
            len2 (+ (* dx dx) (* dy dy)))
      (if (< len2 1e-9) z1
        (progn
          (setq t0 (/ (+ (* (- x (car p1)) dx) (* (- y (cadr p1)) dy)) len2))
          (+ z1 (* t0 (- z2 z1))))))
    ((= n 1) (car (car picks)))
    (T nil)))

;; 2026-09-11 (pedido del usuario: "que los cortes y rellenos esten bien con
;; respecto a los llenos granulares que toque hacer"). Hasta v4.93 esta
;; funcion comparaba el terreno contra la cota TERMINADA (encima de la
;; loseta o de la tierra negra) y NO descontaba la estructura. Eso
;; subestimaba el corte (hay que excavar hasta la subrasante para meter la
;; estructura) y contaba la estructura granular como si fuera relleno de
;; tierra. El calculo ORIGINAL del anden (urb:run-anden-earthworks) si lo
;; hacia bien -- terreno contra (terminado - *urb-anden-depth*) --, asi que
;; los dos caminos del anden daban numeros distintos para lo mismo.
;; Ahora cada llamador pasa el ESPESOR de su estructura y se mide contra la
;; SUBRASANTE = cota terminada - espesor:
;;   anden y rampa -> *urb-anden-depth* (0.60 = loseta + arena + SBG)
;;   zona verde    -> espesor de tierra negra de la zona
;;   sendero       -> espesor de su tipo (Ajustes)
;; La estructura en si (granular, tierra negra) se sigue cantidando aparte.
;; Cuadratura por triangulos: cada muestra tiene su area real. No contar
;; celdas completas de una malla que exceden o pierden el borde del contorno.
;; 5.6.3: contornos CURVOS densificados (DD2CA 1272 vertices, F20E5 2012)
;; salen de la triangulacion como abanicos de astillas: 253 000 muestras y
;; ~3 min de calculo con AutoCAD congelado (Windows lo marca "no responde";
;; el visor de eventos tiene esos AppHang del 11 y 13-09). Con muchos
;; vertices se muestrea por BARRIDO: filas cada 0.5 m, intervalos exactos
;; en X partidos en celdas de 0.5 m; pesos normalizados al area del
;; contorno. Contornos simples: triangulos de siempre (cifras intactas).
(defun urb:earthwork-area-samples (points)
  (if (> (length points) 200)
    (urb:earthwork-scanline-samples points 0.5)
    (urb:earthwork-triangle-samples points)))

(defun urb:earthwork-strip-x (edge y / a b)
  (setq a (car edge) b (cadr edge))
  (+ (car a) (* (- y (cadr a))
    (/ (- (car b) (car a)) (- (cadr b) (cadr a))))))

(defun urb:earthwork-scanline-samples (points step / pts rest a b edges levels y0 y1 ym
   hits edge pair l0 l1 r0 r1 n k f0 f1 p0 p1 p2 p3 quad centroid weight ox oy z out height
   active waiting event sample-count failed)
  ;; 5.7.4: trapecios recortados entre TODOS los niveles de vertices.
  ;; Cada celda aporta area y centroide reales, sin normalizacion global.
  ;; Evita perder remates <0.25m y conserva integrales de planos lineales.
  ;; Coordenadas locales: estabilidad en las coordenadas grandes del DWG.
  (if (and (> (length points) 2) (> step 0.0))
    (progn
      (setq ox (caar points) oy (cadar points)
            z (if (caddr (car points)) (caddr (car points)) 0.0)
            pts (mapcar '(lambda (p) (list (- (car p) ox) (- (cadr p) oy))) points)
            rest (append pts (list (car pts)))
            levels (vl-sort (mapcar 'cadr pts) '<))
      (while (cdr rest)
        (setq a (car rest) b (cadr rest))
        (if (/= (cadr a) (cadr b)) (setq edges (cons (list a b) edges)))
        (setq rest (cdr rest)))
      ;; 5.7.17: barrido por eventos. Antes CADA nivel recorria TODAS las
      ;; aristas (4392 x 4392 en el caso 1B3D3F), aunque solo dos cruzaban
      ;; esa fila. Conserva los mismos niveles, trapecios y centros de masa.
      (setq waiting
        (mapcar '(lambda (edge)
          (list (min (cadar edge) (cadadr edge))
                (max (cadar edge) (cadadr edge)) edge)) edges))
      (setq waiting (mapcar '(lambda (i) (nth i waiting))
        (vl-sort-i waiting '(lambda (a b) (< (car a) (car b))))))
      (setq sample-count 0)
      (while (and (cdr levels) (not failed))
        (setq y0 (car levels) y1 (cadr levels))
        (while (and (< y0 (- y1 1e-10)) (not failed))
          (setq height (min step (- y1 y0)) ym (+ y0 (* 0.5 height)) hits nil)
          (while (and waiting (<= (caar waiting) ym))
            (setq active (cons (car waiting) active) waiting (cdr waiting)))
          (setq active (vl-remove-if '(lambda (event) (<= (cadr event) ym)) active))
          (foreach event active
            (setq edge (caddr event))
            (setq hits (cons (list (urb:earthwork-strip-x edge ym) edge) hits)))
          (setq hits (mapcar '(lambda (i) (nth i hits))
            (vl-sort-i hits '(lambda (a b) (< (car a) (car b))))))
          (while (and (cdr hits) (not failed))
            (setq pair (list (cadar hits) (cadadr hits)) hits (cddr hits)
                  l0 (urb:earthwork-strip-x (car pair) y0)
                  l1 (urb:earthwork-strip-x (car pair) (+ y0 height))
                  r0 (urb:earthwork-strip-x (cadr pair) y0)
                  r1 (urb:earthwork-strip-x (cadr pair) (+ y0 height))
                  n (max 1 (fix (+ 0.999999999 (/ (max (- r0 l0) (- r1 l1)) step)))) k 0)
            ;; No conservar una malla parcial ni seguir hasta agotar memoria.
            (if (> (+ sample-count n) 250000)
              (setq failed T n 0))
            (setq sample-count (+ sample-count n))
            (repeat n
              (setq f0 (/ (float k) n) f1 (/ (float (1+ k)) n)
                    p0 (list (+ l0 (* f0 (- r0 l0))) y0)
                    p1 (list (+ l0 (* f1 (- r0 l0))) y0)
                    p2 (list (+ l1 (* f1 (- r1 l1))) (+ y0 height))
                    p3 (list (+ l1 (* f0 (- r1 l1))) (+ y0 height)))
              ;; Un trapecio convexo necesita una sola consulta a la superficie:
              ;; su centroide y area integran exactamente cualquier plano lineal.
              ;; Antes se dividia siempre en dos triangulos, duplicando las
              ;; llamadas COM sin ganar precision sobre una superficie TIN.
              (setq quad (list p0 p1 p2 p3)
                    weight (abs (urb:polygon-signed-area quad))
                    centroid (urb:polygon-centroid quad))
              (if (and centroid (> weight 1e-14))
                (setq out (cons (list
                  (list (+ ox (car centroid)) (+ oy (cadr centroid)) z)
                  weight) out)))
              (setq k (1+ k))))
          (setq y0 (+ y0 height)))
        (setq levels (cdr levels)))
      (if failed
        (progn
          (prompt "\nTierras PENDIENTES: la huella exige mas de 250000 muestras; revise su contorno. No se usa un volumen parcial.")
          nil)
        out))))

(defun urb:earthwork-triangle-samples (points / pending tri a b c ab bc ca mid w out)
  (setq pending (urb:triangulate-polygon points))
  (while pending
    (setq tri (car pending) pending (cdr pending)
          a (car tri) b (cadr tri) c (caddr tri)
          ab (distance a b) bc (distance b c) ca (distance c a))
    (if (> (max ab bc ca) 2.5)
      (progn
        (cond ((and (>= ab bc) (>= ab ca))
               (setq mid (mapcar '(lambda (x y) (/ (+ x y) 2.0)) a b))
               (setq pending (cons (list a mid c) (cons (list mid b c) pending))))
              ((>= bc ca)
               (setq mid (mapcar '(lambda (x y) (/ (+ x y) 2.0)) b c))
               (setq pending (cons (list b mid a) (cons (list mid c a) pending))))
              (T
               (setq mid (mapcar '(lambda (x y) (/ (+ x y) 2.0)) c a))
               (setq pending (cons (list c mid b) (cons (list mid a b) pending))))))
      (progn
        (setq w (* 0.5 (abs (urb:triangle-cross a b c))))
        (if (> w 1e-10)
          (setq out (cons (list
            (mapcar '(lambda (x y z) (/ (+ x y z) 3.0)) a b c) w) out))))))
  out)

(defun urb:earthworks-from-picks
  (ename picks depth / surface poly area samples sample p weight total covered cut fill ztn zdis delta scale)
  (if (not (numberp depth)) (setq depth 0.0))
  (setq surface (mp:current-terrain-surface))
  (if surface
    (progn
      (setq poly (urb:anden-earthwork-raw-points ename)
            area (vla-get-Area (vlax-ename->vla-object ename))
            samples (urb:earthwork-area-samples poly)
            total 0.0 covered 0.0 cut 0.0 fill 0.0)
      ;; 5.6.1: si una cota vino de una via creada, distancia del eje de
      ;; esa via al borde del elemento (para la cota de diseno completa)
      (setq *urb-picks-edge-offset*
        (vl-some '(lambda (pk)
                    (if (> (length pk) 2)
                      (vl-catch-all-apply 'urb:anden-axis-edge-offset
                        (list (if *urb-picks-base-points* *urb-picks-base-points* poly)
                              (car (caddr pk))))))
                 picks))
      (if (vl-catch-all-error-p *urb-picks-edge-offset*)
        (setq *urb-picks-edge-offset* nil))
      (foreach sample samples
        (setq p (car sample) weight (cadr sample) total (+ total weight)
              ztn (urb:surface-elevation surface (car p) (cadr p))
              zdis (urb:design-z-from-picks picks (car p) (cadr p)))
        (if (and (numberp ztn) (numberp zdis))
          (progn
            ;; 5.6.5: sobreexcavacion del material no portante incluida
            (setq covered (+ covered weight)
                  delta (urb:cut-fill-at (- ztn (- zdis depth))))
            (setq cut (+ cut (* weight (car delta)))
                  fill (+ fill (* weight (cadr delta)))))))
      (urb:anden-ref-curves-clear)
      (if (and (> total 1e-9) (> area 1e-9)
               (<= (abs (- area total)) (max 0.001 (* area 0.0001)))
               (>= covered (* total 0.999999)))
        (progn
          (setq scale (/ area total))
          (list (* scale cut) (* scale fill)))
        (progn
          (prompt "\nTierras PENDIENTES: contorno incompleto o puntos fuera de SUP_TN; no se guarda un volumen parcial.")
          nil)))
    (progn
      (prompt (strcat "\nNo se encontro la superficie " *mp-terrain-surface-name* "."))
      nil)))

(defun urb:green-zone-data (ename / data object attributes)
  (setq data (urb:get-xdata-strings ename "URB_GREEN_BLOCK"))
  (if data
    data
    (progn
      (setq object (urb:as-vla-object ename))
      (if object
        (progn
          (setq attributes (urb:block-attribute-values object))
          (list "ZONA_VERDE"
            (urb:attribute-alist-value attributes "ETAPA" "1")
            (urb:attribute-alist-value attributes "SUBETAPA" "1")
            (urb:attribute-alist-value attributes "AREA_M2" "0")
            (urb:attribute-alist-value attributes "PERIMETRO_M" "0")
            (urb:attribute-alist-value
              attributes "ESPESOR_TIERRA_NEGRA_M" "0.20")
            (urb:attribute-alist-value
              attributes "TIERRA_NEGRA_M3" "0")
            "0"))
        nil)))
)

(defun urb:green-zone-block-p (ename / data object layer name)
  (setq data (urb:get-xdata-strings ename "URB_GREEN_BLOCK")
        object (urb:as-vla-object ename))
  (and object
       (urb:string-equal-p (vla-get-ObjectName object)
         "AcDbBlockReference")
       (or
         (and data
              (urb:string-equal-p (car data) "ZONA_VERDE"))
         (progn
           (setq layer
             (strcase (urb:safe-string (vla-get-Layer object) ""))
                 name
             (strcase (urb:safe-string (vla-get-Name object) "")))
           (or (= layer "URB-ZONA-VERDE-BLOQUE") (= layer "URB-ZONA-VERDE")
               (urb:starts-with name "URB_ZONA_VERDE_")))))
)

(defun urb:selected-green-zones
  (selection / index ename result)
  (setq index 0)
  (repeat (sslength selection)
    (setq ename (ssname selection index))
    (if (urb:green-zone-block-p ename)
      (setq result (cons ename result)))
    (setq index (1+ index)))
  (reverse result)
)

(defun urb:package-green-zone
  (ename hatch etapa subetapa thickness
   / boundary area perimeter volume point handle objects block-name blocks
   block-definition copy-result insert-result block-ref block-ename
   xdata-result)
  (setq boundary (vlax-ename->vla-object ename)
        area (vla-get-Area boundary)
        perimeter (urb:poly-perimeter boundary)
        volume (* area thickness)
        point
          (if (urb:lwpoly-points ename)
            (car (urb:lwpoly-points ename))
            '(0.0 0.0 0.0))
        handle (vla-get-Handle boundary)
        objects (list boundary))
  (if (urb:valid-vla-object-p hatch)
    (setq objects (append objects (list hatch))))
  (setq block-name
    (strcat "URB_ZONA_VERDE_" handle "_"
      (itoa (getvar "MILLISECS")))
        blocks (vla-get-Blocks (urb:doc))
        block-definition
          (vla-Add blocks
            (vlax-3d-point '(0.0 0.0 0.0)) block-name)
        copy-result
          (vl-catch-all-apply 'vla-CopyObjects
            (list (urb:doc)
              (urb:object-array-variant objects)
              block-definition)))
  (if (vl-catch-all-error-p copy-result)
    (progn
      (urb:safe-delete block-definition)
      (prompt
        (strcat "\nERROR al crear el bloque de zona verde: "
          (vl-catch-all-error-message copy-result)))
      nil)
    (progn
      (urb:set-block-draw-order
        block-definition
        (urb:variant-object-list copy-result))
      (urb:add-invisible-attribute
        block-definition point "TIPO" "Tipo" "ZONA VERDE")
      (urb:add-invisible-attribute
        block-definition point "ETAPA" "Etapa" etapa)
      (urb:add-invisible-attribute
        block-definition point "SUBETAPA" "Subetapa" subetapa)
      (urb:add-invisible-attribute
        block-definition point "AREA_M2" "Area zona verde m2"
        (rtos area 2 2))
      (urb:add-invisible-attribute
        block-definition point "PERIMETRO_M" "Perimetro m"
        (rtos perimeter 2 2))
      (urb:add-invisible-attribute
        block-definition point "ESPESOR_TIERRA_NEGRA_M"
        "Espesor tierra negra m" (rtos thickness 2 3))
      (urb:add-invisible-attribute
        block-definition point "TIERRA_NEGRA_M3"
        "Tierra negra m3" (rtos volume 2 2))
      ;; 2026-09-02: corte/relleno opcionales contra SUP_TN (0 si no se
      ;; calcularon; se llenan desde urb:create-green-zone-command)
      (urb:add-invisible-attribute
        block-definition point "CORTE_M3" "Corte m3" "0")
      (urb:add-invisible-attribute
        block-definition point "RELLENO_M3" "Relleno m3" "0")
      (setq insert-result
        (vl-catch-all-apply 'vla-InsertBlock
          (list (urb:space)
            (vlax-3d-point '(0.0 0.0 0.0))
            block-name 1.0 1.0 1.0 0.0)))
      (if (vl-catch-all-error-p insert-result)
        (progn
          (urb:safe-delete block-definition)
          (prompt
            (strcat "\nERROR al insertar la zona verde: "
              (vl-catch-all-error-message insert-result)))
          nil)
        (progn
          (setq block-ref insert-result
                block-ename (urb:as-ename block-ref))
          (vla-put-Layer block-ref "URB-ZONA-VERDE")
          (setq xdata-result
            (urb:set-xdata-strings block-ename "URB_GREEN_BLOCK"
              (list "ZONA_VERDE" etapa subetapa
                (rtos area 2 8)
                (rtos perimeter 2 8)
                (rtos thickness 2 8)
                (rtos volume 2 8)
                *urb-green-schema-version*)))
          (if xdata-result
            (progn
              (foreach object objects (urb:safe-delete object))
              block-ref)
            (progn
              (urb:safe-delete block-ref)
              (urb:safe-delete block-definition)
              (prompt
                "\nERROR: no fue posible guardar los datos de la zona verde.")
              nil))))))
)

(defun urb:create-green-zone-command
  (/ data etapa subetapa thickness ename object area volume hatch block-ref
   old-fillmode doc undo-open undo-result *error* mov kw picks)
  (setq doc (urb:doc)
        old-fillmode (getvar "FILLMODE"))
  (defun *error* (message)
    (if old-fillmode
      (progn (setvar "FILLMODE" old-fillmode) (vla-Regen doc 1)))
    (if undo-open
      (progn
        (vl-catch-all-apply 'vla-EndUndoMark (list doc))
        (setq undo-open nil)))
    (if (and message
             (not (member message
               '("Function cancelled" "quit / exit abort"))))
      (prompt (strcat "\nERROR EN ZONA VERDE: " message)))
    (princ))
  (setq undo-result
    (vl-catch-all-apply 'vla-StartUndoMark (list doc))
        undo-open (not (vl-catch-all-error-p undo-result))
        data
          (if (urb:confirm-meter-units)
            (urb:dialog-green "1" "1" 0.20)
            nil))
  (if data
    (progn
      (setq etapa (nth 0 data)
            subetapa (nth 1 data)
            thickness (nth 2 data)
            ename (urb:draw-green-boundary))))
  (if ename
    (progn
      (urb:prepare-green-layers)
      (setq object (vlax-ename->vla-object ename))
      (setq area (vla-get-Area object)
            volume (* area thickness))
      (vla-put-Layer object "URB-ZONA-VERDE")
      (vla-put-Color object 256)
      ;; 2026-09-02 (pedido del usuario): hatch VERDE SOLIDO con
      ;; transparencia (antes patron GRASS que casi no se veia)
      (setq hatch
        (urb:add-hatch object "URB-ZONA-VERDE"
          "SOLID" 1 "SOLID" 1.0 3))
      (if (vl-catch-all-error-p hatch) (setq hatch nil))
      (if (and hatch (vlax-property-available-p hatch 'EntityTransparency T))
        (vl-catch-all-apply 'vlax-put-property
          (list hatch 'EntityTransparency "70")))
      ;; 5.7.16: confirmar el bloque ANTES de preguntar/calcular tierras.
      ;; Cancelar el MT no debe dejar un hatch sin propiedades.
      (setq block-ref
        (vl-catch-all-apply 'urb:package-green-zone
          (list ename hatch etapa subetapa thickness)))
      (if (vl-catch-all-error-p block-ref)
        (progn
          (prompt (strcat "\nError de empaquetado: " (vl-catch-all-error-message block-ref)))
          (setq block-ref nil)))
      (if block-ref
        (urb:area-created-earthworks (urb:as-ename block-ref) "ZONA_VERDE" thickness)
        (progn
          (urb:safe-delete hatch)
          (prompt "\nNo se creo el bloque. Se conserva el contorno para reintentar; se retira el hatch incompleto.")))
      (setvar "FILLMODE" 1)
      (vla-Regen doc 1)
      (if block-ref
        (prompt
          (strcat "\nZona verde creada: "
            (rtos area 2 2)
            " m2 | Tierra negra: "
            (rtos volume 2 2)
            " m3 | Espesor "
            (rtos thickness 2 3) " m."))
        (prompt "\nNo fue posible crear la zona verde.")))
    (if data
      (prompt "\nNo se definio un contorno valido.")
      (prompt "\nCreacion de zona verde cancelada.")))
  ;; ver comentario equivalente en urb:create-sidewalk-command: sin este
  ;; regen la vista se queda mostrando todo objeto rellenable del dibujo
  ;; solido (heredado del REGEN con FILLMODE=1 de mas arriba) aunque la
  ;; variable ya haya vuelto a su valor original.
  (if old-fillmode
    (progn (setvar "FILLMODE" old-fillmode) (vla-Regen doc 1)))
  (if undo-open
    (progn
      (vl-catch-all-apply 'vla-EndUndoMark (list doc))
      (setq undo-open nil)))
  (princ)
)

(defun urb:update-green-zone-data
  (ename etapa subetapa thickness
   / data object area perimeter volume)
  (setq data (urb:green-zone-data ename)
        object (urb:as-vla-object ename)
        area (atof (urb:safe-string (nth 3 data) "0"))
        perimeter (atof (urb:safe-string (nth 4 data) "0"))
        volume (* area thickness))
  ;; Invalidar por CADA zona: las seleccionadas pueden tener espesores distintos.
  (if (not (equal thickness (atof (urb:safe-string (nth 5 data) "0.20")) 1e-9))
    (progn
      (urb:area-earthwork-clear ename "URB_GREEN_MOV")
      (prompt "\nEspesor modificado: tierras pendientes hasta recalcular.")))
  (urb:set-xdata-strings ename "URB_GREEN_BLOCK"
    (list "ZONA_VERDE" etapa subetapa
      (rtos area 2 8)
      (rtos perimeter 2 8)
      (rtos thickness 2 8)
      (rtos volume 2 8)
      *urb-green-schema-version*))
  (urb:set-block-attribute object "ETAPA" etapa)
  (urb:set-block-attribute object "SUBETAPA" subetapa)
  (urb:set-block-attribute object
    "ESPESOR_TIERRA_NEGRA_M" (rtos thickness 2 3))
  (urb:set-block-attribute object
    "TIERRA_NEGRA_M3" (rtos volume 2 2))
  T
)

;; Recalculo interactivo del movimiento de una zona verde YA empacada.
;; El contorno se extrae en una copia temporal y se elimina siempre; el
;; bloque solo recibe atributos/XDATA despues de un calculo completo.
(defun urb:green-earthworks-edit-one (ename thickness)
  (urb:green-earthworks-run ename thickness T))

(defun urb:green-earthworks-run
  (ename thickness editing / boundary picks mov object)
  (setq boundary (urb:explode-green-block-boundary ename))
  (if (null boundary)
    (prompt "\nNo se pudo leer el contorno de la zona verde.")
    (progn
      (setq picks (vl-catch-all-apply 'urb:area-earthwork-picks (list boundary editing)))
      (if (vl-catch-all-error-p picks) (setq picks nil))
      (if picks
        (setq mov
          (vl-catch-all-apply 'urb:earthworks-from-picks (list boundary picks thickness))))
      (if (vl-catch-all-error-p mov) (setq mov nil))
      (if (entget boundary) (entdel boundary))
      (urb:anden-ref-curves-clear)
      (if (and picks (null mov)) (urb:area-earthwork-clear ename "URB_GREEN_MOV"))
      (if mov
        (progn
          (setq object (urb:as-vla-object ename))
          (urb:set-block-attribute object "CORTE_M3" (rtos (car mov) 2 2))
          (urb:set-block-attribute object "RELLENO_M3" (rtos (cadr mov) 2 2))
          (urb:set-xdata-strings ename "URB_GREEN_MOV"
            (list (rtos (car mov) 2 8) (rtos (cadr mov) 2 8)
                  (rtos thickness 2 8)))
          (prompt
            (strcat "\nZona verde: corte " (rtos (car mov) 2 2)
              " m3 | relleno " (rtos (cadr mov) 2 2) " m3.")))
        (prompt "\nMovimiento de la zona verde no actualizado."))))
  mov)

(defun urb:edit-green-zones (zones / mode en data)
  (initget "Datos Tierras Ambos")
  (setq mode (getkword "\nZona verde: editar [Datos/Tierras/Ambos] <Ambos>: "))
  (if (null mode) (setq mode "Ambos"))
  (if (= mode "Tierras")
    (foreach en zones
      (setq data (urb:green-zone-data en))
      (urb:green-earthworks-edit-one en (atof (urb:safe-string (nth 5 data) "0.20"))))
    (urb:edit-green-zone-properties zones (= mode "Ambos")))
  T)

(defun urb:edit-green-zone-properties
  (zones with-earthworks / first data etapa subetapa thickness old-thickness dialog-data
          ename updated edit-mov mov-updated)
  (setq first (car zones)
        data (urb:green-zone-data first)
        etapa (urb:safe-string (nth 1 data) "1")
        subetapa (urb:safe-string (nth 2 data) etapa)
        thickness (atof (urb:safe-string (nth 5 data) "0.20"))
        old-thickness thickness
        dialog-data
          (urb:dialog-green etapa subetapa thickness))
  (if dialog-data
    (progn
      (setq etapa (nth 0 dialog-data)
            subetapa (nth 1 dialog-data)
            thickness (nth 2 dialog-data)
            updated 0)
      (foreach ename zones
        (if (urb:update-green-zone-data
              ename etapa subetapa thickness)
          (setq updated (1+ updated))))
      (setq edit-mov with-earthworks)
      (if edit-mov
        (progn
          (setq mov-updated 0)
          (foreach ename zones
            (if (urb:green-earthworks-edit-one ename thickness)
              (setq mov-updated (1+ mov-updated))))
          (prompt (strcat "\nMovimiento actualizado en "
            (itoa mov-updated) " de " (itoa (length zones))
            " zona(s) verde(s).")))
        ;; Cambiar el espesor cambia la subrasante: no conservar como
        ;; validos volumenes calculados con el valor anterior.
        (if (not (equal thickness old-thickness 1e-9))
          (progn
            (foreach ename zones
              (urb:set-block-attribute (urb:as-vla-object ename) "CORTE_M3" "0")
              (urb:set-block-attribute (urb:as-vla-object ename) "RELLENO_M3" "0")
              (urb:set-xdata-strings ename "URB_GREEN_MOV" nil))
            (prompt
              "\nEl espesor cambio: corte/relleno queda PENDIENTE hasta recalcularlo."))))
      (vla-Regen (urb:doc) 1)
      (prompt
        (strcat "\nZonas verdes actualizadas: "
          (itoa updated) "."))))
  T
)

(defun c:EDITAR
  (/ selection parents prefabs greens senderos first metadata material format etapa subetapa
   guia toperol calculate surface grade-source data
   ename obj result deleted updated failed old-material boundary block-ref
   cleaned old-guia old-toperol old-format old-calculate old-surface
   old-grade-source old-schema mp-entities roads omitted
   mixed-count orientation-choice start-choice pattern-mode old-pattern-mode
   old-rotated old-reversed new-rotated new-reversed
   anden-points anden-area earthworks-ok new-ename old-handle
   old-movement old-earthworks-p *urb-confirm-tactile-side*
   doc undo-open undo-result *error*)
  (setq doc (urb:doc))
  (defun *error* (message)
    (setq *urb-current-tactile-side-point* nil
          *urb-current-tactile-side-anchor* nil
          *urb-current-tactile-side-choice* nil)
    (if undo-open
      (progn
        (vl-catch-all-apply 'vla-EndUndoMark (list doc))
        (setq undo-open nil)))
    (if (and message
             (not (member message '("Function cancelled" "quit / exit abort"))))
      (prompt (strcat "\nERROR EN EDITAR: " message)))
    (princ))
  (setq undo-result
    (vl-catch-all-apply 'vla-StartUndoMark (list doc)))
  (setq undo-open (not (vl-catch-all-error-p undo-result)))
  (setq *urb-current-tactile-side-point* nil
        *urb-current-tactile-side-anchor* nil
        *urb-current-tactile-side-choice* nil)
  (setq cleaned (urb:clean-selector-layer))
  (if (> cleaned 0)
    (prompt
      (strcat
        "\nEfectos defectuosos eliminados: "
        (itoa cleaned) ".")))
  (prompt
    "\nSeleccione uno o varios elementos para editar: ")
  (setq selection (ssget))
  (if selection
    (progn
      (setq parents (urb:selected-anden-parents selection))
      (setq prefabs (urb:selected-prefabs selection))
      (setq greens (urb:selected-green-zones selection))
      (setq roads (urb:selected-roads selection))
      (setq mp-entities (urb:selected-mp-entities selection))
      (setq senderos (urb:send-selected selection))
      ;; Una seleccion mixta ya no descarta objetos silenciosamente. Se
      ;; rechaza completa para que el usuario sepa exactamente qué se editó.
      (setq mixed-count
        (+ (if roads 1 0)
           (if parents 1 0)
           (if prefabs 1 0)
           (if greens 1 0)
           (if mp-entities 1 0)
           (if senderos 1 0)))
      (if (> mixed-count 1)
        (progn
          (prompt
            "\nLa seleccion contiene categorias diferentes. No se modifico ningun objeto; seleccione un solo tipo.")
          (setq roads nil parents nil prefabs nil greens nil mp-entities nil senderos nil)))
      (if roads
        (foreach ename roads (urb:edit-road ename))
        (if parents
        (progn
          (foreach ename parents
            (if (urb:anden-block-p ename)
              (urb:call-edit-stage
                "revisar bloque anterior"
                'urb:migrate-anden-block
                (list ename))))
          (setq first (car parents))
          (setq metadata
            (if (urb:anden-block-p first)
              (urb:anden-block-data first)
              (urb:get-xdata-strings first "URB_ANDEN")))
          (setq material
            (if metadata
              (nth 1 metadata)
              (if
                (urb:string-equal-p
                  (vla-get-Layer
                    (vlax-ename->vla-object first))
                  "URB-Q-ANDEN-ADOQUIN")
                "Adoquin"
                "Loseta")))
          (setq etapa
            (if metadata (nth 2 metadata) "1"))
          (setq subetapa
            (if metadata (nth 3 metadata) "1"))
          (setq guia
            (if (urb:anden-block-p first)
              (if (> (length metadata) 7) (nth 7 metadata) "No")
              (if (> (length metadata) 4) (nth 4 metadata) "No")))
          (setq toperol
            (if (urb:anden-block-p first)
              (if (> (length metadata) 8) (nth 8 metadata) "No")
              (if (> (length metadata) 5) (nth 5 metadata) "No")))
          (setq format
            (if (urb:anden-block-p first)
              (if (> (length metadata) 9) (nth 9 metadata) "20 x 20 cm")
              (if (> (length metadata) 6) (nth 6 metadata) "20 x 20 cm")))
          (setq calculate
            (if (urb:anden-block-p first)
              (if (> (length metadata) 10) (nth 10 metadata) "Si")
              (if (> (length metadata) 7) (nth 7 metadata) "Si")))
          (setq surface
            (if (urb:anden-block-p first)
              (if (> (length metadata) 11) (nth 11 metadata) "SUP_TN")
              (if (> (length metadata) 8) (nth 8 metadata) "SUP_TN")))
          (setq grade-source
            (if (urb:anden-block-p first)
              (if (> (length metadata) 12) (nth 12 metadata) "Via creada")
              (if (> (length metadata) 9) (nth 9 metadata) "Via creada")))
          (setq material (urb:safe-string material "Loseta"))
          (setq etapa (urb:safe-string etapa "1"))
          (setq subetapa (urb:safe-string subetapa etapa))
          (setq guia (urb:safe-string guia "No"))
          (setq toperol (urb:safe-string toperol "No"))
          (setq format (urb:safe-string format "20 x 20 cm"))
          (setq calculate (urb:safe-string calculate "Si"))
          (setq surface (urb:safe-string surface "SUP_TN"))
          (setq grade-source (urb:safe-string grade-source "Via creada"))
          ;; Orientacion/extremo van dentro del mismo dialogo (igual que en
          ;; la creacion); aqui las listas incluyen "Conservar" para
          ;; mantener el sentido propio de cada anden seleccionado. El lado
          ;; del toperol se marca con un click despues de aceptar.
          (setq data
            (urb:dialog-anden
              material format etapa subetapa guia toperol
              calculate surface grade-source
              "Conservar" "Conservar"
              '("Conservar" "Automatico" "Girar90")
              '("Conservar" "Normal" "Opuesto")))
          (if data
            (progn
              (setq material (nth 0 data))
              (setq format (nth 1 data))
              (setq etapa (nth 2 data))
              (setq subetapa (nth 3 data))
              (setq guia (nth 4 data))
              (setq toperol (nth 5 data))
              (setq calculate (nth 6 data))
              (setq surface (nth 7 data))
              (setq grade-source (nth 8 data))
              (setq orientation-choice (nth 9 data))
              (setq start-choice (nth 10 data))
              (setq material (urb:safe-string material "Loseta"))
              (setq etapa (urb:safe-string etapa "1"))
              (setq subetapa (urb:safe-string subetapa etapa))
              (setq guia (urb:safe-string guia "No"))
              (setq toperol (urb:safe-string toperol "No"))
              (setq format (urb:safe-string format "40 x 40 cm"))
              (setq calculate (urb:safe-string calculate "Si"))
              (setq surface (urb:safe-string surface "SUP_TN"))
              (setq grade-source (urb:safe-string grade-source "Via creada"))
              (if (or (urb:yes-p guia) (urb:yes-p toperol))
                (progn
                  (setq *urb-confirm-tactile-side* T)
                  (setq *urb-current-tactile-side-point* nil
                        *urb-current-tactile-side-choice* nil)
                  ;; El ancla se calcula por cada contorno dentro de
                  ;; urb:rebuild-working-boundary.
                  (setq *urb-current-tactile-side-anchor* nil)))
              (setq deleted 0 updated 0 failed 0)
              (foreach ename parents
                (setq old-pattern-mode (urb:anden-pattern-mode ename)
                      old-rotated
                        (urb:anden-pattern-rotated-p old-pattern-mode)
                      old-reversed
                        (urb:anden-pattern-reversed-p old-pattern-mode)
                      new-rotated
                        (cond
                          ((= orientation-choice "Automatico") nil)
                          ((= orientation-choice "Girar90") T)
                          (T old-rotated))
                      new-reversed
                        (cond
                          ((= start-choice "Normal") nil)
                          ((= start-choice "Opuesto") T)
                          (T old-reversed))
                      pattern-mode
                        (urb:compose-anden-pattern-mode
                          new-rotated new-reversed))
                (if (urb:anden-block-p ename)
                  (progn
                    (setq metadata
                      (urb:anden-block-data ename))
                    (setq old-material (nth 1 metadata))
                    (setq old-schema
                      (if (> (length metadata) 6) (nth 6 metadata) "0"))
                    (setq old-guia
                      (if (> (length metadata) 7) (nth 7 metadata) "No"))
                    (setq old-toperol
                      (if (> (length metadata) 8) (nth 8 metadata) "No"))
                    (setq old-format
                      (if (> (length metadata) 9) (nth 9 metadata) "20 x 20 cm"))
                    (setq old-calculate
                      (if (> (length metadata) 10) (nth 10 metadata) "Si"))
                    (setq old-surface
                      (if (> (length metadata) 11) (nth 11 metadata) "SUP_TN"))
                    (setq old-grade-source
                      (if (> (length metadata) 12) (nth 12 metadata) "Via creada"))
                    (setq old-movement
                      (urb:get-xdata-strings ename "URB_ANDEN_MOV"))
                    (setq old-earthworks-p
                      (urb:valid-anden-earthworks-data-p old-movement))
                    (if (and
                          (= old-schema *urb-schema-version*)
                          (urb:string-equal-p old-material material)
                          (urb:string-equal-p old-guia guia)
                          (urb:string-equal-p old-toperol toperol)
                          (urb:string-equal-p old-format format)
                          (urb:string-equal-p old-calculate calculate)
                          (urb:string-equal-p old-surface surface)
                          (urb:string-equal-p old-grade-source grade-source)
                          (urb:string-equal-p
                            old-pattern-mode pattern-mode)
                          ;; Con calculo activo, EDITAR tambien funciona como
                          ;; recalculo aunque el dialogo no haya cambiado.
                          (not (urb:yes-p calculate)))
                      (progn
                        (if
                          (urb:call-edit-stage
                            "actualizar propiedades"
                            'urb:update-anden-block-data
                            (list ename material etapa subetapa guia toperol
                              format calculate surface grade-source))
                          (setq updated (1+ updated))
                          (setq failed (1+ failed)))
                        ;; 2026-09-10: aqui la geometria no cambia, asi que
                        ;; el movimiento se puede rehacer sobre el MISMO
                        ;; bloque -- segundos, en vez de los minutos que
                        ;; cuesta reconstruir el anden entero.
                        (if (urb:ask-edit-movimiento "el anden")
                          (urb:call-edit-stage
                            "editar movimiento del anden"
                            'urb:anden-earthworks-por-cotas
                            (list ename (urb:anden-block-points ename)))))
                      (progn
                        (setq boundary
                          (urb:call-edit-stage
                            "extraer contorno"
                            'urb:explode-anden-block-boundary
                            (list ename)))
                        (if boundary
                          (progn
                            (urb:set-anden-pattern-mode
                              boundary pattern-mode)
                            (setq anden-points (urb:lwpoly-points boundary))
                            (setq anden-area
                              (vla-get-Area (vlax-ename->vla-object boundary)))
                            (setq block-ref
                              (urb:rebuild-working-boundary
                                boundary material etapa subetapa
                                guia toperol format calculate surface grade-source))
                            (if block-ref
                              (urb:copy-quantity-scope ename block-ref))
                            (setq earthworks-ok
                              (if block-ref
                                (urb:prompt-anden-earthworks
                                  block-ref anden-points anden-area
                                  calculate surface grade-source)
                                nil))
                            (if
                              (and
                                block-ref
                                (or earthworks-ok (not old-earthworks-p)))
                              (progn
                                ;; La geometria corregida se conserva aunque
                                ;; el movimiento siga pendiente, siempre que
                                ;; el bloque anterior tampoco tuviera un
                                ;; calculo valido que debamos proteger.
                                ;; 2026-08-27: capturar el handle viejo ANTES
                                ;; de borrar, para re-apuntar los anillos de
                                ;; prefabricado al bloque nuevo (sin esto el
                                ;; descuento de bordillo moria al EDITAR).
                                (setq old-handle
                                  (cdr (assoc 5 (entget ename))))
                                (if
                                  (urb:call-edit-stage
                                    "reemplazar bloque anterior"
                                    'urb:delete-anden-block
                                    (list ename))
                                  (progn
                                    (setq new-ename (urb:as-ename block-ref))
                                    (if (and old-handle new-ename)
                                      (urb:relink-anden-anillos old-handle
                                        (cdr (assoc 5 (entget new-ename)))))
                                    (setq updated (1+ updated)))
                                  (progn
                                    (setq new-ename (urb:as-ename block-ref))
                                    (if new-ename
                                      (urb:delete-anden-block new-ename))
                                    (setq failed (1+ failed)))))
                              (progn
                                ;; Un movimiento anterior valido no se pierde
                                ;; si su recalculo fue cancelado o fallo.
                                (setq new-ename (urb:as-ename block-ref))
                                (if new-ename (urb:delete-anden-block new-ename))
                                (setq failed (1+ failed)))))
                          (setq failed (1+ failed))))))
                  (progn
                    (setq obj (vlax-ename->vla-object ename))
                    (setq result
                      (urb:call-edit-stage
                        "copiar contorno anterior"
                        'vla-Copy
                        (list obj)))
                    (setq boundary
                      (if result
                        (urb:call-edit-stage
                          "preparar contorno"
                          'urb:as-ename
                          (list result))))
                    (if boundary
                      (progn
                        (urb:set-anden-pattern-mode
                          boundary pattern-mode)
                        (setq anden-points (urb:lwpoly-points boundary))
                        (setq anden-area
                          (vla-get-Area (vlax-ename->vla-object boundary)))))
                    (setq block-ref
                      (if boundary
                        (urb:rebuild-working-boundary
                          boundary material etapa subetapa
                          guia toperol format calculate surface grade-source)))
                    (if block-ref
                      (urb:copy-quantity-scope ename block-ref))
                    ;; Este contorno no era un anden empacado: nunca hubo
                    ;; movimiento de tierras previo, se ofrece calcularlo.
                    (setq earthworks-ok
                      (if block-ref
                        (urb:prompt-anden-earthworks
                          block-ref anden-points anden-area
                          calculate surface grade-source)
                        nil))
                    (setq old-handle
                      (vl-catch-all-apply 'vla-get-Handle (list obj)))
                    (if (vl-catch-all-error-p old-handle)
                      (setq old-handle nil))
                    (if block-ref
                      (if (urb:safe-delete obj)
                        (progn
                          ;; Los auxiliares se limpian solo despues de confirmar
                          ;; que el contorno anterior realmente fue eliminado.
                          (if old-handle
                            (progn
                              (urb:remove-anden-group old-handle)
                              (setq deleted
                                (+ deleted
                                   (urb:delete-generated old-handle)))))
                          (setq updated (1+ updated)))
                        (progn
                          ;; Evita dejar dos andenes si AutoCAD impide borrar
                          ;; el objeto anterior (capa bloqueada, proxy, etc.).
                          (setq new-ename (urb:as-ename block-ref))
                          (if new-ename (urb:delete-anden-block new-ename))
                          (setq failed (1+ failed))))
                      (progn
                        (setq new-ename (urb:as-ename block-ref))
                        (if new-ename (urb:delete-anden-block new-ename))
                        (setq failed (1+ failed))))))
              )
              (vla-Regen (urb:doc) 1)
              (prompt
                (strcat
                  "\nAndenes actualizados: " (itoa updated)
                  " | Fallidos: " (itoa failed)
                  " | Elementos reemplazados: "
                  (itoa deleted) ".")))))
        (if prefabs
          (urb:edit-prefabs prefabs)
          (if greens
            (urb:edit-green-zones greens)
            (if mp-entities
              ;; 5.6.0: con tramos en la seleccion EDITAR ofrece tambien
              ;; voltear su texto (integrado aqui a pedido del usuario:
              ;; nada de comandos sueltos). Enter = Propiedades, como antes.
              (if (and (vl-some
                         '(lambda (e)
                            (mp:base-is-tramo
                              (mp:infer-base
                                (vla-get-EffectiveName (vlax-ename->vla-object e))
                                (mp:att-alist e))))
                         mp-entities)
                       (progn
                         (initget "Propiedades Voltear")
                         (= "Voltear"
                            (getkword
                              "\nTramos: [Propiedades/Voltear texto] <Propiedades>: "))))
                (mp:flip-tramo-texts mp-entities)
                (foreach ename mp-entities (mp:edit-entity ename)))
              (if senderos
                ;; 5.6.2: senderos -> recalcular su movimiento de tierras
                (urb:edit-senderos-movimiento senderos)
                (prompt
                "\nLa seleccion no contiene elementos editables."))))))))
    (prompt "\nNo se selecciono ningun objeto."))
  (setq *urb-current-tactile-side-point* nil
        *urb-current-tactile-side-anchor* nil
        *urb-current-tactile-side-choice* nil)
  (if undo-open
    (progn
      (vl-catch-all-apply 'vla-EndUndoMark (list doc))
      (setq undo-open nil)))
  (princ)
)


(defun urb:add-hatch
  (boundary layer pattern pattern-type fallback scale color
   / first-error result)
  (setq result
    (vl-catch-all-apply
      'urb:add-hatch-raw
      (list boundary layer pattern pattern-type scale color)))
  (if (vl-catch-all-error-p result)
    (progn
      (setq first-error (vl-catch-all-error-message result))
      (prompt
        (strcat
          "\nEl patron " pattern " no pudo crearse: "
          first-error
          "\nIntentando patron nativo " fallback "..."))
      (setq result
        (vl-catch-all-apply
          'urb:add-hatch-raw
          (list boundary layer fallback 1 scale color)))
      (if (vl-catch-all-error-p result)
        (prompt
          (strcat
            "\nERROR al crear el achurado: "
            (vl-catch-all-error-message result)))
      )
    )
  )
  result
)

;; Nota 4.1.0: se eliminaron urb:prepare-layers, urb:process-selection,
;; urb:get-scale y urb:select-polygons (solo las usaban los antiguos
;; comandos URBLOSETA/URBVIA retirados del sistema).

(defun urb:layer-description (layer / parts)
  (setq parts
    (cond
      ((= layer "URB-ANDEN") '("ANDEN" "LOSETA"))
      ((= layer "URB-BORDILLO") '("BORDILLO" "PREFABRICADO"))
      ((= layer "URB-SARDINEL") '("SARDINEL" "PREFABRICADO"))
      ((= layer "URB-CANUELA") '("CANUELA" "PREFABRICADO"))
      ;; Nombres de capa anteriores a la consolidacion 4.18.0 -- se
      ;; conservan para etiquetar filas de dibujos viejos correctamente.
      ((= layer "URB-Q-ANDEN-LOSETA") '("ANDEN" "LOSETA"))
      ((= layer "URB-Q-ANDEN-ADOQUIN") '("ANDEN" "ADOQUIN"))
      ((= layer "URB-Q-VIA-ASFALTO") '("VIA" "ASFALTO"))
      ((= layer "URB-Q-VIA-CONCRETO") '("VIA" "CONCRETO"))
      ((= layer "URB-Q-VIA-ADOQUIN") '("VIA" "ADOQUIN"))
      ((= layer "URB-PREFAB-SARDINEL") '("SARDINEL" "PREFABRICADO"))
      ((= layer "URB-PREFAB-BORDILLO") '("BORDILLO" "PREFABRICADO"))
      ((= layer "URB-PREFAB-BORDILLO-BLOQUE")
        '("BORDILLO" "PREFABRICADO"))
      ((= layer "URB-PREFAB-SARDINEL-BLOQUE")
        '("SARDINEL" "PREFABRICADO"))
      ((= layer "URB-PREFAB-CANUELA-BLOQUE")
        '("CANUELA" "PREFABRICADO"))
    )
  )
  parts
)

(defun urb:accumulate
  (rows key layer etapa subetapa area perimeter / item)
  (if (setq item (assoc key rows))
    (subst
      (list key
        (1+ (nth 1 item))
        (+ area (nth 2 item))
        (+ perimeter (nth 3 item))
        layer etapa subetapa)
      item
      rows)
    (cons
      (list key 1 area perimeter layer etapa subetapa)
      rows)
  )
)

(defun urb:draw-open-polyline
  (label / before after obj old-plinewid *error*)
  (setq old-plinewid (getvar "PLINEWID"))
  (defun *error* (message)
    (if old-plinewid (setvar "PLINEWID" old-plinewid))
    (if (and message
             (not (member message '("Function cancelled" "quit / exit abort"))))
      (prompt (strcat "\nError al dibujar el recorrido: " message)))
    (princ))
  (setvar "PLINEWID" 0.0)
  (setq before (entlast))
  (prompt
    (strcat
      "\nDibuje el recorrido de " label
      ". Enter termina el trazado."))
  (urb:draw-polyline-once before)
  (setq after (entlast))
  (if (and after (/= after before)
           (= (cdr (assoc 0 (entget after))) "LWPOLYLINE"))
    (progn
      (setq obj (vlax-ename->vla-object after))
      (if (vlax-property-available-p obj 'ConstantWidth T)
        (vla-put-ConstantWidth obj 0.0))
      after)
    nil)
)

(defun urb:offset-candidate (obj distance-value / result objects candidate item)
  (setq result
    (vl-catch-all-apply 'vla-Offset (list obj distance-value)))
  (if (vl-catch-all-error-p result)
    nil
    (progn
      (setq objects (urb:variant-object-list result))
      (setq candidate (car objects))
      (foreach item (cdr objects) (urb:safe-delete item))
      candidate))
)

(defun urb:point-to-curve-distance (point obj / closest result)
  (setq result
    (vl-catch-all-apply
      'vlax-curve-getClosestPointTo
      (list (vlax-vla-object->ename obj) point)))
  (if (vl-catch-all-error-p result)
    1.0e99
    (distance point result))
)

(defun urb:offset-toward-point
  (obj width side-point / positive negative selected)
  (setq positive (urb:offset-candidate obj width))
  (setq negative (urb:offset-candidate obj (- width)))
  (cond
    ((and positive negative)
      (if
        (<= (urb:point-to-curve-distance side-point positive)
            (urb:point-to-curve-distance side-point negative))
        (progn (setq selected positive) (urb:safe-delete negative))
        (progn (setq selected negative) (urb:safe-delete positive))))
    (positive (setq selected positive))
    (negative (setq selected negative)))
  selected
)

(defun urb:add-solid-hatch-loop (objects layer color / hatch result)
  (setq hatch
    (vl-catch-all-apply
      'vla-AddHatch
      (list (urb:space) 1 "SOLID" :vlax-true)))
  (if (vl-catch-all-error-p hatch)
    nil
    (progn
      (setq result
        (vl-catch-all-apply
          'vla-AppendOuterLoop
          (list hatch (urb:object-array-variant objects))))
      (if (vl-catch-all-error-p result)
        (progn (urb:safe-delete hatch) nil)
        (progn
          (vla-put-Layer hatch layer)
          (vla-put-Color hatch color)
          (urb:evaluate-render-hatch hatch)
          hatch))))
)

(defun urb:prefab-token (prefab / s)
  ;; 2026-09-11: el token va a la CAPA, asi que los tipos con espacio
  ;; ("Remate A-105") quedan con guion: URB-REMATE-A-105.
  (setq s (strcase (urb:safe-string prefab "Bordillo")))
  (while (vl-string-search " " s)
    (setq s (vl-string-subst "-" " " s)))
  s
)

;; 4.18.0: una sola capa por tipo de prefabricado (antes 5: BLOQUE/
;; INTERIOR/EXTERIOR/REMATE/RELLENO). El rol de cada pieza (interior,
;; exterior, remate, relleno) ahora se guarda como xdata (urb:tag-generated-role)
;; en vez de codificarse en el nombre de la capa.
(defun urb:prefab-layer (prefab)
  (strcat "URB-" (urb:prefab-token prefab))
)

(defun urb:prefab-color (prefab)
  (cond
    ((= (urb:prefab-token prefab) "SARDINEL") 30)
    ((= (urb:prefab-token prefab) "CANUELA") 4)
    ((wcmatch (urb:prefab-token prefab) "*A-105*") 6)
    ;; 2026-09-11: los sardineles de rampa se distinguen del bordillo A-80
    ;; (rojo) para poder leer en planta que material va en cada longitud
    ((wcmatch (urb:prefab-token prefab) "*A-85*") 5)
    ((wcmatch (urb:prefab-token prefab) "*A-86*") 3)
    ((wcmatch (urb:prefab-token prefab) "*A-100*") 2)
    (T 1))
)

(defun urb:package-prefab-block
  (objects source prefab width etapa subetapa mode length-value destino
   / handle block-name blocks block-definition copy-result point
   block-ref area-value obj block-layer insert-result block-ename xdata-result)
  (setq handle (vla-get-Handle source))
  (setq block-name
    (strcat
      "URB_" prefab "_" handle "_"
      (itoa (getvar "MILLISECS"))))
  (setq point
    (vlax-curve-getStartPoint (vlax-vla-object->ename source)))
  (setq blocks (vla-get-Blocks (urb:doc)))
  (setq block-definition
    (vla-Add blocks (vlax-3d-point '(0.0 0.0 0.0)) block-name))
  (setq copy-result
    (vl-catch-all-apply
      'vla-CopyObjects
      (list
        (urb:doc)
        (urb:object-array-variant objects)
        block-definition)))
  (if (vl-catch-all-error-p copy-result)
    (progn
      (urb:safe-delete block-definition)
      nil)
    (progn
      (urb:set-block-draw-order
        block-definition
        (urb:variant-object-list copy-result))
      (setq area-value (* width length-value))
      (urb:add-invisible-attribute
        block-definition point "TIPO" "Tipo" prefab)
      (urb:add-invisible-attribute
        block-definition point "ANCHO_M" "Ancho m" (rtos width 2 3))
      (urb:add-invisible-attribute
        block-definition point "LONGITUD_M" "Longitud m"
        (rtos length-value 2 2))
      (urb:add-invisible-attribute
        block-definition point "AREA_M2" "Area m2"
        (rtos area-value 2 2))
      (urb:add-invisible-attribute
        block-definition point "ETAPA" "Etapa" etapa)
      (urb:add-invisible-attribute
        block-definition point "SUBETAPA" "Subetapa" subetapa)
      (urb:add-invisible-attribute
        block-definition point "MODELADO" "Modelado" mode)
      (urb:add-invisible-attribute
        block-definition point "DESTINO_PPTO" "Destino presupuesto" destino)
      (setq insert-result
        (vl-catch-all-apply
          'vla-InsertBlock
          (list
            (urb:space)
            (vlax-3d-point '(0.0 0.0 0.0))
            block-name 1.0 1.0 1.0 0.0)))
      (if (vl-catch-all-error-p insert-result)
        (progn
          (urb:safe-delete block-definition)
          (prompt
            (strcat "\nERROR al insertar el bloque prefabricado: "
              (vl-catch-all-error-message insert-result)))
          nil)
        (progn
          (setq block-ref insert-result block-ename (urb:as-ename block-ref))
          (if (not block-ename)
            (progn
              (urb:safe-delete block-ref)
              (urb:safe-delete block-definition)
              (prompt
                "\nERROR: AutoCAD no devolvio una referencia de bloque prefabricado valida.")
              nil)
            (progn
              (setq block-layer (urb:prefab-layer prefab))
              (vla-put-Layer block-ref block-layer)
              (setq xdata-result
                (urb:set-xdata-strings
                  block-ename
                  "URB_PREFAB_BLOCK"
                   (list prefab etapa subetapa
                         (rtos width 2 8)
                         (rtos length-value 2 8)
                         mode *urb-prefab-schema-version* destino)))
              (if xdata-result
                (progn
                  (foreach obj objects (urb:safe-delete obj))
                  ;; 2026-09-02 (pedido del usuario: bordillo tapado por el
                  ;; anden): el prefabricado SIEMPRE al frente del orden de
                  ;; dibujo -- nunca queda debajo del relleno del anden
                  (vl-catch-all-apply 'vl-cmdf
                    (list "_.DRAWORDER" block-ename "" "_Front"))
                  block-ref)
                (progn
                  (urb:safe-delete block-ref)
                  (urb:safe-delete block-definition)
                  (prompt
                    "\nERROR: no fue posible guardar los datos del bloque prefabricado.")
                  nil))))))))
)

(defun urb:prepare-prefab-layers (prefab / color)
  (setq color (urb:prefab-color prefab))
  (urb:ensure-layer (urb:prefab-layer prefab) color T)
)

(defun urb:build-prefab-from-reference
  (ename side-point prefab width etapa subetapa mode destino
   / source offset piece-layer source-role offset-role
   source-start source-end offset-start offset-end temp connector-start
   connector-end hatch objects length-value block-ref color parent-handle)
  (setq prefab (urb:safe-string prefab "Bordillo"))
  (setq mode (urb:safe-string mode "Interior"))
  (setq destino
    (urb:safe-string destino (urb:prefab-destino-default prefab)))
  (urb:prepare-prefab-layers prefab)
  (setq color (urb:prefab-color prefab))
  (setq source (vlax-ename->vla-object ename))
  (setq offset (urb:offset-toward-point source width side-point))
  (if offset
    (progn
      ;; 4.18.0: una sola capa por tipo (piece-layer). Interior/exterior/
      ;; remate/relleno se distinguen por rol xdata, no por capa; el color
      ;; de interior (3, verde) se conserva como color de entidad.
      (setq piece-layer (urb:prefab-layer prefab))
      (if (urb:string-equal-p mode "Interior")
        (setq source-role "EXTERIOR" offset-role "INTERIOR")
        (setq source-role "INTERIOR" offset-role "EXTERIOR"))
      (setq parent-handle (vla-get-Handle source))
      (vla-put-Layer source piece-layer)
      (vla-put-Layer offset piece-layer)
      (vla-put-Color source (if (= source-role "INTERIOR") 3 color))
      (vla-put-Color offset (if (= offset-role "INTERIOR") 3 color))
      (urb:tag-generated-role source parent-handle source-role)
      (urb:tag-generated-role offset parent-handle offset-role)
      (setq source-start (vlax-curve-getStartPoint ename))
      (setq source-end (vlax-curve-getEndPoint ename))
      (setq offset-start
        (vlax-curve-getStartPoint (vlax-vla-object->ename offset)))
      (setq offset-end
        (vlax-curve-getEndPoint (vlax-vla-object->ename offset)))
      (if (> (distance source-start offset-start)
             (distance source-start offset-end))
        (progn
          (setq temp offset-start)
          (setq offset-start offset-end)
          (setq offset-end temp)))
      (setq connector-start
        (vla-AddLine
          (urb:space)
          (vlax-3d-point source-start)
          (vlax-3d-point offset-start)))
      (setq connector-end
        (vla-AddLine
          (urb:space)
          (vlax-3d-point source-end)
          (vlax-3d-point offset-end)))
      (vla-put-Layer connector-start piece-layer)
      (vla-put-Layer connector-end piece-layer)
      (urb:tag-generated-role connector-start parent-handle "REMATE")
      (urb:tag-generated-role connector-end parent-handle "REMATE")
      (setq objects (list source connector-end offset connector-start))
      (setq hatch
        (urb:add-solid-hatch-loop objects piece-layer color))
      (if hatch
        (progn
          (urb:tag-generated-role hatch parent-handle "RELLENO")
          (setq objects (append objects (list hatch)))))
      (setq length-value (urb:poly-perimeter source))
      (setq block-ref
        (urb:package-prefab-block
          objects source prefab width etapa subetapa mode length-value destino))
      (if (not block-ref)
        (foreach temp objects (urb:safe-delete temp))))
    (urb:safe-delete source))
  block-ref
)

;; ---------- prefabricado PERIMETRAL (2026-08-21 v4.50, pedido del
;; usuario): anillo de prefabricado alrededor de un contorno CERRADO de
;; anden o sendero. Posicion Externo = el anillo crece hacia AFUERA (el
;; area dibujada queda intacta); Interno = el anillo ocupa una franja
;; DENTRO del area dibujada (y el area del anden/sendero la descuenta).

;; offset de un contorno cerrado controlado por AREA: hacia afuera el
;; area crece y hacia adentro decrece, sin depender del sentido de giro
(defun urb:offset-anillo (obj width hacia-afuera / a0 pos neg sel)
  (setq a0 (vla-get-Area obj))
  (setq pos (urb:offset-candidate obj width))
  (setq neg (urb:offset-candidate obj (- width)))
  (cond
    ((and pos neg)
      (if (eq (> (vla-get-Area pos) a0) hacia-afuera)
        (progn (setq sel pos) (urb:safe-delete neg))
        (progn (setq sel neg) (urb:safe-delete pos))))
    (pos
      (if (eq (> (vla-get-Area pos) a0) hacia-afuera)
        (setq sel pos)
        (urb:safe-delete pos)))
    (neg
      (if (eq (> (vla-get-Area neg) a0) hacia-afuera)
        (setq sel neg)
        (urb:safe-delete neg))))
  sel)

;; construye el anillo como bloque prefabricado estandar (mismas capas,
;; roles xdata y atributos que un prefabricado normal: cuenta solo al
;; presupuesto como ML por su longitud). contour NO se consume.
(defun urb:build-prefab-anillo (contour prefab width etapa subetapa posicion destino
                                / src base ring inner outer externo layer
                                color hatch objects per block-ref)
  (setq externo (urb:string-equal-p posicion "Externo"))
  (urb:prepare-prefab-layers prefab)
  (setq layer (urb:prefab-layer prefab)
        color (urb:prefab-color prefab))
  (setq src (vlax-ename->vla-object contour))
  (setq per (vla-get-Length src))
  (setq base (vl-catch-all-apply 'vla-Copy (list src)))
  (if (vl-catch-all-error-p base)
    nil
    (progn
      (setq ring (urb:offset-anillo base width externo))
      (if (null ring)
        (progn (urb:safe-delete base) nil)
        (progn
          (if externo
            (setq inner base outer ring)
            (setq inner ring outer base))
          (vla-put-Layer inner layer)
          (vla-put-Layer outer layer)
          ;; convencion prefab: la arista interior en verde (3)
          (vla-put-Color inner 3)
          (vla-put-Color outer color)
          (urb:tag-generated-role inner (vla-get-Handle base) "INTERIOR")
          (urb:tag-generated-role outer (vla-get-Handle base) "EXTERIOR")
          (setq hatch
            (vl-catch-all-apply
              '(lambda ()
                (setq hatch
                  (vla-AddHatch (urb:space) 1 "SOLID" :vlax-true))
                (vla-AppendOuterLoop hatch
                  (urb:object-array-variant (list outer)))
                (vla-AppendInnerLoop hatch
                  (urb:object-array-variant (list inner)))
                (vla-put-Layer hatch layer)
                (vla-put-Color hatch color)
                (urb:evaluate-render-hatch hatch)
                hatch)))
          (if (vl-catch-all-error-p hatch)
            (setq hatch nil)
            (urb:tag-generated-role hatch (vla-get-Handle base) "RELLENO"))
          (setq objects
            (append (list inner outer) (if hatch (list hatch))))
          (setq block-ref
            (urb:package-prefab-block objects base prefab width etapa
              subetapa (if externo "Exterior" "Interior") per destino))
          (if (not block-ref)
            (foreach src objects (urb:safe-delete src)))
          block-ref)))))

(defun urb:create-prefabricado
  (/ data prefab width etapa subetapa mode destino ename side-point block-ref)
  (setq data
    (urb:dialog-prefab "Bordillo" 0.20 "1" "1" "Interior" "Anden"))
  (if data
    (progn
      (setq prefab (nth 0 data))
      (setq width (nth 1 data))
      (setq etapa (nth 2 data))
      (setq subetapa (nth 3 data))
      (setq mode (nth 4 data))
      (setq destino (nth 5 data))
      (setq ename
        (urb:draw-open-polyline
          (strcat (strcase prefab) " - arista de referencia")))
      (if ename
        (progn
          (setq side-point
            (getpoint
              (strcat
                "\nMarque un punto hacia el lado " mode
                " donde crecera el espesor: ")))
          (if side-point
            (progn
              (setq block-ref
                (urb:build-prefab-from-reference
                  ename side-point prefab width etapa subetapa mode destino))
              (if block-ref
                (prompt
                  (strcat
                    "\n" (strcase prefab) " creado como bloque."
                    " Destino del presupuesto: " destino "."
                    " Use la arista verde como limite del elemento."))
                (prompt "\nNo fue posible crear el bloque prefabricado.")))
            (progn
              (urb:safe-delete (vlax-ename->vla-object ename))
              (prompt "\nComando cancelado."))))
        (prompt "\nNo se creo una polilinea valida.")))
    (prompt "\nComando cancelado."))
  (princ)
)

(defun urb:create-precast-command ()
  (if (urb:confirm-meter-units)
    (urb:create-prefabricado)
    (prompt "\nComando cancelado: confirme que el dibujo trabaja en metros."))
)

(defun urb:collect-quantities
  (/ ss i ename obj layer rows metadata etapa subetapa key
   material area perimeter prefab)
  (setq rows nil)
  (if (setq ss
        (ssget "_X"
          '((0 . "LWPOLYLINE,POLYLINE"))))
    (progn
      (setq i 0)
      (repeat (sslength ss)
        (setq ename (ssname ss i))
        (setq obj (vlax-ename->vla-object ename))
        (setq layer (strcase (vla-get-Layer obj)))
        (if (and
              (urb:q-modelspace-p ename)
              (urb:starts-with layer "URB-Q-")
              (urb:closed-poly-p ename)
              (urb:layer-description layer))
          (progn
            (setq metadata
              (urb:get-xdata-strings ename "URB_ANDEN"))
            (setq etapa
              (if metadata (nth 2 metadata) ""))
            (setq subetapa
              (if metadata (nth 3 metadata) ""))
            (setq key
              (strcat layer "|" etapa "|" subetapa))
            (setq rows
              (urb:accumulate
                rows key layer etapa subetapa
                (vla-get-Area obj)
                (urb:poly-perimeter obj))))
          (if (setq metadata (urb:prefab-data ename))
            (progn
              (setq etapa (nth 1 metadata))
              (setq subetapa (nth 2 metadata))
              (setq key
                (strcat layer "|" etapa "|" subetapa))
              (setq rows
                (urb:accumulate
                  rows key layer etapa subetapa
                  0.0 (urb:poly-perimeter obj)))))
        )
        (setq i (1+ i))
      )
    )
  )
  (if (setq ss (ssget "_X" '((0 . "INSERT"))))
    (progn
      (setq i 0)
      (repeat (sslength ss)
        (setq ename (ssname ss i))
        (if (and (urb:q-modelspace-p ename)
                 (urb:anden-block-p ename))
          (progn
            (setq metadata
              (urb:get-xdata-strings
                ename "URB_ANDEN_BLOCK"))
            (setq material (nth 1 metadata))
            (setq etapa (nth 2 metadata))
            (setq subetapa (nth 3 metadata))
            (setq area (atof (nth 4 metadata)))
            (setq perimeter (atof (nth 5 metadata)))
            (setq layer
              (if (= (strcase material) "ADOQUIN")
                "URB-Q-ANDEN-ADOQUIN"
                "URB-Q-ANDEN-LOSETA"))
            (setq key
              (strcat layer "|" etapa "|" subetapa))
            (setq rows
              (urb:accumulate
                rows key layer etapa subetapa area perimeter)))
          (if (and (urb:q-modelspace-p ename)
                   (urb:prefab-block-p ename))
            (progn
              (setq metadata
                (urb:get-xdata-strings
                  ename "URB_PREFAB_BLOCK"))
              (setq prefab (urb:safe-string (nth 0 metadata) "BORDILLO"))
              (setq etapa (urb:safe-string (nth 1 metadata) ""))
              (setq subetapa (urb:safe-string (nth 2 metadata) ""))
              (setq perimeter
                (atof (urb:safe-string (nth 4 metadata) "0")))
              (setq layer
                (urb:prefab-layer prefab))
              (setq key
                (strcat layer "|" etapa "|" subetapa))
              (setq rows
                (urb:accumulate
                  rows key layer etapa subetapa 0.0 perimeter)))))
        (setq i (1+ i)))))
  (reverse rows)
)

(defun urb:set-cell (table row col value)
  (vla-SetText table row col value)
)

(defun urb:create-table (point rows / space table textheight rowheight
                         rowindex item description)
  (setq space (urb:space))
  (setq textheight (max 0.01 (getvar "TEXTSIZE")))
  (setq rowheight (* textheight 1.8))
  (setq table
    (vla-AddTable
      space
      (vlax-3d-point point)
      (+ 2 (length rows))
      7
      rowheight
      (* textheight 12.0)))
  (vla-MergeCells table 0 0 0 6)
  (urb:set-cell table 0 0 "CUADRO DE CANTIDADES URBANISMO")
  (urb:set-cell table 1 0 "ELEMENTO")
  (urb:set-cell table 1 1 "MATERIAL")
  (urb:set-cell table 1 2 "ETAPA")
  (urb:set-cell table 1 3 "SUBETAPA")
  (urb:set-cell table 1 4 "UNIDADES")
  (urb:set-cell table 1 5 "AREA")
  (urb:set-cell table 1 6 "PERIM./LONG.")
  (setq rowindex 2)
  (foreach item rows
    (setq description (urb:layer-description (nth 4 item)))
    (urb:set-cell table rowindex 0 (nth 0 description))
    (urb:set-cell table rowindex 1 (nth 1 description))
    (urb:set-cell table rowindex 2 (nth 5 item))
    (urb:set-cell table rowindex 3 (nth 6 item))
    (urb:set-cell table rowindex 4 (itoa (nth 1 item)))
    (urb:set-cell table rowindex 5 (rtos (nth 2 item) 2 2))
    (urb:set-cell table rowindex 6 (rtos (nth 3 item) 2 2))
    (setq rowindex (1+ rowindex))
  )
  table
)

;; Estructura de pavimento de andenes, senderos peatonales y plazoletas
;; segun estudio de suelos AUS-10786-10. Capas de arriba hacia abajo,
;; espesores en metros; el geotextil tejido tipo 2100 se cuantifica en
;; m2 con traslapo. La excavacion NO se incluye como una capa fija:
;; cuando existe topografia ya forma parte del corte/relleno hasta subrasante.
;; Si no existe topografia se reporta como pendiente, evitando duplicar 0.60 m.
(setq *urb-anden-structure*
  '(("Adoquin o loseta prefabricada" "Tratamiento" "0.06" "0")
    ("Arena de nivelacion" "Volumen" "0.04" "0")
    ("Suministro e instalacion de subbase granular SBG-C" "Volumen" "0.50" "0")
    ("Suministro y colocacion de geotextil Tejido 2100" "Geotextil" "0" "15")
    ("Suministro e instalacion de Geomembrana (Incluye excavacion)" "Geomalla" "0" "0")))

;; 2026-08-24 (pedido del usuario): el perfil estratigrafico del anden es
;; EDITABLE desde la ventana Movimiento de tierras. Reconstruye la lista
;; con los espesores nuevos y actualiza *urb-anden-depth* = suma de las
;; capas (unica fuente de verdad de la excavacion del anden, antes fija
;; en 6+4+50 = 60 cm). El geotextil (15% traslapo) y la geomembrana no
;; llevan espesor y quedan como estan.
(defun urb:anden-structure-apply (adoquin arena sbg)
  (setq *urb-anden-structure*
    (list
      (list "Adoquin o loseta prefabricada" "Tratamiento"
        (rtos adoquin 2 3) "0")
      (list "Arena de nivelacion" "Volumen" (rtos arena 2 3) "0")
      (list "Suministro e instalacion de subbase granular SBG-C" "Volumen"
        (rtos sbg 2 3) "0")
      (list "Suministro y colocacion de geotextil Tejido 2100" "Geotextil"
        "0" "15")
      (list "Suministro e instalacion de Geomembrana (Incluye excavacion)"
        "Geomalla" "0" "0")))
  (setq *urb-anden-depth* (+ adoquin arena sbg)))

(defun urb:anden-structure-rows
  (area / result layer layer-type thickness overlap quantity unit thick-label)
  ;; La capa de acabado se informa por formato y tipo en
  ;; urb:anden-finish-rows; aqui quedan solamente las capas inferiores.
  (foreach layer (cdr *urb-anden-structure*)
    (setq layer-type (nth 1 layer))
    (setq thickness (atof (nth 2 layer)))
    (setq overlap (atof (nth 3 layer)))
    (if (urb:string-equal-p layer-type "Volumen")
      (setq quantity (* area thickness)
            unit "M3"
            thick-label (strcat (rtos (* 100.0 thickness) 2 0) " cm"))
      (setq quantity (* area (+ 1.0 (/ overlap 100.0)))
            unit "M2"
            thick-label
              (if (> thickness 0.0)
                (strcat (rtos (* 100.0 thickness) 2 0) " cm")
                "-")))
    (setq result
      (append result
        (list (list (nth 0 layer) thick-label quantity unit)))))
  result
)

(defun urb:finish-total-add (totals key value / pair)
  (setq pair (assoc key totals))
  (if pair
    (subst (cons key (+ (cdr pair) value)) pair totals)
    (cons (cons key value) totals))
)

(defun urb:anden-finish-rows
  (/ ss index data material format totals key result pair label unit)
  (setq ss (ssget "_X" '((-3 ("URB_ANDEN_BLOCK")))))
  (if ss
    (progn
      (setq index 0)
      (repeat (sslength ss)
        (setq data
          (urb:get-xdata-strings (ssname ss index) "URB_ANDEN_BLOCK"))
        (setq material (strcase (urb:safe-string (nth 1 data) "")))
        (if (= material "LOSETA")
          (progn
            (setq format
              (if (> (length data) 9) (nth 9 data) "20 x 20 cm"))
            (setq totals
              (urb:finish-total-add totals (strcat "LISA|" format)
                (atof (urb:safe-string
                  (if (> (length data) 14) (nth 14 data) "0") "0"))))
            (setq totals
              (urb:finish-total-add totals (strcat "GUIA|" format)
                (atof (urb:safe-string
                  (if (> (length data) 15) (nth 15 data) "0") "0"))))
            (setq totals
              (urb:finish-total-add totals (strcat "TOPEROL|" format)
                (atof (urb:safe-string
                  (if (> (length data) 16) (nth 16 data) "0") "0"))))
            (setq totals
              (urb:finish-total-add totals "ADOQUIN|20 x 10 cm"
                (atof (urb:safe-string
                  (if (> (length data) 18) (nth 18 data) "0") "0"))))))
        (setq index (1+ index)))))
  (foreach pair (reverse totals)
    (cond
      ((urb:starts-with (car pair) "LISA|")
        (setq label (strcat "Loseta lisa " (substr (car pair) 6)) unit "UND"))
      ((urb:starts-with (car pair) "GUIA|")
        (setq label (strcat "Loseta guia " (substr (car pair) 6)) unit "ML"))
      ((urb:starts-with (car pair) "TOPEROL|")
        (setq label (strcat "Loseta toperol " (substr (car pair) 9)) unit "ML"))
      (T
        (setq label "Adoquin blanco 20 x 10 cm" unit "UND")))
    (if (> (cdr pair) 1e-9)
      (setq result
        (append result (list (list label "-" (cdr pair) unit))))))
  result
)

(defun urb:create-anden-structure-table
  (point area / rows mov extra space table textheight rowheight rowindex item)
  (setq rows
    (append (urb:anden-finish-rows) (urb:anden-structure-rows area)))
  (setq mov (urb:anden-earthworks-totals))
  (setq extra (if (> (nth 2 mov) 0) 2 0))
  (setq space (urb:space))
  (setq textheight (max 0.01 (getvar "TEXTSIZE")))
  (setq rowheight (* textheight 1.8))
  (setq table
    (vla-AddTable
      space
      (vlax-3d-point point)
      (+ 2 (length rows) extra)
      4
      rowheight
      (* textheight 10.0)))
  (vla-MergeCells table 0 0 0 3)
  (urb:set-cell table 0 0 "ESTRUCTURA ANDENES, SENDEROS Y PLAZOLETAS")
  (urb:set-cell table 1 0 "CAPA")
  (urb:set-cell table 1 1 "ESPESOR")
  (urb:set-cell table 1 2 "CANTIDAD")
  (urb:set-cell table 1 3 "UND")
  (setq rowindex 2)
  (foreach item rows
    (urb:set-cell table rowindex 0 (nth 0 item))
    (urb:set-cell table rowindex 1 (nth 1 item))
    (urb:set-cell table rowindex 2 (rtos (nth 2 item) 2 2))
    (urb:set-cell table rowindex 3 (nth 3 item))
    (setq rowindex (1+ rowindex)))
  (if (> extra 0)
    (progn
      (urb:set-cell table rowindex 0
        (strcat "Corte con topografia (" (itoa (nth 2 mov)) " anden(es))"))
      (urb:set-cell table rowindex 1 "-")
      (urb:set-cell table rowindex 2 (rtos (nth 0 mov) 2 2))
      (urb:set-cell table rowindex 3 "M3")
      (setq rowindex (1+ rowindex))
      (urb:set-cell table rowindex 0 "Relleno con topografia")
      (urb:set-cell table rowindex 1 "-")
      (urb:set-cell table rowindex 2 (rtos (nth 1 mov) 2 2))
      (urb:set-cell table rowindex 3 "M3")))
  table
)

;; Comando 4.1.0: genera el cuadro de cantidades de andenes y prefabricados.
;; Reconecta urb:collect-quantities y urb:create-table, que quedaron sin
;; comando al retirar el antiguo URBCANT. Si hay andenes, agrega debajo
;; la tabla de la estructura de pavimento peatonal.
(defun urb:insert-quantities-table-command
  (/ rows point item anden-area textheight offset)
  (if (urb:confirm-meter-units)
    (progn
      (setq rows (urb:collect-quantities))
      (if rows
        (progn
          (setq point
            (getpoint "\nPunto de insercion del cuadro de cantidades: "))
          (if point
            (progn
              (urb:create-table point rows)
              (setq anden-area 0.0)
              (foreach item rows
                (if (urb:starts-with (nth 4 item) "URB-Q-ANDEN-")
                  (setq anden-area (+ anden-area (nth 2 item)))))
              (if (> anden-area 1e-6)
                (progn
                  (setq textheight (max 0.01 (getvar "TEXTSIZE")))
                  (setq offset (* textheight 1.8 (+ 4 (length rows))))
                  (urb:create-anden-structure-table
                    (list (car point) (- (cadr point) offset) 0.0)
                    anden-area)
                  (prompt
                    (strcat
                      "\nEstructura de anden calculada sobre "
                      (rtos anden-area 2 2) " m2."))))
              (vla-Regen (urb:doc) 1)
              (prompt
                (strcat
                  "\nCuadro de cantidades creado con "
                  (itoa (length rows)) " fila(s).")))
            (prompt "\nComando cancelado.")))
        (prompt
          "\nNo se encontraron andenes ni prefabricados cuantificables.")))
    (prompt "\nCANTIDADES cancelado: confirme primero las unidades del dibujo."))
  (princ)
)

(setq *urb-pattern-install-result*
  (vl-catch-all-apply 'urb:install-patterns nil))
(if (and
      (not (vl-catch-all-error-p *urb-pattern-install-result*))
      *urb-pattern-install-result*)
  (prompt
    (strcat
      "\nUrbanismo Cantidades " *urb-version*
      " cargado."))
  (prompt
    "\nUrbanismo cargado, pero no fue posible instalar los patrones temporales."))
(prompt
  "\nComandos principales: URBANISMO y EDITAR.")
(princ)


;;; ============================================================
;;; MODULO INTEGRADO MAIPORE REDES V13
;;; ============================================================
;;; MAIPORE_BLOQUES_REDES_ELECT_LISTAS_V13_OPTIMIZADO.lsp
;;; Urbanismo Interno Maipore - Captura y exportacion de cantidades PPTO
;;;
;;; Mejoras V13:
;;; - Codigo consolidado: una sola definicion por funcion y comando.
;;; - Reutilizacion de definiciones para reducir el crecimiento del DWG.
;;; - Cancelacion segura, longitud geometrica protegida y CSV con conteo.
;;; - Edicion unificada con el comando EDITAR.
;;; - Migracion de atributos existentes mediante las rutinas internas.
;;; - Pendiente hidrosanitaria visible y actualizada por EDITAR.
;;;
;;; Flujo: cargue el LSP, ejecute MAIPORE_BLOQUES_REDES_ELECT,
;;; inserte cantidades, edite con EDITAR y exporte desde URBANISMO.


(vl-load-com)

;; Desactiva comandos de edicion de versiones anteriores al recargar.
(vl-catch-all-apply 'vl-acad-undefun (list 'c:EDITAR_PPTO))
(vl-catch-all-apply 'vl-acad-undefun (list 'c:EDIT_CANTIDAD))
(vl-catch-all-apply 'vl-acad-undefun (list 'c:EDITAR_CANTIDAD))
(setq c:EDITAR_PPTO nil)
(setq c:EDIT_CANTIDAD nil)
(setq c:EDITAR_CANTIDAD nil)

(setq *mp-vis-width* 0.20) ; ancho visual unificado de todos los tramos
(setq *mp-vis-radius* 1.50) ; radio de circulos de inicio/fin
(setq *mp-vis-text-height* 1.50) ; altura de datos de elementos puntuales
(setq *mp-vis-tramo-text-height* 0.60) ; altura unificada de datos del tramo
;; 5.6.0 (pedido del usuario: "que en configuracion pueda graduar la
;; separacion frente al eje del tramo"): espacio LIBRE entre el borde de
;; la linea del tramo y el borde del texto. v5.5.13 lo dejaba fijo en
;; 0.75 x altura desde el EJE, sin contar el espesor de la linea: con un
;; tramo grueso el texto quedaba practicamente encima.
(setq *mp-vis-tramo-text-gap* 0.15)

;; Separador del CSV: ";" abre en columnas en Excel con configuracion
;; regional de Colombia/Espana. Cambie a "," si su sistema usa la coma.
(setq *mp-csv-sep* ";")

;; Marcas de sesion: fuerzan a reescribir los DCL temporales tras recargar.
(setq *mp-dcl-listas-ok* nil)
(setq *mp-dcl-puntos-ok* nil)
(setq *mp-dcl-editar-ok* nil)

(setq *mp-blocks*
  '("TRAMO_E_MT" "TRAMO_E_BT_AP" "CAMARA_CS274" "CAMARA_CS275" "CAMARA_CS276" "CAMARA_CS280" "CAJA_BARRAJE_CS281"
    "POSTE_ELEC" "SUBESTACION_E" "CDMT_E" "LUMINARIA_AP" "TRANSFORMADOR_AP" "PUNTO_CONEXION_E"
    "TRAMO_ARESIDUAL" "TRAMO_ALLUVIAS" "TRAMO_ACUEDUCTO" "POZO_SANITARIO" "POZO_PLUVIAL" "SUMIDERO"
    "ACCESORIO_ACUEDUCTO"))


(setq *mp-red-list* '("Aresidual" "Alluvias" "Acueducto"))
(setq *mp-extremo-hidro-list*
  '("NINGUNO" "POZO" "SUMIDERO" "ACCESORIO_ACUEDUCTO"))
(setq *mp-extremo-elec-list*
  '("NINGUNO" "CAMARA_CS274" "CAMARA_CS275" "CAMARA_CS276" "CAMARA_CS280"
    "CAJA_BARRAJE_CS281" "POSTE_ELEC" "SUBESTACION_E" "CDMT_E"
    "TRANSFORMADOR_AP" "PUNTO_CONEXION_E"))
;; Cajas y camaras electricas CODENSA (Likinormas):
;; CS274 doble para AP/BT (acometidas), CS275 sencilla, CS276 doble MT,
;; CS280 camara de paso MT, CS281 caja para barraje.
(setq *mp-caja-elec-list*
  '("CAMARA_CS274" "CAMARA_CS275" "CAMARA_CS276" "CAMARA_CS280"
    "CAJA_BARRAJE_CS281"))
;; Ubicacion del banco de ductos: define el recubrimiento normativo
;; (CODENSA CS203/CS207: 0.60 m bajo anden o zona verde, 0.80 m bajo calzada).
(setq *mp-ubic-elec-list* '("Anden o zona verde" "Calzada"))
;; 2026-09-13: se agrega 45" (GRP del colector). Va DESPUES de 36" para no
;; correr los indices 0-13, que son los que usan los mp:fill-popup por
;; defecto de los dialogos de tramo.
(setq *mp-diam-alc-list* '("6" "8" "10" "12" "14" "15" "16" "18" "20" "24" "27" "30" "33" "36" "45" "48" "51" "54" "64"))
(setq *mp-diam-acu-list* '("4" "6" "8" "10" "12" "18" "24"))

;; --- Diametros EDITABLES (2026-09-13, pedido del usuario) -------------
;; Mismo patron que el catalogo de etapas: la lista vive en la
;; configuracion del DIBUJO (URB_DIAMETROS_ALC / URB_DIAMETROS_ACU) y se
;; administra desde Configuracion -> Diametros de tuberia. Si el dibujo no
;; trae nada guardado, quedan las listas de fabrica de arriba.
;; OJO: los dialogos de creacion ya NO eligen el diametro por defecto por
;; POSICION sino por VALOR (mp:fill-popup-val). Con la lista editable, un
;; indice fijo dejaba de apuntar al diametro que se queria.
(setq *urb-diam-alc-default* *mp-diam-alc-list*)
(setq *urb-diam-acu-default* *mp-diam-acu-list*)

(defun urb:diam-config-key (red)
  (if (= red "ACU") "URB_DIAMETROS_ACU" "URB_DIAMETROS_ALC"))

(defun urb:diam-default-list (red)
  (if (= red "ACU") *urb-diam-acu-default* *urb-diam-alc-default*))

(defun urb:diam-list-of (red)
  (if (= red "ACU") *mp-diam-acu-list* *mp-diam-alc-list*))

(defun urb:diam-set-list (red lst)
  (if (= red "ACU")
    (setq *mp-diam-acu-list* lst)
    (setq *mp-diam-alc-list* lst)))

;; la lista es de TEXTOS ("6" "8" "10"): un sort alfabetico pondria "10"
;; antes que "6", asi que se ordena por el valor numerico. vl-sort ademas
;; elimina duplicados, que es justo lo que se quiere aqui.
(defun urb:diam-sort (lst)
  (mapcar 'itoa (vl-sort (mapcar 'atoi lst) '<)))

(defun urb:refresh-diametros-catalog (/ red raw parsed)
  (foreach red '("ALC" "ACU")
    (setq raw (urb:config-read (urb:diam-config-key red)))
    (if (and raw (/= raw ""))
      (progn
        (setq parsed (urb:read-lisp-safe raw))
        (if (and parsed (listp parsed) (= (type (car parsed)) 'STR))
          (urb:diam-set-list red parsed)))))
  (princ))

(defun urb:save-diametros-catalog (red)
  (urb:config-write (urb:diam-config-key red)
    (urb:serialize-lisp (urb:diam-list-of red))))

;; Desde 5.3.0 NINGUN diametro se queda sin ancho de zanja: el que no esta
;; en *mp-pvc-trench-width-table* se interpola entre sus vecinos. El gestor
;; ya no avisa de un problema, solo informa cuales anchos son interpolados
;; y cual le quedo al diametro que se acaba de agregar.
(defun urb:diam-interpolado-p (d)
  (if (mp:trench-width-exacto-p (atoi (urb:safe-string d "0"))) nil T))

;; ancho para el primer tramo de profundidad (H<=1,5 m), que es el que se
;; muestra en pantalla como referencia
(defun urb:diam-ancho-txt (d / w)
  (setq w (mp:pvc-trench-width (atoi (urb:safe-string d "0")) 1.0))
  (if w (strcat (rtos w 2 2) " m") "-"))

;; Defecto del popup de diametro en los dialogos de CREACION: el valor
;; pedido si sigue en el catalogo; si el usuario lo borro, el primero de la
;; lista. No se usa mp:fill-popup-val a secas porque esa AGREGA al popup el
;; valor ausente, y haria reaparecer un diametro que se quito a proposito.
;; (En los dialogos de EDICION si se usa fill-popup-val: ahi el valor viene
;; del elemento que ya existe y debe verse aunque ya no este en la lista.)
(defun urb:fill-diam-popup (key lst val)
  (mp:fill-popup key lst
    (if (member (urb:safe-string val "") lst) (urb:index-of val lst) 0)))

(defun urb:diam-info-text (red lst / interp d)
  (setq interp "")
  (if (/= red "ACU")
    (foreach d lst
      (if (urb:diam-interpolado-p d)
        (setq interp (strcat interp (if (= interp "") "" ", ") d)))))
  (cond
    ((= red "ACU")
      (strcat (itoa (length lst)) " diametros de acueducto."))
    ((= interp "")
      (strcat (itoa (length lst))
        " diametros. Todos con ancho de zanja tomado de la tabla."))
    (T
      (strcat (itoa (length lst)) " diametros. Ancho INTERPOLADO en: "
        interp))))

;; Gestor de Configuracion -> Diametros de tuberia. El dialogo se reabre
;; tras cada operacion para refrescar la lista, igual que el de etapas.
(defun urb:diametros-manager-command
  (/ filename dcl-id done code red idx lst nuevo n)
  (urb:refresh-diametros-catalog)
  (setq done nil red "ALC" idx 0)
  (while (not done)
    (setq filename (urb:write-main-menu-dcl))
    (setq dcl-id (if filename (load_dialog filename) -1))
    (if (and dcl-id (> dcl-id 0) (new_dialog "urb_diametros" dcl-id))
      (progn
        (setq lst (urb:diam-list-of red))
        (if (>= idx (length lst)) (setq idx 0))
        (start_list "red")
        (mapcar 'add_list (list "Alcantarillado" "Acueducto"))
        (end_list)
        (set_tile "red" (if (= red "ACU") "1" "0"))
        (start_list "diam")
        (mapcar 'add_list lst)
        (end_list)
        (set_tile "diam" (itoa idx))
        (set_tile "info" (urb:diam-info-text red lst))
        (action_tile "red"
          "(setq red (if (= $value \"1\") \"ACU\" \"ALC\"))(done_dialog 6)")
        (action_tile "diam" "(setq idx (atoi $value))")
        (action_tile "agregar"
          "(setq nuevo (get_tile \"nuevo\"))(done_dialog 4)")
        (action_tile "quitar" "(done_dialog 3)")
        (action_tile "restaurar" "(done_dialog 5)")
        (action_tile "accept" "(done_dialog 1)")
        (setq code (start_dialog))
        (unload_dialog dcl-id)
        (cond
          ;; cambio de red: solo recargar con la otra lista
          ((= code 6) (setq idx 0))
          ((= code 3)
            (if (<= (length lst) 1)
              (alert "Debe quedar al menos un diametro.")
              (progn
                (urb:diam-set-list red
                  (urb:diam-sort
                    (vl-remove (nth idx lst) lst)))
                (urb:save-diametros-catalog red)
                (setq idx 0))))
          ((= code 4)
            (setq nuevo (vl-string-trim " " (urb:safe-string nuevo ""))
                  n (atoi nuevo))
            (cond
              ((= nuevo "") (alert "Escriba el diametro en pulgadas."))
              ((or (<= n 0) (/= nuevo (itoa n)))
                (alert "El diametro debe ser un numero entero de pulgadas."))
              ((member (itoa n) lst) (alert "Ese diametro ya esta en la lista."))
              (T
                (urb:diam-set-list red
                  (urb:diam-sort (cons (itoa n) lst)))
                (urb:save-diametros-catalog red)
                (setq idx (urb:index-of (itoa n) (urb:diam-list-of red)))
                ;; informar el ancho que le quedo: es el momento en que el
                ;; usuario acaba de crearlo y puede corregir si no cuadra
                (if (/= red "ACU")
                  (alert
                    (strcat "Diametro " (itoa n) "\" agregado."
                      "\n\nAncho de zanja para H<=1,5 m: "
                      (urb:diam-ancho-txt (itoa n))
                      (if (urb:diam-interpolado-p (itoa n))
                        (strcat "\n(interpolado: no esta en la tabla del"
                          "\nExcel de redes, se calculo entre sus vecinos)")
                        "\n(tomado de la tabla del Excel de redes)")))))))
          ((= code 5)
            (urb:diam-set-list red (urb:diam-default-list red))
            (urb:save-diametros-catalog red)
            (setq idx 0))
          (T (setq done T))))
      (progn
        (prompt "\nNo se pudo abrir el dialogo de diametros.")
        (setq done T))))
  (princ))
(setq *mp-material-acu-list* '("PVC" "WSP" "CCP" "PE" "ACERO" "HDPE" "OTRO"))
(setq *mp-material-red-list* '("PVC" "HDPE" "GRP" "CONCRETO" "ACERO" "OTRO"))
(setq *mp-acc-acu-list*
  '("TAPON" "TEE" "VALVULA_RED_MENOR" "VALVULA_VENTOSA" "VALVULA_PURGA" "REDUCCION"
    "CODO_90" "CODO_45" "CODO_22_5" "CODO_11_5" "VALVULA_REDUCTORA_PRESION"
    "VALVULA_CIERRE_PERMANENTE" "VALVULA_PIE_HIDRANTE" "HIDRANTE_TORRE" "NIPLE_PASAMUROS" "JUNTA_CONSTRUCCION" "OTRO"))
(setq *mp-cond-mt-list*
  '("3x70mm2 Al XLPE 15kV" "3x120mm2 Al XLPE 15kV" "3x150mm2 Cu XLPE 15kV"
    "3x185mm2 Al XLPE 15kV" "2(3x185mm2) Al XLPE 15kV" "3(3x185mm2) Al XLPE 15kV"
    "5(3x185mm2) Al XLPE 15kV" "3x240mm2 Al XLPE 15kV" "3x300mm2 Al XLPE 15kV"
    "2(3x300mm2) Al XLPE 15kV" "3x500mm2 Al XLPE 35kV" "3x2/0 ACSR" "3x4/0 ACSR" "OTRO"))
;; 5.7.24: superficie que hay que reponer encima de la zanja del tramo.
;; "ANDEN EN ADOQUIN" son los tramos que cruzan un anden YA construido:
;; se levanta el adoquin, se excava, se rellena y se vuelve a instalar.
(setq *mp-reposicion-list* '("NINGUNA" "ANDEN EN ADOQUIN" "PAVIMENTO"))
(setq *mp-ductos-list* '("1" "2" "3" "4" "5" "6" "9" "12"))
(setq *mp-diam-ducto-list* '("2\"" "3\"" "4\"" "6\""))
(setq *mp-mat-ducto-list* '("PVC" "IMC" "RMC" "EMT" "OTRO"))
(setq *mp-cond-bt-list* '("3x4+4 THW" "3x6+6 THW" "3x8+8 THW" "2x4 THW" "2x6 THW" "1x4 THW" "1x6 THW" "OTRO"))
(setq *mp-elem-elec-list* '("CAMARA_CS274" "CAMARA_CS275" "CAMARA_CS276" "CAMARA_CS280" "CAJA_BARRAJE_CS281" "POSTE_ELEC" "SUBESTACION_E" "CDMT_E" "LUMINARIA_AP" "TRANSFORMADOR_AP" "PUNTO_CONEXION_E"))
;; 5.7.14: "CAMBIO (retiro y reinstalacion)" marca una luminaria EXISTENTE
;; que solo se cambia: se exporta a "Retiro y reinstalacion de luminarias
;; nuevas" en su etapa/subetapa, no como suministro nuevo.
(setq *mp-lum-list* '("DECOLED 100 W" "RALED II" "AREALED II" "OTRA" "CAMBIO (retiro y reinstalacion)"))
(setq *mp-led-list* '("32 LED" "48 LED" "64 LED" "160 LED" "OTRO"))

(defun mp:layer (name color / doc layers lay)
  ;; Crea la capa si falta. 5.7.20 (reporte del usuario 2026-09-22: "si
  ;; apago el resto de redes humedas y secas y dibujo un tramo de pluvial
  ;; se me prenden todas las capas"): mp:ensure-layers corre en CADA
  ;; comando y esta funcion prendia, descongelaba y recoloreaba las seis
  ;; capas PPTO de redes. Una capa EXISTENTE ya no se toca (solo se
  ;; desbloquea para poder escribir); la visibilidad de la red que se
  ;; dibuja la asegura mp:layer-show, solo para esa capa.
  (vl-load-com)
  (setq doc (vla-get-ActiveDocument (vlax-get-acad-object)))
  (setq layers (vla-get-Layers doc))
  (if (tblsearch "LAYER" name)
    (setq lay (vla-Item layers name))
    (progn
      (setq lay (vla-Add layers name))
      (vla-put-Color lay color)))
  (vl-catch-all-apply 'vla-put-Lock (list lay :vlax-false))
  lay)

;; Prende y descongela UNA capa (la de la red que se esta dibujando), para
;; que el elemento nuevo no quede invisible; las demas redes no se tocan.
(defun mp:layer-show (name / lay)
  (if (and name (tblsearch "LAYER" name))
    (progn
      (setq lay (vla-Item (vla-get-Layers (vla-get-ActiveDocument (vlax-get-acad-object))) name))
      (vl-catch-all-apply 'vla-put-LayerOn (list lay :vlax-true))
      (if (/= (strcase name) (strcase (getvar "CLAYER")))
        (vl-catch-all-apply 'vla-put-Freeze (list lay :vlax-false))))))

(defun mp:store-cant-data (ename alist / serialized)
  (if (and ename alist)
    (progn
      (setq serialized (urb:serialize-lisp alist))
      (urb:set-xdata-strings ename "MP_CANT_DATA"
        (urb:string-chunks serialized 240)))))

(defun mp:read-cant-data (ename / chunks value)
  (setq chunks (urb:get-xdata-strings ename "MP_CANT_DATA"))
  (if chunks
    (progn
      (setq value (urb:read-lisp-safe (apply 'strcat chunks)))
      (if (listp value) value nil))))

;; v4.73.0 -- Escritura parcial segura. El motor permanece en este LSP.
;; mp:store-cant-data conserva su contrato de REEMPLAZO completo para
;; migraciones existentes. mp:setatts ahora combina antes de escribir.
(defun mp:cant-patch-valid-p (patch / valid pair n)
  (setq n (vl-catch-all-apply 'vl-list-length (list patch))
        valid (and (not (vl-catch-all-error-p n)) (numberp n)))
  (if valid
    (foreach pair patch
      (if (not (and (listp pair) (= (type (car pair)) 'STR)
                    (/= (vl-string-trim " " (car pair)) "")
                    (or (null (cdr pair))
                        (member (type (cdr pair)) '(STR INT REAL)))))
        (setq valid nil))))
  valid)

(defun mp:cant-merge (current patch / result pair tag)
  ;; Claves sin distincion de mayusculas; el ultimo valor prevalece.
  ;; Una cadena vacia es un borrado EXPLICITO del valor, no de la clave.
  (foreach pair (append current patch)
    (setq tag (strcase (car pair))
          result (mp:alist-set result tag (mp:safe-str (cdr pair)))))
  result)

(defun mp:cant-data-equal-p (left right / same pair)
  (setq same (= (length left) (length right)))
  (foreach pair left
    (if (not (equal pair (assoc (car pair) right))) (setq same nil)))
  same)

(defun mp:setatts (ename alist / obj a tag pair changed before old-data
                          merged snapshot result restore-result data-changed)
  ;; Conserva campos ocultos aun cuando el llamador envia solo un campo.
  ;; Ante error restaura atributos y XDATA de ESTA entidad y aborta la
  ;; operacion; nunca informa exito despues de una escritura incompleta.
  (if (not (mp:cant-patch-valid-p alist))
    (progn (prompt "\nActualizacion cancelada: lista de atributos invalida.") (exit)))
  (setq obj (vlax-ename->vla-object ename)
        old-data (mp:read-cant-data ename)
        before (entget ename '("*"))
        merged (mp:cant-merge (mp:att-alist ename) alist)
        alist (mp:cant-merge nil alist)
        changed 0
        data-changed (not (mp:cant-data-equal-p merged old-data)))
  (if (= (vla-get-HasAttributes obj) :vlax-true)
    (foreach a (vlax-invoke obj 'GetAttributes)
      (if (and (setq pair (assoc (strcase (vla-get-TagString a)) alist))
               (/= (vla-get-TextString a) (cdr pair)))
        (setq snapshot (cons (list a (vla-get-TextString a) (cdr pair)) snapshot)))))
  (setq result
    (vl-catch-all-apply
      '(lambda ()
         (foreach pair snapshot
           (vla-put-TextString (car pair) (nth 2 pair))
           (vla-Update (car pair))
           (setq changed (1+ changed)))
         (if data-changed
           (if (not (and (mp:store-cant-data ename merged)
                         (mp:cant-data-equal-p merged (mp:read-cant-data ename))))
             (progn (prompt "\nFallo al verificar los datos guardados.") (exit))))
         (if (> changed 0) (vla-Update obj))) nil))
  (if (vl-catch-all-error-p result)
    (progn
      (setq restore-result
        (vl-catch-all-apply
          '(lambda ()
             (foreach pair snapshot
               (vla-put-TextString (car pair) (cadr pair))
               (vla-Update (car pair)))
             (if (null (entmod before)) (exit))
             (entupd ename)) nil))
      (prompt (strcat "\nActualizacion cancelada: " (vl-catch-all-error-message result)))
      (if (vl-catch-all-error-p restore-result)
        (prompt "\nATENCION: no se pudo restaurar todo; deshaga la operacion y revise el objeto.")
        (prompt "\nSe restauraron los atributos y datos anteriores del objeto."))
      (exit)))
  ;; Auditoria separada y acotada: ultima escritura, no crecimiento indefinido.
  (if (or data-changed (> changed 0))
    (vl-catch-all-apply 'urb:set-xdata-strings
      (list ename "URB_DATA_AUDIT"
        (list "1" *urb-version* (rtos (getvar "CDATE") 2 6)
              (itoa (length alist))))))
  changed)

(defun mp:getval (tag vals def / a)
  (setq a (assoc tag vals))
  (if (and a (/= (cdr a) "")) (cdr a) def))

(defun mp:safe-str (x) (if (null x) "" (vl-princ-to-string x)))

;; 2026-08-12: tiles etapa/subetapa OCULTOS en los dialogos de CREACION
;; cuando las etapas estan deshabilitadas. Los DCL de creacion emiten
;; esta cadena (vacia si estan deshabilitadas); los de EDICION mantienen
;; los tiles (grises). *mp-dialog-edit-mode* lo fijan los write-dcl.
(setq *mp-dialog-edit-mode* nil)
(defun mp:dcl-etapa-str ()
  (if (urb:etapas-enabled-p)
    ": popup_list { label = \"Etapa\"; key = \"etapa\"; } : popup_list { label = \"Subetapa\"; key = \"subetapa\"; }"
    ""))

(defun mp:reset-dialog-capture ()
  (setq *mp-dialog-values* nil)
  (setq *mp-dialog-values-active* nil))

(defun mp:capture-dialog-values (/ keys key value result)
  ;; DCL deja de exponer get_tile despues de done_dialog. Capture antes de cerrar.
  (setq keys
    '("red" "blk" "tipo" "acc" "etapa" "subetapa" "tipo_ini" "tipo_fin"
      "pini" "pfin" "diam" "diamsal" "mat" "long" "pend"
      "ctni" "ctnf" "ccini" "ccfin" "ctn" "cclave" "cc_dig" "cc_sel"
      "serie" "circuito" "desde" "hasta" "cond" "ductos"
      "diamducto" "matducto" "libres" "prof" "id" "lote"
      "anchoz" "cama" "repos"
      "cd" "pf" "lum" "led" "altura" "brazo" "avance"
      ;; 5.6.0: "ctapa" FALTABA -- mp:dialog-punto-hidro la leia despues de
      ;; done_dialog, cuando get_tile ya no responde, y la cota de tapa
      ;; digitada se perdia (caia al terreno automatico). "tipo_plu" es el
      ;; selector Pozo/Sumidero/Cabezal de la ventana pluvial unificada.
      "ctapa" "tipo_plu"))
  (setq result nil)
  (foreach key keys
    (setq value (vl-catch-all-apply 'get_tile (list key)))
    (if (not (vl-catch-all-error-p value))
      (setq result (cons (cons key (if value value "")) result))))
  (setq *mp-dialog-values* result)
  (setq *mp-dialog-values-active* T)
  T)

(defun mp:gettile (key / pair v)
  (if (and *mp-dialog-values-active*
           (setq pair (assoc key *mp-dialog-values*)))
    (cdr pair)
    (progn
      ;; vl-catch-all: un tile oculto (etapa/subetapa deshabilitadas) no
      ;; queda en la captura y get_tile puede tronar tras done_dialog
      (setq v (vl-catch-all-apply 'get_tile (list key)))
      (if (or (null v) (vl-catch-all-error-p v)) "" v))))

(defun mp:update-red-diam ()
  (if (= (mp:gettile "red") "2")
    (progn (urb:fill-diam-popup "diam" *mp-diam-acu-list* "4") (mp:fill-popup "mat" *mp-material-acu-list* 0))
    (progn (urb:fill-diam-popup "diam" *mp-diam-alc-list* "15") (mp:fill-popup "mat" *mp-material-red-list* 0))))

(defun mp:csv-safe (s / out i ch) (if (not s) (setq s "")) (setq out "" i 1) (while (<= i (strlen s)) (setq ch (substr s i 1)) (if (= ch "\"") (setq out (strcat out "\"\"")) (setq out (strcat out ch))) (setq i (1+ i))) (strcat "\"" out "\""))
(defun mp:att-alist (ename / obj atts res a stored pair)
  (setq obj (vlax-ename->vla-object ename) res nil)
  (if (= (vla-get-HasAttributes obj) :vlax-true)
    (foreach a (vlax-invoke obj 'GetAttributes)
      (setq res
        (cons
          (cons (strcase (vla-get-TagString a)) (vla-get-TextString a))
          res))))
  (setq stored (mp:read-cant-data ename))
  (foreach pair stored
    (if (not (assoc (strcase (car pair)) res))
      (setq res (cons (cons (strcase (car pair)) (cdr pair)) res))))
  res)

(setq *mp-cant-counter* 0)

(defun mp:starts-with (s pref / n)
  (setq s (strcase (mp:safe-str s)) pref (strcase pref) n (strlen pref))
  (and (>= (strlen s) n) (= (substr s 1 n) pref)))

(defun mp:3d (p)
  (vlax-3d-point (list (float (car p)) (float (cadr p)) (if (caddr p) (float (caddr p)) 0.0))))

(defun mp:var-dbls (lst)
  (vlax-make-variant
    (vlax-safearray-fill
      (vlax-make-safearray vlax-vbDouble (cons 0 (1- (length lst))))
      (mapcar 'float lst))))

(defun mp:vla-add-att (blk tag prompt def pt h invisible lay col / att mode)
  ;; Modo 1 = invisible, 0 = normal. Son atributos editables con EATTEDIT.
  (setq mode (if invisible 1 0))
  (setq att (vla-AddAttribute blk (float h) mode prompt (mp:3d pt) tag (mp:safe-str def)))
  (vla-put-Layer att lay)
  (vla-put-Color att col)
  att)

(defun mp:center-visible-att (att pt height)
  ;; 10 = acAlignmentMiddleCenter.
  (vl-catch-all-apply 'vla-put-Height (list att (float height)))
  (vl-catch-all-apply 'vla-put-Alignment (list att 10))
  (vl-catch-all-apply 'vla-put-TextAlignmentPoint (list att (mp:3d pt)))
  att)

(defun mp:make-cant-tramo-block (blkname baseb dist vals / doc blks blk lay col w r th lab mid y pl ln c1 c2 cut a)
  ;; V9: crea la definicion de bloque con ActiveX, no con INSERT de DWG externo.
  ;; Esto evita el error: Can't find file "CANT_TRAMO_....dwg".
  (vl-load-com)
  (mp:ensure-layers)
  (setq doc (vla-get-ActiveDocument (vlax-get-acad-object)))
  (setq blks (vla-get-Blocks doc))
  (setq lay (mp:vis-layer baseb)
        col (mp:vis-color baseb)
        w   *mp-vis-width*
        a   (mp:layer-show (mp:vis-layer baseb))
        r   *mp-vis-radius*
        th  *mp-vis-tramo-text-height*)
  (if (< w 0.01) (setq w 0.01))
  ;; 4.74.0: una sola regla visual para redes humedas y secas.
  (if (< r 2.00) (setq r 2.00))
  (if (< th 0.10) (setq th 0.10))
  ;; 2026-09-08: una sola fuente de configuracion. Las claves MP_TRAMO_*
  ;; son canonicas; las URB_MP_* solo se leen como compatibilidad.
  (setq th (mp:cfg-tramo-text th))
  (setq w (mp:cfg-tramo-width w))
  (setq lab (mp:label-tramo baseb vals))
  (setq blk (vla-Add blks (mp:3d '(0 0 0)) blkname))

  ;; La geometria conserva la longitud centro a centro, pero la franja
  ;; visible termina en el borde de los circulos de inicio y fin.
  ;; 2026-08-28: en ACUEDUCTO la linea se RECORTA 2.0 en cada punta
  ;; aunque tenga bloques de nodo propios -- los simbolos de accesorio
  ;; son trazo abierto (tee, codo, valvula) y la tuberia pasandoles por
  ;; encima los volvia ilegibles (revision del usuario).
  (setq cut (min r (/ dist 4.0)))
  (setq pl
    (vla-AddLightWeightPolyline
      blk
      (mp:var-dbls
        (cond
          ;; ACU: linea CONTINUA de extremo a extremo, sin recorte --
          ;; en el plano original el simbolo del accesorio va SOBRE la
          ;; linea fina y se lee perfecto (3a revision del usuario:
          ;; los recortes se veian como tramos partidos)
          ((mp:tramo-own-node-blocks-p baseb)
            (list 0.0 0.0 dist 0.0))
          (T (list cut 0.0 (- dist cut) 0.0))))))
  (vla-put-Layer pl lay)
  (vla-put-Color pl col)
  (vla-put-ConstantWidth pl (float w))

  ;; En redes hidrosanitarias (y MT/BT-AP) los pozos/cajas/postes son
  ;; bloques puntuales independientes y compartibles. Dibujar ademas
  ;; circulos dentro de CADA tramo producia dos o tres anillos
  ;; superpuestos en una union.
  (if (not (mp:tramo-own-node-blocks-p baseb))
    (progn
      (setq c1 (vla-AddCircle blk (mp:3d '(0 0 0)) (float r)))
      (vla-put-Layer c1 lay)
      (vla-put-Color c1 col)
      (setq c2 (vla-AddCircle blk (mp:3d (list dist 0.0 0.0)) (float r)))
      (vla-put-Layer c2 lay)
      (vla-put-Color c2 col)))

  ;; Etiqueta y pendiente centradas respecto al punto medio del tramo.
  (setq mid (list (/ dist 2.0) (mp:tramo-label-offset th) 0.0))
  (mp:center-visible-att
    (mp:vla-add-att blk "ETIQUETA" "Etiqueta visible" lab mid th nil lay col)
    mid
    th)
  ;; 2026-08-28: pendiente visible SOLO en redes por gravedad -- en
  ;; acueducto (presion) el "-0.102%" era puro ruido visual
  (if (member baseb '("TRAMO_ARESIDUAL" "TRAMO_ALLUVIAS"))
    (progn
      (setq mid (list (/ dist 2.0) (- (mp:tramo-label-offset th)) 0.0))
      (mp:center-visible-att
        (mp:vla-add-att
          blk
          "PENDIENTE_VIS"
          "Pendiente visible"
          (mp:pendiente-label vals)
          mid
          th
          nil
          lay
          col)
        mid
        th)))
  ;; MT/BT-AP: longitud y tubos debajo; conductor/acometida arriba.
  (if (member baseb '("TRAMO_E_MT" "TRAMO_E_BT_AP"))
    (progn
      (setq mid (list (/ dist 2.0) (- (mp:tramo-label-offset th)) 0.0))
      (mp:center-visible-att
        (mp:vla-add-att blk "LONG_VIS" "Longitud visible"
          (mp:long-label vals) mid th nil lay col)
        mid
        th)))

  ;; Atributos invisibles de datos.
  (setq y (- (* th 1.25)))
  (foreach a (mp:base-atts-for baseb)
    (mp:vla-add-att blk (car a) (cadr a) (if (caddr a) (caddr a) "") (list 0 y 0.0) 0.10 T lay col)
    (setq y (- y 0.20)))
  blkname)

(defun mp:ins-block-scaled (bname p1 p2 vals)
  (mp:insert-cant-tramo bname p1 p2 vals))

;; Ahora reconoce los bloques CANT_TRAMO_* como bloques de cantidad.
(defun mp:is-mp-block (en / obj b)
  (if (and en (= (cdr (assoc 0 (entget en))) "INSERT"))
    (progn
      (setq obj (vlax-ename->vla-object en))
      (setq b (vla-get-EffectiveName obj))
      (mp:is-cant-blockname b))))

(defun mp:setatt-one (ename tag val / obj a vals)
  (setq vals (mp:att-alist ename))
  (setq obj (vlax-ename->vla-object ename))
  (if (= (vla-get-HasAttributes obj) :vlax-true)
    (foreach a (vlax-invoke obj 'GetAttributes)
      (if (= (strcase (vla-get-TagString a)) (strcase tag))
        (progn
          (vla-put-TextString a (mp:safe-str val))
          (vla-Update a)))))
  (vla-Update obj)
  (mp:store-cant-data ename (mp:alist-set vals (strcase tag) (mp:safe-str val))))

;; Actualizacion masiva de presentacion: no toca MP_CANT_DATA. Los valores
;; tecnicos ya se conservaron y esta ruta evita serializar XDATA 557 veces.
(defun mp:setatt-visible-only (ename tag val / obj a)
  (setq obj (vlax-ename->vla-object ename))
  (if (= (vla-get-HasAttributes obj) :vlax-true)
    (foreach a (vlax-invoke obj 'GetAttributes)
      (if (= (strcase (vla-get-TagString a)) (strcase tag))
        (progn (vla-put-TextString a (mp:safe-str val)) (vla-Update a)))))
  (vla-Update obj))


;; Unificado 4.1.0: una sola lista de etapas para todo el archivo.
(setq *mp-etapa-list* *urb-etapa-list*)
(setq *mp-csv-tags*
  '("BLOQUE" "HANDLE" "LAYER" "X" "Y" "ID" "CODIGO" "ETAPA" "SUBETAPA" "RED" "TIPO_RED"
    "POZO_INI" "POZO_FIN" "COTA_TN_INI" "COTA_TN_FIN" "COTA_CLAVE_INI" "COTA_CLAVE_FIN"
    "DIAMETRO" "DIAMETRO_SALIDA" "MATERIAL" "LONGITUD" "PENDIENTE" "SERIE" "CIRCUITO" "CIRCUITO_AP"
    "DESDE" "HASTA" "CONDUCTORES" "CONDUCTOR" "CALIBRE" "MATERIAL_COND" "DUCTOS" "DIAM_DUCTO"
    "MATERIAL_DUCTO" "LIBRES" "CIRCUITOS" "PROFUNDIDAD" "UBICACION" "TIPO_CAJA" "COTA_TAPA" "NIVELACION" "TIPO_LUMINARIA" "LUMINARIAS" "FUENTE_LED"
    "ALTURA_M" "BRAZO_M" "AVANCE_M" "TIPO_SE" "LOTE" "CD" "PF" "ENTRADAS" "SALIDAS" "CELDAS"
    "TIPO_ACCESORIO" "TIPO_EXTREMO_INI" "TIPO_EXTREMO_FIN"
    "HANDLE_EXTREMO_INI" "HANDLE_EXTREMO_FIN" "LONGITUD_2D" "LONGITUD_3D"
    "MODO_LONGITUD" "PENDIENTE_CALCULADA" "PROFUNDIDAD_INI"
    "PROFUNDIDAD_FIN" "PROFUNDIDAD_MEDIA" "ANCHO_ZANJA" "ESPESOR_CAMA"
    "ANCHO_REPOSICION" "EXCAVACION_M3" "CAMA_M3" "VOLUMEN_ELEMENTO_M3"
    "RELLENO_M3" "ARENA_M3" "BASE_GRANULAR_M3" "TRITURADO_M3" "RECEBO_M3" "ENTIBADO_LE3_M2"
    "ENTIBADO_GT3_M2" "SOBRANTE_M3" "REPOSICION_M2" "METODO_CANTIDADES"
    "SUPERFICIE_TN" "ESTADO_COTA_TN" "ORIGEN_CREACION"
    "CONTROL_ESTADO" "CONTROL_MENSAJES"))

;; Unificado 4.1.0: delega en urb:subetapas-for para mantener una sola
;; matriz de etapas/subetapas en todo el archivo.
(defun mp:subetapas-for (e)
  (urb:subetapas-for e))

(defun mp:update-subetapa ()
  ;; sin etapas habilitadas el tile no existe en los dialogos de creacion
  (if (or (urb:etapas-enabled-p) *mp-dialog-edit-mode*)
    (mp:fill-popup "subetapa" (mp:subetapas-for (mp:item *mp-etapa-list* "etapa")) 0)))

(defun mp:ensure-layers ()
  ;; Capas de presupuesto: SOLO el juego canonico PPTO- (2026-08-28,
  ;; pedido del usuario: sin capas repetidas por especialidad). Las
  ;; capas viejas (RED-ELECTRICA-*, EQUIPOS-ELECTRICOS, REDES-*,
  ;; ACCESORIOS-ACUEDUCTO, TEXTOS-CANTIDADES) YA NO se crean aqui:
  ;; recrearlas en cada comando era lo que revivia las capas purgadas
  ;; del master una y otra vez. PPTO-EQUIPOS-ELECTRICOS (eliminada del
  ;; master el 2026-08-26) tampoco se crea eager: solo aparece bajo
  ;; demanda si un bloque desconocido cae al fallback de mp:point-layer.
  (mp:layer "PPTO-ACUEDUCTO" 5)
  (mp:layer "PPTO-ALC-SANITARIO" 1)
  (mp:layer "PPTO-ALC-PLUVIAL" 3)
  (mp:layer "PPTO-ELECTRICA-MT" 6)
  (mp:layer "PPTO-ELECTRICA-BT-AP" 2)
  ;; 2026-09-01: PPTO-ACCESORIOS-ACUEDUCTO eliminada (los accesorios van
  ;; en PPTO-ACUEDUCTO, una capa por red) -- no recrearla
  (mp:layer "PPTO-TEXTOS-CANTIDADES" 7))

(defun mp:vis-layer (bname)
  (cond
    ((= bname "TRAMO_ACUEDUCTO") "PPTO-ACUEDUCTO")
    ((= bname "TRAMO_ALLUVIAS") "PPTO-ALC-PLUVIAL")
    ((= bname "TRAMO_ARESIDUAL") "PPTO-ALC-SANITARIO")
    ((= bname "TRAMO_E_MT") "PPTO-ELECTRICA-MT")
    ((= bname "TRAMO_E_BT_AP") "PPTO-ELECTRICA-BT-AP")
    (T "PPTO-TEXTOS-CANTIDADES")))

(defun mp:vis-color (bname)
  (cond
    ((= bname "TRAMO_ACUEDUCTO") 5) ; azul
    ((= bname "TRAMO_ALLUVIAS") 3) ; verde
    ((= bname "TRAMO_ARESIDUAL") 1) ; rojo
    ((= bname "TRAMO_E_MT") 6) ; magenta
    ((= bname "TRAMO_E_BT_AP") 2) ; amarillo
    (T 7)))

(defun mp:tramo-common-atts ()
  '(("HANDLE_EXTREMO_INI" "Handle extremo inicial" "")
    ("HANDLE_EXTREMO_FIN" "Handle extremo final" "")
    ("LONGITUD" "Longitud de presupuesto m" "")
    ("LONGITUD_2D" "Longitud en planta m" "")
    ("LONGITUD_3D" "Longitud espacial m" "")
    ("MODO_LONGITUD" "Modo de longitud" "PLANTA")
    ("ANCHO_ZANJA" "Ancho de zanja m" "")
    ("ESPESOR_CAMA" "Espesor de cama m" "0.10")
    ("ANCHO_REPOSICION" "Ancho de reposicion m" "")
    ;; 5.7.24: que se repone encima de la zanja -- NINGUNA, el anden en
    ;; adoquin que hay que levantar y volver a instalar, o el pavimento.
    ("TIPO_REPOSICION" "Reposicion de superficie" "NINGUNA")
    ("PROFUNDIDAD_INI" "Profundidad inicial m" "")
    ("PROFUNDIDAD_FIN" "Profundidad final m" "")
    ("PROFUNDIDAD_MEDIA" "Profundidad media m" "")
    ("PENDIENTE_CALCULADA" "Pendiente calculada %" "")
    ("EXCAVACION_M3" "Excavacion m3" "0")
    ("CAMA_M3" "Cama de apoyo m3" "0")
    ("VOLUMEN_ELEMENTO_M3" "Volumen desplazado m3" "0")
    ("RELLENO_M3" "Relleno m3" "0")
    ("TRITURADO_M3" "Cimentacion triturado m3" "")
    ("RECEBO_M3" "Relleno recebo m3" "")
    ("ENTIBADO_LE3_M2" "Entibado hasta 3m m2" "")
    ("ENTIBADO_GT3_M2" "Entibado mayor 3m m2" "")
    ("SOBRANTE_M3" "Retiro sobrante m3" "0")
    ("REPOSICION_M2" "Reposicion superficial m2" "0")
    ("MEMORIAS" "Memorias - use QMEMORIATRAMO" "OCULTAR")
    ("METODO_CANTIDADES" "Metodo de cantidades" "PRELIMINAR_GEOMETRICO")
    ("CONTROL_ESTADO" "Estado de control" "PENDIENTE")
    ("CONTROL_MENSAJES" "Mensajes de control" "")))

(defun mp:tramo-public-property-p (tag)
  (member (strcase (mp:safe-str tag))
    '("ETAPA" "SUBETAPA" "RED" "TIPO_RED" "SERIE" "CIRCUITO"
      "CIRCUITO_AP" "DESDE" "HASTA" "POZO_INI" "POZO_FIN"
      "DIAMETRO" "MATERIAL" "PENDIENTE" "CARCAMO" "CONDUCTOR"
      "DUCTOS" "DIAM_DUCTO" "MATERIAL_DUCTO" "LIBRES" "CIRCUITOS" "PROFUNDIDAD"
      "UBICACION" "COTA_TN_INI" "COTA_TN_FIN" "COTA_CLAVE_INI" "COTA_CLAVE_FIN"
      "LONGITUD" "ANCHO_ZANJA" "EXCAVACION_M3" "CAMA_M3"
      "VOLUMEN_ELEMENTO_M3" "RELLENO_M3" "TRITURADO_M3" "RECEBO_M3"
      "ARENA_M3" "BASE_GRANULAR_M3"
      "ENTIBADO_LE3_M2" "ENTIBADO_GT3_M2" "SOBRANTE_M3"
      "REPOSICION_M2" "MEMORIAS")))

(defun mp:base-atts-for (bname / specific all)
  (setq specific
    (cond
      ;; 2026-08-26 (pedido del usuario: propiedades "muy desordenadas"):
      ;; orden por grupos -- identificacion, ducteria, conductor,
      ;; profundidad/cotas. Se quito el duplicado CONDUCTORES (queda solo
      ;; CONDUCTOR; los lectores ya caian a uno u otro).
      ((= bname "TRAMO_E_MT")
        '(("SERIE" "Serie" "1") ("ETAPA" "Etapa" "")
          ("SUBETAPA" "Subetapa" "") ("TIPO_RED" "Tipo red" "MT")
          ("CIRCUITO" "Circuito" "") ("DESDE" "Desde" "")
          ("HASTA" "Hasta" "")
          ("TIPO_EXTREMO_INI" "Tipo extremo inicial" "")
          ("TIPO_EXTREMO_FIN" "Tipo extremo final" "")
          ("DUCTOS" "Numero de tubos" "6") ("DIAM_DUCTO" "Diametro de tubo (pulgadas)" "6")
          ("MATERIAL_DUCTO" "Material ducto" "PVC")
          ("LIBRES" "Ductos libres" "")
          ("UBICACION" "Ubicacion ducteria" "Anden o zona verde")
          ("CONDUCTOR" "Conductor" "3x185mm2 Al XLPE 15kV")
          ;; 2026-08-26: nro de circuitos de cable en el mismo banco
          ;; ("2(3x185)(C1)+3x185(C2)" = 3) -- multiplica las filas de
          ;; suministro y tendido de cable
          ("CIRCUITOS" "Circuitos de cable" "1")
          ("PROFUNDIDAD" "Profundidad m" "")
          ("ARENA_M3" "Relleno arena limpia proteccion ductos m3" "0")
          ("BASE_GRANULAR_M3" "Relleno base granular clase B m3" "0")
          ("COTA_TN_INI" "Cota terreno ini" "")
          ("COTA_TN_FIN" "Cota terreno fin" "")))
      ((= bname "TRAMO_E_BT_AP")
        '(("SERIE" "Serie" "6") ("ETAPA" "Etapa" "")
          ("SUBETAPA" "Subetapa" "") ("TIPO_RED" "Tipo red" "BT")
          ("CIRCUITO_AP" "Circuito AP/BT" "")
          ("DESDE" "Desde" "") ("HASTA" "Hasta" "")
          ("TIPO_EXTREMO_INI" "Tipo extremo inicial" "")
          ("TIPO_EXTREMO_FIN" "Tipo extremo final" "")
          ("DUCTOS" "Numero de tubos" "1") ("DIAM_DUCTO" "Diametro de tubo (pulgadas)" "3")
          ("MATERIAL_DUCTO" "Material ducto" "PVC")
          ("LIBRES" "Ductos libres" "")
          ("UBICACION" "Ubicacion ducteria" "Anden o zona verde")
          ("CONDUCTOR" "Conductor" "3x4+4 THW")
          ("PROFUNDIDAD" "Profundidad m" "")
          ("ARENA_M3" "Relleno arena limpia proteccion ductos m3" "0")
          ("BASE_GRANULAR_M3" "Relleno base granular clase B m3" "0")
          ("COTA_TN_INI" "Cota terreno ini" "")
          ("COTA_TN_FIN" "Cota terreno fin" "")))
      (T
        '(("ETAPA" "Etapa" "") ("SUBETAPA" "Subetapa" "")
          ("RED" "Red" "")
          ("POZO_INI" "Nodo/pozo inicial" "")
          ("POZO_FIN" "Nodo/pozo final" "")
          ("TIPO_EXTREMO_INI" "Tipo extremo inicial" "")
          ("TIPO_EXTREMO_FIN" "Tipo extremo final" "")
          ("DIAMETRO" "Diametro" "") ("MATERIAL" "Material" "PVC")
          ("PENDIENTE" "Pendiente %" "")
          ("CARCAMO" "Carcamo proteccion (SI/vacio)" "")
          ("COTA_TN_INI" "Cota terreno ini" "")
          ("COTA_TN_FIN" "Cota terreno fin" "")
          ("COTA_CLAVE_INI" "Cota clave ini" "")
          ("COTA_CLAVE_FIN" "Cota clave fin" "")))))
  (setq all
    (append
      specific
      '(("SUPERFICIE_TN" "Superficie de terreno" "SUP_TN")
        ("ESTADO_COTA_TN" "Estado cota terreno" "PENDIENTE"))
      (mp:tramo-common-atts)))
  ;; MT/BT-AP: fuera del panel los campos que el usuario marco como ruido
  ;; (2026-08-26) -- los DATOS no se pierden: mp:setatts guarda la copia
  ;; completa en XDATA y calculos/exportacion leen de ahi; el dialogo
  ;; EDITAR sigue mostrando conductor/ductos/etc. Tambien fuera
  ;; triturado/recebo/entibado (APUs de alcantarillado) y CAMA/RELLENO
  ;; genericos (en electricas el ppto los desglosa como ARENA y BASE
  ;; GRANULAR, ver ARENA_M3 / BASE_GRANULAR_M3).
  (if (member bname '("TRAMO_E_MT" "TRAMO_E_BT_AP"))
    (setq all
      (vl-remove-if
        '(lambda (item)
          (member (car item)
            '("TRITURADO_M3" "RECEBO_M3" "ENTIBADO_LE3_M2" "ENTIBADO_GT3_M2"
              "TIPO_RED" "CIRCUITO" "CIRCUITO_AP" "DESDE" "HASTA"
              "LIBRES" "PROFUNDIDAD" "UBICACION"
              "CAMA_M3" "RELLENO_M3" "MEMORIAS"
              ;; 2026-08-26: la excavacion electrica incluye disposicion
              ;; (sin sobrantes) y no se cobra reposicion
              "SOBRANTE_M3" "REPOSICION_M2")))
        all)))
  (vl-remove-if-not
    '(lambda (item) (mp:tramo-public-property-p (car item))) all))

(defun mp:write-dcl (/ fn f)
  (mp:reset-dialog-capture)
  (setq *mp-dialog-edit-mode* nil)
  (setq fn (urb:temp-file "maipore_listas_v13" ".dcl"))
  (if (and *mp-dcl-listas-ok* (findfile fn))
    fn
    (progn
  (setq f (open fn "w"))
  (write-line "maipore_tramo_red : dialog { label = \"Maipore - Tramo red PPTO\";" f)
  (write-line ": boxed_column { label = \"Datos de presupuesto\";" f)
  (write-line ": popup_list { label = \"Red\"; key = \"red\"; }" f)
  (write-line (mp:dcl-etapa-str) f)
  (write-line ": popup_list { label = \"Elemento inicial\"; key = \"tipo_ini\"; } : popup_list { label = \"Elemento final\"; key = \"tipo_fin\"; }" f)
  (write-line ": popup_list { label = \"Diametro\"; key = \"diam\"; }" f)
  (write-line ": popup_list { label = \"Material\"; key = \"mat\"; }" f)
  (write-line ": toggle { label = \"Carcamo de proteccion (cruce/recubrimiento bajo)\"; key = \"carcamo\"; }" f)
  (write-line ": popup_list { label = \"Reposicion de superficie\"; key = \"repotipo\"; } }" f)
  (write-line ": boxed_column { label = \"Cotas de diseno\";" f)
  (write-line ": radio_row { label = \"Cota clave\";" f)
  (write-line ": radio_button { label = \"Digitar\"; key = \"cc_dig\"; value = \"1\"; }" f)
  (write-line ": radio_button { label = \"Seleccionar en dibujo\"; key = \"cc_sel\"; } }" f)
  (write-line ": edit_box { label = \"Cota clave inicial\"; key = \"ccini\"; edit_width = 12; }" f)
  (write-line ": edit_box { label = \"Cota clave final\"; key = \"ccfin\"; edit_width = 12; } }" f)
  (write-line ": text { label = \"Las cotas TN se toman de SUP_TN al marcar los extremos.\"; } ok_cancel; }" f)

  ;; 2026-09-02 (pedido del usuario): tramo de ACUEDUCTO simplificado --
  ;; solo se dibuja de donde va a donde va: sin elemento inicial/final y
  ;; sin cotas de diseno; la zanja se calcula por reglamentacion (RAS
  ;; 0330: recubrimiento minimo 1.0 m a clave) igual que las electricas.
  (write-line "maipore_tramo_acu : dialog { label = \"Maipore - Tramo acueducto PPTO\";" f)
  (write-line ": boxed_column { label = \"Datos de presupuesto\";" f)
  (write-line (mp:dcl-etapa-str) f)
  (write-line ": popup_list { label = \"Diametro\"; key = \"diam\"; }" f)
  (write-line ": popup_list { label = \"Material\"; key = \"mat\"; }" f)
  (write-line ": toggle { label = \"Carcamo de proteccion (cruce/recubrimiento bajo)\"; key = \"carcamo\"; }" f)
  ;; 5.7.24 (pedido del usuario): tramos que van bajo anden ya construido --
  ;; hay que levantar el adoquin, excavar, rellenar y reinstalar.
  (write-line ": popup_list { label = \"Reposicion de superficie\"; key = \"repotipo\"; } }" f)
  (write-line ": text { label = \"Solo dibuje de donde va a donde va el tramo.\"; }" f)
  (write-line ": text { label = \"Zanja y excavacion automaticas (RAS 0330: recubrimiento 1.0 m).\"; } ok_cancel; }" f)

  (write-line "maipore_tramo_mt : dialog { label = \"Maipore - Tramo MT PPTO\"; : boxed_column {" f)
  (write-line (mp:dcl-etapa-str) f)
  (write-line ": popup_list { label = \"Elemento inicial\"; key = \"tipo_ini\"; } : popup_list { label = \"Elemento final\"; key = \"tipo_fin\"; }" f)
  (write-line ": popup_list { label = \"Conductor\"; key = \"cond\"; } : popup_list { label = \"Ductos\"; key = \"ductos\"; } : popup_list { label = \"Diametro ducto\"; key = \"diamducto\"; } : popup_list { label = \"Material ducto\"; key = \"matducto\"; }" f)
  (write-line ": popup_list { label = \"Ubicacion ducteria\"; key = \"ubic\"; } : text { label = \"Excavacion y relleno automaticos (norma CODENSA CS203).\"; } } ok_cancel; }" f)

  (write-line "maipore_tramo_bt : dialog { label = \"Maipore - Tramo BT/AP PPTO\"; : boxed_column {" f)
  (write-line (mp:dcl-etapa-str) f)
  (write-line ": popup_list { label = \"Elemento inicial\"; key = \"tipo_ini\"; } : popup_list { label = \"Elemento final\"; key = \"tipo_fin\"; }" f)
  (write-line ": popup_list { label = \"Conductor\"; key = \"cond\"; } : popup_list { label = \"Ductos\"; key = \"ductos\"; } : popup_list { label = \"Diametro ducto\"; key = \"diamducto\"; } : popup_list { label = \"Material ducto\"; key = \"matducto\"; }" f)
  (write-line ": popup_list { label = \"Ubicacion ducteria\"; key = \"ubic\"; } : text { label = \"Excavacion y relleno automaticos (norma CODENSA CS203).\"; } } ok_cancel; }" f)

  ;; Se mantienen los formularios de puntos/accesorios para compatibilidad con los comandos existentes.
  (write-line (strcat "maipore_elem_elec : dialog { label = \"Maipore - Elemento electrico\"; : boxed_column { : popup_list { label = \"Tipo elemento\"; key = \"blk\"; } : edit_box { label = \"ID / Codigo\"; key = \"id\"; edit_width = 26; } : edit_box { label = \"Serie\"; key = \"serie\"; edit_width = 8; } " (mp:dcl-etapa-str) " : edit_box { label = \"Lote / circuito\"; key = \"lote\"; edit_width = 26; } : edit_box { label = \"CD\"; key = \"cd\"; edit_width = 20; } : edit_box { label = \"PF\"; key = \"pf\"; edit_width = 20; } : popup_list { label = \"Luminaria\"; key = \"lum\"; } : popup_list { label = \"Fuente LED\"; key = \"led\"; } : edit_box { label = \"Altura montaje m\"; key = \"altura\"; edit_width = 12; } : edit_box { label = \"Brazo m\"; key = \"brazo\"; edit_width = 12; } : edit_box { label = \"Avance m\"; key = \"avance\"; edit_width = 12; } } ok_cancel; }") f)
  ;; 2026-09-02 (pedido del usuario): fuera Lote/Sector (no servia);
  ;; entra la NUMERACION del accesorio (asi vienen todos en el plano:
  ;; AC-461...) que ademas arma la etiqueta "numero + nombre".
  (write-line (strcat "maipore_acc_acu : dialog { label = \"Maipore - Accesorio acueducto\"; : boxed_column { : popup_list { label = \"Tipo accesorio\"; key = \"acc\"; } : edit_box { label = \"Numero (ej AC-461)\"; key = \"accid\"; edit_width = 18; } " (mp:dcl-etapa-str) " : popup_list { label = \"Diametro principal\"; key = \"diam\"; } : popup_list { label = \"Diametro salida\"; key = \"diamsal\"; } : popup_list { label = \"Material\"; key = \"mat\"; } } : text { label = \"Luego: punto de insercion y direccion (Enter = horizontal).\"; } ok_cancel; }") f)
  (close f)
  (setq *mp-dcl-listas-ok* T)
  fn)))

;; Dialogo simplificado del tramo de ACUEDUCTO (2026-09-02, pedido del
;; usuario): sin elemento inicial/final ni cotas de diseno -- devuelve el
;; mismo alist que mp:dialog-tramo-red para que el flujo aguas abajo no
;; cambie (extremos NINGUNO, cotas vacias -> profundidad normativa RAS).
(defun mp:dialog-tramo-acu (/ dcl ok res etapa)
  (setq dcl (load_dialog (mp:write-dcl)))
  (if (not (new_dialog "maipore_tramo_acu" dcl)) (exit))
  (mp:fill-popup "etapa" *mp-etapa-list* 0)
  (mp:update-subetapa)
  (urb:fill-diam-popup "diam" *mp-diam-acu-list* "4")
  (mp:fill-popup "mat" *mp-material-acu-list* 0)
  (mp:fill-popup "repotipo" *mp-reposicion-list* 0)
  (action_tile "etapa" "(mp:update-subetapa)")
  (action_tile "accept" "(mp:capture-dialog-values)(setq ok T)(done_dialog 1)")
  (action_tile "cancel" "(setq ok nil)(done_dialog 0)")
  (start_dialog)
  (if ok
    (progn
      (setq etapa (mp:item *mp-etapa-list* "etapa"))
      (setq res
        (list
          (cons "REDOPT" "Acueducto")
          (cons "ETAPA" etapa)
          (cons "SUBETAPA" (mp:item (mp:subetapas-for etapa) "subetapa"))
          (cons "POZO_INI" "") (cons "POZO_FIN" "")
          (cons "TIPO_EXTREMO_INI" "NINGUNO")
          (cons "TIPO_EXTREMO_FIN" "NINGUNO")
          (cons "DIAMETRO" (mp:item *mp-diam-acu-list* "diam"))
          (cons "MATERIAL" (mp:item *mp-material-acu-list* "mat"))
          (cons "CARCAMO" (if (= (mp:gettile "carcamo") "1") "SI" ""))
          (cons "TIPO_REPOSICION" (mp:item *mp-reposicion-list* "repotipo"))
          (cons "PENDIENTE" "")
          (cons "COTA_TN_INI" "") (cons "COTA_TN_FIN" "")
          (cons "COTA_CLAVE_INI" "") (cons "COTA_CLAVE_FIN" "")
          (cons "MODO_CLAVE" "Digitar")))))
  (unload_dialog dcl)
  res)

(defun mp:dialog-tramo-red (forced-red / dcl ok res etapa red-index modo-clave)
  (if (= forced-red "Acueducto")
    (mp:dialog-tramo-acu)
    (progn
  (setq dcl (load_dialog (mp:write-dcl)))
  (if (not (new_dialog "maipore_tramo_red" dcl)) (exit))
  (setq red-index
    (if forced-red (mp:idx forced-red *mp-red-list*) 0))
  (mp:fill-popup "red" *mp-red-list* red-index)
  (if forced-red (mode_tile "red" 1))
  (mp:fill-popup "etapa" *mp-etapa-list* 0)
  (mp:update-subetapa)
  (mp:update-red-diam)
  (mp:fill-popup "tipo_ini" *mp-extremo-hidro-list*
    (if (= forced-red "Acueducto") 3 1))
  (mp:fill-popup "tipo_fin" *mp-extremo-hidro-list*
    (if (= forced-red "Acueducto") 3 1))
  ;; Cota clave: "Digitar" (por defecto, radio_button value="1" en el DCL)
  ;; deja los 2 edit_box habilitados; "Seleccionar en dibujo" los apaga en
  ;; vivo -- se leen despues de cerrar el dialogo, con un clic sobre la
  ;; etiqueta real (mp:prompt-clave-from-label), asi que digitar algo ahi
  ;; no serviria de nada.
  (set_tile "cc_dig" "1")
  (action_tile "cc_dig" "(mode_tile \"ccini\" 0)(mode_tile \"ccfin\" 0)")
  (action_tile "cc_sel" "(mode_tile \"ccini\" 1)(mode_tile \"ccfin\" 1)")
  (action_tile "red" "(mp:update-red-diam)")
  (action_tile "etapa" "(mp:update-subetapa)")
  (action_tile "accept" "(mp:capture-dialog-values)(setq ok T)(done_dialog 1)")
  (action_tile "cancel" "(setq ok nil)(done_dialog 0)")
  (start_dialog)
  (if ok
    (progn
      (setq etapa (mp:item *mp-etapa-list* "etapa"))
      (setq modo-clave
        (if (= (mp:safe-str (mp:gettile "cc_sel")) "1") "Seleccionar" "Digitar"))
      (setq res
        (list
          (cons "REDOPT" (mp:item *mp-red-list* "red"))
          (cons "ETAPA" etapa)
          (cons "SUBETAPA" (mp:item (mp:subetapas-for etapa) "subetapa"))
          (cons "POZO_INI" "")
          (cons "POZO_FIN" "")
          (cons "TIPO_EXTREMO_INI" (mp:item *mp-extremo-hidro-list* "tipo_ini"))
          (cons "TIPO_EXTREMO_FIN" (mp:item *mp-extremo-hidro-list* "tipo_fin"))
          (cons "DIAMETRO" (if (= (mp:gettile "red") "2") (mp:item *mp-diam-acu-list* "diam") (mp:item *mp-diam-alc-list* "diam")))
          (cons "MATERIAL" (if (= (mp:gettile "red") "2") (mp:item *mp-material-acu-list* "mat") (mp:item *mp-material-red-list* "mat")))
          ;; Sin campo en el dialogo (se saco a pedido del usuario): siempre
          ;; en blanco, asi mp:derive-tramo-values la calcula sola de las
          ;; cotas clave (mismo camino que si el usuario la dejaba vacia).
          (cons "PENDIENTE" "")
          (cons "COTA_TN_INI" "")
          (cons "COTA_TN_FIN" "")
          (cons "COTA_CLAVE_INI" (mp:gettile "ccini"))
          (cons "COTA_CLAVE_FIN" (mp:gettile "ccfin"))
          (cons "CARCAMO" (if (= (mp:gettile "carcamo") "1") "SI" ""))
          (cons "TIPO_REPOSICION" (mp:item *mp-reposicion-list* "repotipo"))
          (cons "MODO_CLAVE" modo-clave)))))
  (unload_dialog dcl)
  res)))

(defun mp:dialog-tramo-mt (/ dcl ok res etapa)
  (setq dcl (load_dialog (mp:write-dcl)))
  (if (not (new_dialog "maipore_tramo_mt" dcl)) (exit))
  (mp:fill-popup "etapa" *mp-etapa-list* 0)
  (mp:update-subetapa)
  (mp:fill-popup "cond" *mp-cond-mt-list* 3)
  (mp:fill-popup "ductos" *mp-ductos-list* 5)
  (mp:fill-popup "diamducto" *mp-diam-ducto-list* 3)
  (mp:fill-popup "matducto" *mp-mat-ducto-list* 0)
  (mp:fill-popup "tipo_ini" *mp-extremo-elec-list* 3)
  (mp:fill-popup "tipo_fin" *mp-extremo-elec-list* 3)
  (mp:fill-popup "ubic" *mp-ubic-elec-list* 0)
  (action_tile "etapa" "(mp:update-subetapa)")
  (action_tile "accept" "(mp:capture-dialog-values)(setq ok T)(done_dialog 1)")
  (action_tile "cancel" "(setq ok nil)(done_dialog 0)")
  (start_dialog)
  (if ok
    (progn
      (setq etapa (mp:item *mp-etapa-list* "etapa"))
      (setq res
        (list (cons "ETAPA" etapa) (cons "SUBETAPA" (mp:item (mp:subetapas-for etapa) "subetapa"))
              (cons "DESDE" "") (cons "HASTA" "")
              (cons "CONDUCTORES" (mp:item *mp-cond-mt-list* "cond")) (cons "CONDUCTOR" (mp:item *mp-cond-mt-list* "cond"))
              (cons "DUCTOS" (mp:item *mp-ductos-list* "ductos")) (cons "DIAM_DUCTO" (mp:item *mp-diam-ducto-list* "diamducto"))
              (cons "MATERIAL_DUCTO" (mp:item *mp-mat-ducto-list* "matducto"))
              (cons "UBICACION" (mp:item *mp-ubic-elec-list* "ubic"))
              (cons "TIPO_EXTREMO_INI" (mp:item *mp-extremo-elec-list* "tipo_ini"))
              (cons "TIPO_EXTREMO_FIN" (mp:item *mp-extremo-elec-list* "tipo_fin"))))))
  (unload_dialog dcl)
  res)

(defun mp:dialog-tramo-bt (/ dcl ok res etapa)
  (setq dcl (load_dialog (mp:write-dcl)))
  (if (not (new_dialog "maipore_tramo_bt" dcl)) (exit))
  (mp:fill-popup "etapa" *mp-etapa-list* 0)
  (mp:update-subetapa)
  (mp:fill-popup "cond" *mp-cond-bt-list* 0)
  (mp:fill-popup "ductos" *mp-ductos-list* 0)
  (mp:fill-popup "diamducto" *mp-diam-ducto-list* 1)
  (mp:fill-popup "matducto" *mp-mat-ducto-list* 0)
  (mp:fill-popup "tipo_ini" *mp-extremo-elec-list* 3)
  (mp:fill-popup "tipo_fin" *mp-extremo-elec-list* 3)
  (mp:fill-popup "ubic" *mp-ubic-elec-list* 0)
  (action_tile "etapa" "(mp:update-subetapa)")
  (action_tile "accept" "(mp:capture-dialog-values)(setq ok T)(done_dialog 1)")
  (action_tile "cancel" "(setq ok nil)(done_dialog 0)")
  (start_dialog)
  (if ok
    (progn
      (setq etapa (mp:item *mp-etapa-list* "etapa"))
      (setq res
        (list (cons "ETAPA" etapa) (cons "SUBETAPA" (mp:item (mp:subetapas-for etapa) "subetapa"))
              (cons "DESDE" "") (cons "HASTA" "")
              (cons "CONDUCTOR" (mp:item *mp-cond-bt-list* "cond")) (cons "DUCTOS" (mp:item *mp-ductos-list* "ductos"))
              (cons "DIAM_DUCTO" (mp:item *mp-diam-ducto-list* "diamducto")) (cons "MATERIAL_DUCTO" (mp:item *mp-mat-ducto-list* "matducto"))
              (cons "UBICACION" (mp:item *mp-ubic-elec-list* "ubic"))
              (cons "TIPO_EXTREMO_INI" (mp:item *mp-extremo-elec-list* "tipo_ini")) (cons "TIPO_EXTREMO_FIN" (mp:item *mp-extremo-elec-list* "tipo_fin"))))))
  (unload_dialog dcl)
  res)


(defun mp:point-layer (base)
  (cond
    ((= base "POZO_SANITARIO") "PPTO-ALC-SANITARIO")
    ((= base "POZO_PLUVIAL") "PPTO-ALC-PLUVIAL")
    ((= base "SUMIDERO") "PPTO-ALC-PLUVIAL")
    ((= base "CABEZAL_PLUVIAL") "PPTO-ALC-PLUVIAL")
    ;; 2026-09-01 (pedido del usuario): accesorios en la MISMA capa del
    ;; tramo -- una capa por red, como MT/BT
    ((= base "ACCESORIO_ACUEDUCTO") "PPTO-ACUEDUCTO")
    ((= base "LUMINARIA_AP") "PPTO-ELECTRICA-BT-AP")
    ;; 2026-08-26 (pedido del usuario): UNA capa por red -- lo de MT con
    ;; los tramos MT y lo de alumbrado (cajas AP-274/275, postes,
    ;; transformador pedestal) con su red BT-AP.
    ((member base '("TRANSFORMADOR_AP" "CAMARA_CS274" "CAMARA_CS275" "POSTE_ELEC")) "PPTO-ELECTRICA-BT-AP")
    ((member base '("CAMARA_CS276" "CAMARA_CS280" "CAJA_BARRAJE_CS281" "SUBESTACION_E" "CDMT_E" "PUNTO_CONEXION_E")) "PPTO-ELECTRICA-MT")
    ;; fallback SOLO para bloques desconocidos: la capa se crea aqui
    ;; bajo demanda (mp:ensure-layers ya no la crea eager -- el usuario
    ;; la elimino del master el 2026-08-26 y no debe reaparecer sola)
    (T (mp:layer "PPTO-EQUIPOS-ELECTRICOS" 30) "PPTO-EQUIPOS-ELECTRICOS")))

(defun mp:point-color (base)
  (cond
    ((= base "POZO_SANITARIO") 1)
    ((= base "POZO_PLUVIAL") 3)
    ((= base "SUMIDERO") 3)
    ((= base "CABEZAL_PLUVIAL") 3)
    ((= base "ACCESORIO_ACUEDUCTO") 5)
    ((= base "LUMINARIA_AP") 2)
    ((member base '("CAMARA_CS274" "CAMARA_CS275" "POSTE_ELEC" "TRANSFORMADOR_AP")) 2)
    ((member base '("CAMARA_CS276" "CAMARA_CS280" "CAJA_BARRAJE_CS281" "SUBESTACION_E" "CDMT_E" "PUNTO_CONEXION_E")) 6)
    (T 7)))


(defun mp:base-atts-for-point (base)
  (cond
    ((member base '("POZO_SANITARIO" "POZO_PLUVIAL" "SUMIDERO" "CABEZAL_PLUVIAL"))
      '(("ETAPA" "Etapa" "") ("SUBETAPA" "Subetapa" "") ("RED" "Red" "")
        ("ID" "ID / Codigo" "") ("DIAMETRO" "Diametro" "")
        ("COTA_TN_INI" "Cota terreno" "") ("COTA_CLAVE_INI" "Cota clave" "")
        ("PROFUNDIDAD" "Profundidad" "")
        ("SUPERFICIE_TN" "Superficie de terreno" "SUP_TN")
        ("ESTADO_COTA_TN" "Estado cota terreno" "PENDIENTE")
        ("ORIGEN_CREACION" "Origen de creacion" "MANUAL")))
    ((member base '("CAMARA_CS274" "CAMARA_CS275" "CAMARA_CS276" "CAMARA_CS280" "CAJA_BARRAJE_CS281"))
      '(("ETAPA" "Etapa" "") ("SUBETAPA" "Subetapa" "") ("ID" "ID / Codigo" "")
        ("TIPO_CAJA" "Tipo caja" "") ("DUCTOS" "Ductos" "") ("LIBRES" "Libres" "")
        ("PROFUNDIDAD" "Profundidad" "") ("CD" "CD" "") ("PF" "PF" "")
        ("COTA_TN_INI" "Cota terreno" "")
        ;; chequeo de nivelacion (2026-08-26): tapa proyectada vs terreno
        ;; natural muestreado -- detecta cajas enterradas o colgadas
        ("COTA_TAPA" "Cota tapa (rasante)" "")
        ("NIVELACION" "Chequeo nivelacion" "PENDIENTE")
        ("SUPERFICIE_TN" "Superficie de terreno" "SUP_TN")
        ("ESTADO_COTA_TN" "Estado cota terreno" "PENDIENTE")
        ("ORIGEN_CREACION" "Origen de creacion" "MANUAL")))
    ;; 2026-09-07 (pedido del usuario: panel de propiedades LIMPIO):
    ;; fuera LOTE / SUPERFICIE_TN / ESTADO_COTA_TN / ORIGEN_CREACION --
    ;; la maquinaria que los leia usa defaults cuando faltan (verificado:
    ;; mp:getval con default en cada lector).
    ((= base "ACCESORIO_ACUEDUCTO")
      '(("ETAPA" "Etapa" "") ("SUBETAPA" "Subetapa" "") ("ID" "ID / Codigo" "")
        ("TIPO_ACCESORIO" "Tipo accesorio" "") ("DIAMETRO" "Diametro principal" "")
        ("DIAMETRO_SALIDA" "Diametro salida" "") ("MATERIAL" "Material" "")
        ("COTA_TN_INI" "Cota terreno" "")))
    ((= base "LUMINARIA_AP")
      '(("ETAPA" "Etapa" "") ("SUBETAPA" "Subetapa" "") ("CODIGO" "Codigo" "")
        ("TIPO_LUMINARIA" "Tipo luminaria" "") ("FUENTE_LED" "Fuente LED" "")
        ("ALTURA_M" "Altura montaje" "") ("BRAZO_M" "Brazo" "") ("AVANCE_M" "Avance" "") ("CIRCUITO_AP" "Circuito AP" "")
        ("COTA_TN_INI" "Cota terreno" "")
        ("SUPERFICIE_TN" "Superficie de terreno" "SUP_TN")
        ("ESTADO_COTA_TN" "Estado cota terreno" "PENDIENTE")
        ("ORIGEN_CREACION" "Origen de creacion" "MANUAL")))
    ;; 2026-08-26 (pedido del usuario): el poste como elemento con SUS
    ;; luminarias -- numero y referencia como atributos del poste
    ((= base "POSTE_ELEC")
      '(("ETAPA" "Etapa" "") ("SUBETAPA" "Subetapa" "") ("ID" "ID / Codigo" "")
        ("TIPO_RED" "Tipo red" "AP")
        ("LUMINARIAS" "Numero de luminarias" "")
        ("TIPO_LUMINARIA" "Referencia luminaria" "")
        ("ALTURA_M" "Altura montaje" "") ("CIRCUITO_AP" "Circuito AP" "")
        ("COTA_TN_INI" "Cota terreno" "")
        ("SUPERFICIE_TN" "Superficie de terreno" "SUP_TN")
        ("ESTADO_COTA_TN" "Estado cota terreno" "PENDIENTE")
        ("ORIGEN_CREACION" "Origen de creacion" "MANUAL")))
    (T
      '(("ETAPA" "Etapa" "") ("SUBETAPA" "Subetapa" "") ("ID" "ID / Codigo" "")
        ("TIPO_RED" "Tipo red" "") ("LOTE" "Lote/Sector" "") ("CD" "CD" "") ("PF" "PF" "")
        ("ENTRADAS" "Entradas" "") ("SALIDAS" "Salidas" "") ("CELDAS" "Celdas" "")
        ("COTA_TN_INI" "Cota terreno" "")
        ("SUPERFICIE_TN" "Superficie de terreno" "SUP_TN")
        ("ESTADO_COTA_TN" "Estado cota terreno" "PENDIENTE")
        ("ORIGEN_CREACION" "Origen de creacion" "MANUAL")))) )


;; Simbologia de cajas electricas replicada 1:1 del plano SERIE 1
;; (2026-08-25, pedido del usuario: "que se vean asi como en la foto" --
;; CS276 tapa doble, CS274 sencilla). Vertices copiados del bloque
;; "CAJA CS 276" del plano: marco 2.00x1.70 + marco interior + divisor
;; central doble; "CAJA CS 280": 2.00x2.00 + marco interior + circulo
;; r=0.75. CS274/CS275 (sencilla): mismo marco doble de linea SIN
;; divisor. La caja se dibuja centrada en el punto de insercion, igual
;; que el bloque del plano.
(defun mp:caja-plan-p (base)
  (member base '("CAMARA_CS274" "CAMARA_CS275" "CAMARA_CS276" "CAMARA_CS280")))

(defun mp:caja-plan-geom (blk base lay col / rects lins circs pl c r)
  (cond
    ((= base "CAMARA_CS280")
      (setq rects '((-1.0 -1.0 1.0 -1.0 1.0 1.0 -1.0 1.0)
                    (-0.98 -0.98 0.98 -0.98 0.98 0.98 -0.98 0.98))
            lins nil circs '((0.0 0.0 0.75))))
    ((= base "CAMARA_CS276")
      (setq rects '((-1.0 -0.85 1.0 -0.85 1.0 0.85 -1.0 0.85)
                    (-0.98 -0.83 0.98 -0.83 0.98 0.83 -0.98 0.83))
            lins '((-0.01 0.83 -0.01 -0.83) (0.01 0.83 0.01 -0.83))
            circs nil))
    (T ;; CS274 / CS275: caja sencilla, cuadrado 1.08 m como el bloque
       ;; "CAJA AP 274" del plano SERIE 6 (extents medidos +-0.54)
      (setq rects '((-0.54 -0.54 0.54 -0.54 0.54 0.54 -0.54 0.54)
                    (-0.52 -0.52 0.52 -0.52 0.52 0.52 -0.52 0.52))
            lins nil circs nil)))
  (foreach r rects
    (setq pl (vla-AddLightWeightPolyline blk (mp:var-dbls r)))
    (vla-put-Closed pl :vlax-true) (vla-put-Layer pl lay) (vla-put-Color pl col))
  (foreach r lins
    (setq pl (vla-AddLightWeightPolyline blk (mp:var-dbls r)))
    (vla-put-Layer pl lay) (vla-put-Color pl col))
  (foreach r circs
    (setq c (vla-AddCircle blk (mp:3d (list (car r) (cadr r) 0.0)) (float (caddr r))))
    (vla-put-Layer c lay) (vla-put-Color c col)))

;; ---------- simbologia de accesorios de acueducto replicada del plano
;; ACUEDUCTO.dwg (2026-08-28, pedido del usuario: "que se vea bien, que
;; accesorio es cada uno"). Geometria volcada de los bloques del plano
;; (A Tee, codo 45, A Hidrante, VALVULA PROY, etc.) con la escala de
;; insercion tipica YA multiplicada (tee x0.5, codo11 x0.2966,
;; codo22 x0.4083, codo45 x0.3625, codo90 x7.5, hidrante/v.pie x0.5812,
;; buje x0.5506, valvula x0.2, ventosa x0.75, union x0.8333, tapon x1).
;; Cada bloque del plano trae la figura en DOS tamanos superpuestos (el
;; efecto de doble trazo clasico) -- se replican ambos.

(defun mp:acc-tipo-token (tipo)
  (cond
    ((= tipo "TEE") "TEE")
    ((= tipo "CODO_11_5") "C11")
    ((= tipo "CODO_22_5") "C22")
    ((= tipo "CODO_45") "C45")
    ((= tipo "CODO_90") "C90")
    ((= tipo "HIDRANTE_TORRE") "HID")
    ((= tipo "VALVULA_PIE_HIDRANTE") "VPH")
    ((= tipo "VALVULA_RED_MENOR") "VAL")
    ((= tipo "VALVULA_VENTOSA") "VEN")
    ((= tipo "VALVULA_CIERRE_PERMANENTE") "VCP")
    ((= tipo "TAPON") "TAP")
    ((= tipo "REDUCCION") "RDC")
    (T "UNI")))

;; profundidad visual (|y| minimo) por tipo, para colgar la etiqueta
;; debajo del simbolo sin montarse en el
(defun mp:acc-sym-bottom (tk)
  (cond
    ((= tk "TEE") 0.70) ((= tk "C11") 0.50) ((= tk "C22") 0.60)
    ((= tk "C45") 0.75) ((= tk "C90") 1.50) ((= tk "HID") 4.55)
    ((= tk "VPH") 2.25) ((= tk "VAL") 2.20) ((= tk "VEN") 3.95)
    ((= tk "VCP") 1.10) ((= tk "TAP") 1.80) ((= tk "RDC") 0.60)
    (T 1.75)))

;; 5.6.1 (pedido del usuario: "que el espesor de los accesorios este igual
;; que los tramos"): todo el trazo del simbolo es polilinea con el MISMO
;; ancho configurado para los tramos (Ajustes > Apariencia). Antes eran
;; LINE/ARC/CIRCLE de ancho cero y junto a una tuberia gruesa el accesorio
;; casi no se veia.
(defun mp:acc-line-width ()
  (max 0.0 (mp:cfg-tramo-width *mp-vis-width*)))

(defun mp:acc-add-lines (blk lay col lst / l e w)
  (setq w (mp:acc-line-width))
  (foreach l lst
    (setq e (vla-AddLightWeightPolyline blk
      (mp:var-dbls (list (nth 0 l) (nth 1 l) (nth 2 l) (nth 3 l)))))
    (vla-put-ConstantWidth e w)
    (vla-put-Layer e lay) (vla-put-Color e col)))

(defun mp:acc-add-polys (blk lay col closed lst / p e)
  (foreach p lst
    (setq e (vla-AddLightWeightPolyline blk (mp:var-dbls p)))
    (if closed (vla-put-Closed e :vlax-true))
    (vla-put-ConstantWidth e (mp:acc-line-width))
    (vla-put-Layer e lay) (vla-put-Color e col)))

;; arco (cx cy r angulo-inicial angulo-final) como polilinea de un segmento
;; con bulge = tan(barrido/4), para poder darle ancho
(defun mp:acc-add-arcs (blk lay col lst / a e sweep p0 p1)
  (foreach a lst
    (setq sweep (- (nth 4 a) (nth 3 a)))
    (if (<= sweep 0.0) (setq sweep (+ sweep (* 2.0 pi))))
    (setq p0 (polar (list (nth 0 a) (nth 1 a)) (nth 3 a) (nth 2 a))
          p1 (polar (list (nth 0 a) (nth 1 a)) (nth 4 a) (nth 2 a)))
    (setq e (vla-AddLightWeightPolyline blk
      (mp:var-dbls (list (car p0) (cadr p0) (car p1) (cadr p1)))))
    (vla-SetBulge e 0 (/ (sin (/ sweep 4.0)) (cos (/ sweep 4.0))))
    (vla-put-ConstantWidth e (mp:acc-line-width))
    (vla-put-Layer e lay) (vla-put-Color e col)))

;; circulo de contorno con ancho: polilinea cerrada de dos medias vueltas
(defun mp:acc-add-circle (blk lay col cx cy r / e)
  (setq e (vla-AddLightWeightPolyline blk
    (mp:var-dbls (list (- cx r) cy (+ cx r) cy))))
  (vla-put-Closed e :vlax-true)
  (vla-SetBulge e 0 1.0) (vla-SetBulge e 1 1.0)
  (vla-put-ConstantWidth e (mp:acc-line-width))
  (vla-put-Layer e lay) (vla-put-Color e col)
  e)

;; circulo RELLENO (tapa del hidrante): polilinea de 2 arcos con ancho
;; constante = radio (truco donut)
(defun mp:acc-add-disk (blk lay col cx cy r / e)
  (setq e (vla-AddLightWeightPolyline blk
    (mp:var-dbls (list (- cx (/ r 2.0)) cy (+ cx (/ r 2.0)) cy))))
  (vla-put-Closed e :vlax-true)
  (vla-SetBulge e 0 1.0) (vla-SetBulge e 1 1.0)
  (vla-put-ConstantWidth e r)
  (vla-put-Layer e lay) (vla-put-Color e col))

(defun mp:acc-plan-geom (blk tipo lay col)
  (mp:acc-plan-geom-tk blk (mp:acc-tipo-token (mp:safe-str tipo)) lay col))

;; 5.6.1: por TOKEN (TEE, C45, VAL...), que es el sufijo del nombre del
;; bloque MP_PUNTO_ACC_ACU_<token>: permite redibujar una definicion ya
;; existente en el DWG sin conocer el tipo largo del accesorio.
(defun mp:acc-plan-geom-tk (blk tk lay col / c)
  (cond
    ((= tk "TEE")
      (mp:acc-add-lines blk lay col
        '((0.247 0.724 -0.247 0.724) (-0.724 -0.25 -0.724 0.25)
          (0.724 -0.25 0.724 0.25) (0.617 1.811 -0.617 1.811)
          (-1.811 -0.625 -1.811 0.625) (1.811 -0.625 1.811 0.625)
          (-0.724 0.0 0.724 0.0) (0.0 0.724 0.0 0.0)
          (1.811 0.0 -1.811 0.0) (0.0 1.811 0.0 0.0))))
    ((= tk "C11")
      (mp:acc-add-lines blk lay col
        '((0.0 0.0 0.361 0.0) (0.0 0.0 -0.354 0.070)
          (0.361 -0.148 0.361 0.148) (-0.383 -0.075 -0.325 0.216)
          (0.0 0.0 1.187 -0.008) (0.0 0.0 -1.164 0.231)
          (1.187 -0.434 1.187 0.476) (-1.255 -0.229 -1.062 0.743))))
    ((= tk "C22")
      (mp:acc-add-lines blk lay col
        '((0.0 0.0 0.497 0.0) (0.0 0.0 -0.459 0.190)
          (0.497 -0.204 0.497 0.204) (-0.537 0.002 -0.381 0.379)
          (0.0 0.0 1.242 0.0) (0.0 0.0 -1.148 0.475)
          (1.242 -0.510 1.242 0.510) (-1.343 0.004 -0.952 0.947))))
    ((= tk "C45")
      (mp:acc-add-lines blk lay col
        '((0.0 0.0 2.167 0.0) (0.0 0.0 -1.449 1.449)
          (-1.931 0.967 -0.942 1.956) (0.441 -0.181 0.441 0.181)
          (-0.440 0.184 -0.184 0.440) (0.0 0.0 0.441 0.0)
          (0.0 0.0 -0.312 0.312) (2.167 -0.705 2.167 0.681))))
    ((= tk "C90")
      (mp:acc-add-lines blk lay col
        '((0.0 0.0 0.0 -1.373) (0.0 0.0 1.223 0.0)
          (-0.591 -1.373 0.591 -1.373) (1.223 0.591 1.223 -0.591)
          (-0.169 -0.489 0.169 -0.489) (0.489 0.169 0.489 -0.169))))
    ((= tk "HID")
      (mp:acc-add-lines blk lay col
        '((0.0 -1.418 0.0 -4.481) (0.0 1.744 0.0 -3.197)))
      (mp:acc-add-disk blk lay col 0.0 -1.069 0.349)
      (mp:acc-add-circle blk lay col 0.0 2.615 0.872))
    ((= tk "VPH")
      (mp:acc-add-polys blk lay col T
        '((-0.174 2.18 0.174 1.308 -0.174 1.308 0.174 2.18)
          (-0.872 2.18 0.872 -2.18 -0.872 -2.18 0.872 2.18)))
      (mp:acc-add-lines blk lay col '((0.0 2.47 0.0 2.18))))
    ((= tk "VAL")
      (mp:acc-add-polys blk lay col T
        '((0.0 0.0 -0.632 -1.582 0.635 -1.582)
          (0.0 0.0 -0.632 1.577 0.635 1.577)
          (0.0 0.0 -0.303 -0.748 0.297 -0.748)
          (0.0 0.0 -0.303 0.752 0.297 0.752)))
      (mp:acc-add-lines blk lay col
        '((0.635 -2.149 -0.632 -2.149) (0.635 2.144 -0.632 2.144)
          (0.297 1.132 -0.303 1.132) (0.297 -1.137 -0.303 -1.137))))
    ((= tk "VEN")
      (mp:acc-add-arcs blk lay col
        '((1.516 -3.050 0.827 0.4623 3.6039)
          (1.516 -3.050 0.977 0.4623 1.9524)
          (1.516 -3.050 0.977 2.1061 3.6039)))
      (mp:acc-add-lines blk lay col
        '((0.067 0.033 1.152 -2.143) (2.256 -2.681 2.390 -2.614)
          (-0.067 -0.033 1.017 -2.210) (-0.067 -0.033 0.067 0.033)
          (0.641 -3.486 0.776 -3.419))))
    ((= tk "VCP")
      (mp:acc-add-polys blk lay col T
        '((0.0 0.0 -0.30 -0.75 0.30 -0.75)
          (0.0 0.0 -0.30 0.75 0.30 0.75)))
      (mp:acc-add-circle blk lay col 0.0 0.0 1.004)
      (mp:acc-add-lines blk lay col '((1.004 0.0 2.30 0.0))))
    ((= tk "TAP")
      (mp:acc-add-polys blk lay col nil
        '((1.0 -1.0 0.0 -1.0 0.0 1.0 1.0 1.0)
          (1.499 -1.716 0.0 -1.716 0.0 1.689 1.499 1.689))))
    ((= tk "RDC")
      (mp:acc-add-polys blk lay col T
        '((0.826 0.033 0.0 -0.242 0.0 0.309)
          (1.377 0.033 0.0 -0.517 0.0 0.584))))
    (T ;; UNION / OTRO: simbolo abierto, sin marco rectangular que oculte
      ;; accesorios coincidentes. La geometria sigue siendo lineal y no
      ;; introduce hatch/wipeout ni una entidad que tape el cruce.
      (mp:acc-add-lines blk lay col
        '((-1.667 0.18 1.667 0.18) (-1.667 -0.18 1.667 -0.18)
          (-0.20 -0.60 -0.20 0.60) (0.20 -0.60 0.20 0.60))))))

;; nombre de bloque POR TIPO para accesorios (cada tipo con su simbolo);
;; los demas puntos siguen con mp:point-block-name
(defun mp:acc-block-name (vals)
  (strcat "MP_PUNTO_ACC_ACU_"
    (mp:acc-tipo-token (mp:getval "TIPO_ACCESORIO" vals ""))))

(defun mp:make-cant-punto-block (blkname base vals / doc blks blk lay col th r lab pl c y att pos a)
  (vl-load-com)
  (mp:ensure-layers)
  (setq doc (vla-get-ActiveDocument (vlax-get-acad-object)))
  (setq blks (vla-get-Blocks doc))
  (setq lay (mp:point-layer base) col (mp:point-color base) th *mp-vis-text-height* r *mp-vis-radius*)
  (mp:layer-show lay)
  (if (< r 2.00) (setq r 2.00))
  (if (< th 0.50) (setq th 0.50))
  ;; 2026-08-28 (pedido del usuario): postes de alumbrado mas pequenos
  ;; -- circulo 0.7 en vez de 2.0 (el poste real es puntual, no una
  ;; camara) y etiqueta proporcional
  (if (= base "POSTE_ELEC") (setq r 0.70 th (min th 0.50)))
  ;; 2026-09-02 (pedido del usuario: "pozos y sumideros en tamano real,
  ;; estan sobredimensionados"): pozo = camara real D=1.20 m (r 0.60),
  ;; sumidero = caja ~0.70 (r 0.35); etiqueta proporcional 0.60 FUERA
  ;; del circulo (adentro ya no cabe).
  (if (member base '("POZO_SANITARIO" "POZO_PLUVIAL"))
    (setq r 0.60 th (min th 0.60)))
  (if (= base "SUMIDERO")
    (setq r 0.35 th (min th 0.60)))
  (setq lab (mp:label-point base vals))
  (setq blk (vla-Add blks (mp:3d '(0 0 0)) blkname))
  (cond
    ((mp:caja-plan-p base)
      (mp:caja-plan-geom blk base lay col))
    ((= base "ACCESORIO_ACUEDUCTO")
      (mp:acc-plan-geom blk (mp:getval "TIPO_ACCESORIO" vals "") lay col))
    ((= base "CABEZAL_PLUVIAL")
      ;; cabezal de descole replicado del bloque CABEZAL del plano
      ;; PLUVIAL.dwg (aletas trapezoidales, escala tipica 1.3 horneada)
      (mp:acc-add-lines blk lay col
        '((2.041 1.931 1.742 2.108) (1.457 0.0 2.039 1.929)
          (-0.747 0.427 -1.457 0.0) (-0.773 0.427 0.772 0.427)
          (-2.042 1.931 -1.743 2.108) (-2.042 1.931 -0.891 0.0)
          (-1.458 0.0 -2.040 1.929) (-1.743 2.108 -0.747 0.427)
          (2.041 1.931 0.890 0.0) (0.746 0.427 1.457 0.0)
          (1.742 2.108 0.746 0.427) (-1.457 0.0 1.457 0.0))))
    ((member base '("CAJA_BARRAJE_CS281" "SUBESTACION_E" "CDMT_E"))
      (setq pl (vla-AddLightWeightPolyline blk (mp:var-dbls (list (- r) (- r) r (- r) r r (- r) r))))
      (vla-put-Closed pl :vlax-true) (vla-put-Layer pl lay) (vla-put-Color pl col) (vla-put-ConstantWidth pl (float (/ r 3.0))))
    ((= base "SUMIDERO")
      (setq pl (vla-AddLightWeightPolyline blk (mp:var-dbls (list (- r) 0.0 0.0 r r 0.0 0.0 (- r)))))
      (vla-put-Closed pl :vlax-true) (vla-put-Layer pl lay) (vla-put-Color pl col) (vla-put-ConstantWidth pl (float (/ r 3.0))))
    (T
      (setq c (vla-AddCircle blk (mp:3d '(0 0 0)) (float r)))
      (vla-put-Layer c lay) (vla-put-Color c col)))
  (cond
    ((member base '("POZO_SANITARIO" "POZO_PLUVIAL"))
      ;; etiqueta ARRIBA del circulo (con r=0.60 real ya no cabe adentro)
      (setq pos (list 0.0 (+ r (* th 0.75)) 0.0))
      (setq att (mp:vla-add-att blk "ETIQUETA" "Numero de pozo" lab pos th nil lay col))
      (mp:center-visible-att att pos th))
    ((mp:caja-plan-p base)
      ;; caja estilo plano: ARRIBA centrado el numero de norma ("276") y
      ;; ABAJO centrado el consecutivo ("1", "2"...). Texto acotado a 0.60
      ;; y pegado al simbolo para que no se monte sobre otros textos
      ;; (revision del usuario 2026-08-26).
      (setq th (min th 0.60))
      (setq r (cond ((= base "CAMARA_CS280") 1.0)
                    ((member base '("CAMARA_CS274" "CAMARA_CS275")) 0.54)
                    (T 0.85)))
      (setq pos (list 0.0 (+ r (* th 0.75)) 0.0))
      (setq att (mp:vla-add-att blk "ETIQUETA" "Tipo de caja" lab pos th nil lay col))
      (mp:center-visible-att att pos th)
      (setq pos (list 0.0 (- (+ r (* th 0.85))) 0.0))
      (setq att (mp:vla-add-att blk "NUM_VIS" "Numero de caja"
        (mp:caja-num-label vals) pos th nil lay col))
      (mp:center-visible-att att pos th))
    ((= base "CABEZAL_PLUVIAL")
      (setq th 0.60)
      (setq pos (list 0.0 (- (* th 1.2)) 0.0))
      (setq att (mp:vla-add-att blk "ETIQUETA" "Etiqueta visible" lab pos th nil lay col))
      (mp:center-visible-att att pos th))
    ((= base "ACCESORIO_ACUEDUCTO")
      ;; etiqueta UNICA centrada debajo del simbolo (2026-08-28, pedido
      ;; del usuario: el texto era el desorden principal) -- corta
      ;; ("C45 D8"), 0.45 de alto, colgada segun la profundidad visual
      ;; del simbolo para no montarse en el
      (setq th 0.45)
      (setq pos (list 0.0
        (- (+ (mp:acc-sym-bottom
                (mp:acc-tipo-token (mp:getval "TIPO_ACCESORIO" vals "")))
              (* th 0.85))) 0.0))
      (setq att (mp:vla-add-att blk "ETIQUETA" "Etiqueta visible" lab pos th nil lay col))
      (mp:center-visible-att att pos th))
    (T
      (mp:vla-add-att blk "ETIQUETA" "Etiqueta visible" lab
        (list (* r 1.5) (* r 1.5) 0.0) th nil lay col)))
  (mp:vla-add-att blk "BLOQUE_BASE" "Bloque base" base (list 0 (- (* th 1.25)) 0.0) 0.10 T lay col)
  (setq y (- (* th 1.5)))
  (foreach a (mp:base-atts-for-point base)
    (mp:vla-add-att blk (car a) (cadr a) (if (caddr a) (caddr a) "") (list 0 y 0.0) 0.10 T lay col)
    (setq y (- y 0.20)))
  blkname)


(defun mp:write-dcl-puntos (/ fn f)
  (mp:reset-dialog-capture)
  (setq *mp-dialog-edit-mode* nil)
  ;; v13 (5.6.0): nueva ventana maipore_punto_pluvial; subir el nombre
  ;; obliga a reescribir el .dcl temporal que dejo una sesion anterior
  (setq fn (urb:temp-file "maipore_puntos_v14" ".dcl"))
  (if (and *mp-dcl-puntos-ok* (findfile fn))
    fn
    (progn
  (setq f (open fn "w"))
  ;; 2026-09-07 (pedido del usuario: ventana de pozos/sumideros con solo
  ;; lo necesario): fuera "Cota terreno" (automatica de SUP_TN) y fuera
  ;; "Profundidad" (se DERIVA sola: cota tapa - cota clave; la tapa
  ;; manda, como en el cuadro de pozos del plano). La cota de tapa es
  ;; opcional: vacia = terreno natural en el punto.
  (write-line "maipore_punto_hidro : dialog { label = \"Maipore - Punto hidrosanitario\"; : boxed_column {" f)
  (write-line (mp:dcl-etapa-str) f)
  (write-line ": edit_box { label = \"ID / Codigo\"; key = \"id\"; edit_width = 24; } : popup_list { label = \"Diametro\"; key = \"diam\"; }" f)
  (write-line ": edit_box { label = \"Cota tapa (vacia = terreno SUP_TN)\"; key = \"ctapa\"; edit_width = 12; } : edit_box { label = \"Cota clave / fondo\"; key = \"cclave\"; edit_width = 12; }" f)
  (write-line ": text { label = \"La profundidad se calcula sola: tapa - clave.\"; } } ok_cancel; }" f)
  ;; 5.6.0 (pedido del usuario): un solo boton pluvial para pozo, sumidero
  ;; y cabezal de descarga -- todos por unidad; el tipo se elige aqui.
  ;; 5.6.1 (pedido del usuario): "Accesorios" pluviales -- solo Tipo,
  ;; Etapa/Subetapa e ID. Sin diametro ni cotas: el terreno sale solo de
  ;; SUP_TN y el cabezal toma el diametro del tramo que llega a el.
  (write-line "maipore_punto_pluvial : dialog { label = \"Maipore - Accesorios pluviales\"; : boxed_column {" f)
  (write-line ": popup_list { label = \"Tipo\"; key = \"tipo_plu\"; edit_width = 24; }" f)
  (write-line (mp:dcl-etapa-str) f)
  (write-line ": edit_box { label = \"ID / Codigo\"; key = \"id\"; edit_width = 24; } } ok_cancel; }" f)
  (write-line "maipore_caja_elec : dialog { label = \"Maipore - Caja / camara electrica\"; : boxed_column {" f)
  (write-line ": popup_list { label = \"Tipo\"; key = \"tipo\"; }" f)
  (write-line (mp:dcl-etapa-str) f)
  (write-line ": edit_box { label = \"ID / Codigo\"; key = \"id\"; edit_width = 24; } : edit_box { label = \"Ductos\"; key = \"ductos\"; edit_width = 12; } : edit_box { label = \"Libres\"; key = \"libres\"; edit_width = 12; }" f)
  (write-line ": edit_box { label = \"Profundidad\"; key = \"prof\"; edit_width = 12; } : edit_box { label = \"CD\"; key = \"cd\"; edit_width = 14; } : edit_box { label = \"PF\"; key = \"pf\"; edit_width = 14; } } ok_cancel; }" f)
  (close f)
  (setq *mp-dcl-puntos-ok* T)
  fn)))

(defun mp:dialog-punto-hidro (red tipo / dcl ok etapa res tapa clave prof)
  (setq dcl (load_dialog (mp:write-dcl-puntos)))
  (if (not (new_dialog "maipore_punto_hidro" dcl)) (exit))
  (mp:fill-popup "etapa" *mp-etapa-list* 0)
  (mp:update-subetapa)
  (if (= red "Acueducto") (urb:fill-diam-popup "diam" *mp-diam-acu-list* "8") (urb:fill-diam-popup "diam" *mp-diam-alc-list* "8"))
  (action_tile "etapa" "(mp:update-subetapa)")
  (action_tile "accept" "(mp:capture-dialog-values)(setq ok T)(done_dialog 1)")
  (action_tile "cancel" "(setq ok nil)(done_dialog 0)")
  (start_dialog)
  (if ok
    (progn
      (setq etapa (mp:item *mp-etapa-list* "etapa"))
      ;; 2026-09-07: profundidad DERIVADA (tapa - clave); la tapa
      ;; digitada manda sobre el terreno automatico (COTA_TN_INI) --
      ;; si queda vacia, mp:auto-terrain-values pone el TN del punto y
      ;; la profundidad se deriva alla si hay clave.
      (setq tapa (mp:numeric-real (mp:gettile "ctapa")))
      (setq clave (mp:numeric-real (mp:gettile "cclave")))
      (setq prof
        (if (and tapa clave) (rtos (- tapa clave) 2 3) ""))
      (setq res
        (list (cons "ETAPA" etapa) (cons "SUBETAPA" (mp:item (mp:subetapas-for etapa) "subetapa"))
              (cons "RED" red) (cons "ID" (mp:gettile "id")) (cons "DIAMETRO" (if (= red "Acueducto") (mp:item *mp-diam-acu-list* "diam") (mp:item *mp-diam-alc-list* "diam")))
              (cons "COTA_TN_INI" (if tapa (rtos tapa 2 3) ""))
              (cons "COTA_CLAVE_INI" (mp:gettile "cclave"))
              (cons "PROFUNDIDAD" prof)))))
  (unload_dialog dcl)
  res)

;; ---------- Numeracion automatica de elementos electricos ----------
;; MT no traia numeracion (alumbrado si): al abrir el dialogo se propone
;; el siguiente ID libre por tipo, escaneando los bloques ya insertados
;; en el dibujo. El usuario puede sobreescribirlo si quiere otro codigo.
(defun mp:elec-id-prefix (base)
  (cond
    ((= base "CAMARA_CS274") "C274-")
    ((= base "CAMARA_CS275") "C275-")
    ((= base "CAMARA_CS276") "C276-")
    ((= base "CAMARA_CS280") "C280-")
    ((= base "CAJA_BARRAJE_CS281") "B281-")
    ((= base "POSTE_ELEC") "P-")
    ((= base "SUBESTACION_E") "SE-")
    ((= base "CDMT_E") "CD-")
    ((= base "TRANSFORMADOR_AP") "TR-")
    ((= base "PUNTO_CONEXION_E") "PC-")
    ((= base "LUMINARIA_AP") "AP-")
    (T "")))

(defun mp:next-elec-id (base / pref ss i en atts id num mx)
  (setq pref (mp:elec-id-prefix base) mx 0)
  (if (= pref "")
    ""
    (progn
      (setq ss (ssget "_X" '((0 . "INSERT") (2 . "MP_PUNTO_*"))))
      (if ss
        (progn
          (setq i 0)
          (repeat (sslength ss)
            (setq en (ssname ss i))
            (if (= (mp:point-reference-base en) base)
              (progn
                (setq atts (mp:att-alist en))
                (setq id
                  (strcase
                    (urb:safe-string
                      (cdr (assoc
                        (if (= base "LUMINARIA_AP") "CODIGO" "ID") atts))
                      "")))
                (if (= (strcase pref) (substr id 1 (strlen pref)))
                  (progn
                    (setq num (atoi (substr id (1+ (strlen pref)))))
                    (if (> num mx) (setq mx num))))))
            (setq i (1+ i)))))
      (strcat pref
        (if (< (1+ mx) 10)
          (strcat "0" (itoa (1+ mx)))
          (itoa (1+ mx)))))))

(defun mp:dialog-caja-electrica (/ dcl ok etapa res tipo)
  (setq dcl (load_dialog (mp:write-dcl-puntos)))
  (if (not (new_dialog "maipore_caja_elec" dcl)) (exit))
  (mp:fill-popup "tipo" *mp-caja-elec-list* 2)
  (set_tile "id" (mp:next-elec-id (nth 2 *mp-caja-elec-list*)))
  (action_tile "tipo"
    "(set_tile \"id\" (mp:next-elec-id (nth (atoi (get_tile \"tipo\")) *mp-caja-elec-list*)))")
  (mp:fill-popup "etapa" *mp-etapa-list* 0)
  (mp:update-subetapa)
  (action_tile "etapa" "(mp:update-subetapa)")
  (action_tile "accept" "(mp:capture-dialog-values)(setq ok T)(done_dialog 1)")
  (action_tile "cancel" "(setq ok nil)(done_dialog 0)")
  (start_dialog)
  (if ok
    (progn
      (setq etapa (mp:item *mp-etapa-list* "etapa"))
      (setq tipo (mp:item *mp-caja-elec-list* "tipo"))
      (setq res
        (list (cons "BLK" tipo) (cons "ETAPA" etapa) (cons "SUBETAPA" (mp:item (mp:subetapas-for etapa) "subetapa"))
              (cons "ID" (mp:gettile "id")) (cons "TIPO_CAJA" (mp:tipo-caja-de tipo))
              (cons "DUCTOS" (mp:gettile "ductos")) (cons "LIBRES" (mp:gettile "libres")) (cons "PROFUNDIDAD" (mp:gettile "prof"))
              (cons "CD" (mp:gettile "cd")) (cons "PF" (mp:gettile "pf"))))))
  (unload_dialog dcl)
  res)

(defun mp:insert-tramo-forced (redopt / vals base modo-clave modo-relleno v *error*)
  (defun *error* (message)
    (setq *mp-tramo-road-ref* nil)
    (if (and message (not (member message '("Function cancelled" "quit / exit abort"))))
      (prompt (strcat "\nERROR EN TRAMO: " message)))
    (princ))
  (mp:ensure-layers)
  (setq vals (mp:dialog-tramo-red redopt))
  (if vals
    (progn
      (setq vals (mp:alist-set vals "REDOPT" redopt)
            vals (mp:alist-set vals "RED" redopt)
            base
              (cond
                ((= redopt "Acueducto") "TRAMO_ACUEDUCTO")
                ((= redopt "Alluvias") "TRAMO_ALLUVIAS")
                (T "TRAMO_ARESIDUAL")))
      ;; Cota clave: la eleccion Digitar/Seleccionar ya se hizo DENTRO del
      ;; dialogo (radio_row "cc_dig"/"cc_sel"); si eligio Seleccionar los
      ;; edit_box de cota clave quedaron deshabilitados alla, asi que aqui
      ;; solo falta el clic sobre la etiqueta real.
      (setq modo-clave (mp:getval "MODO_CLAVE" vals "Digitar"))
      (if (urb:string-equal-p modo-clave "Seleccionar")
        (progn
          (setq v (mp:prompt-clave-from-label "\nSeleccione la etiqueta de cota clave INICIAL: "))
          (if v (setq vals (mp:alist-set vals "COTA_CLAVE_INI" (rtos v 2 4))))
          (setq v (mp:prompt-clave-from-label "\nSeleccione la etiqueta de cota clave FINAL: "))
          (if v (setq vals (mp:alist-set vals "COTA_CLAVE_FIN" (rtos v 2 4))))))
      ;; Referencia de relleno: modo configurado UNA VEZ desde URBANISMO ->
      ;; Configuracion -> Referencia de relleno de tramos de red (no se
      ;; pregunta aqui). Solo tiene efecto en tramos a gravedad
      ;; (mp:tramo-depth-profile, unico lugar que la usa, solo corre para
      ;; sanitario/pluvial) -- no aplica a acueducto.
      (if (mp:gravity-tramo-p base)
        (progn
          (setq modo-relleno
            (urb:safe-string (urb:config-read "MP_TRAMO_RELLENO_MODO") "Terreno"))
          (setq *mp-tramo-road-ref*
            (if (urb:string-equal-p modo-relleno "Subrasante")
              (mp:select-road-subrasante-reference)
              nil))))
      (mp:create-linked-tramo
        base vals
        (strcat "\nExtremo inicial tramo " redopt ": ")
        (strcat "\nExtremo final tramo " redopt ": "))
      (setq *mp-tramo-road-ref* nil))))


(defun mp:idx (val lst / i found)
  (setq i 0 found nil val (mp:safe-str val))
  (while (and lst (not found))
    (if (= (strcase val) (strcase (car lst)))
      (setq found i)
      (progn (setq i (1+ i)) (setq lst (cdr lst)))))
  (if found found 0))


(defun mp:attval (atts tag def / v)
  (setq v (cdr (assoc (strcase tag) atts)))
  (if (and v (/= v "")) v def))

(defun mp:subetapa-fill-current (/ etapa cur)
  (setq etapa (mp:item *mp-etapa-list* "etapa"))
  (setq cur (if (and (boundp '*mp-edit-subetapa-current*) *mp-edit-subetapa-current*) *mp-edit-subetapa-current* ""))
  (mp:fill-popup-val "subetapa" (mp:subetapas-for etapa) cur))

(defun mp:edit-layer-for-base (base)
  (cond
    ((= base "TRAMO_ACUEDUCTO") "PPTO-ACUEDUCTO")
    ((= base "TRAMO_ARESIDUAL") "PPTO-ALC-SANITARIO")
    ((= base "TRAMO_ALLUVIAS") "PPTO-ALC-PLUVIAL")
    ((= base "TRAMO_E_MT") "PPTO-ELECTRICA-MT")
    ((= base "TRAMO_E_BT_AP") "PPTO-ELECTRICA-BT-AP")
    ((= base "POZO_SANITARIO") "PPTO-ALC-SANITARIO")
    ((= base "POZO_PLUVIAL") "PPTO-ALC-PLUVIAL")
    ((= base "SUMIDERO") "PPTO-ALC-PLUVIAL")
    ((= base "ACCESORIO_ACUEDUCTO") "PPTO-ACUEDUCTO")
    ((= base "LUMINARIA_AP") "PPTO-ELECTRICA-BT-AP")
    ;; misma unificacion de capa MT que mp:point-layer (2026-08-26)
    (T (mp:point-layer base))))

(defun mp:write-dcl-editar (/ fn f)
  (mp:reset-dialog-capture)
  ;; dialogos de EDICION: los tiles etapa/subetapa se conservan siempre
  ;; (grises si las etapas estan deshabilitadas)
  (setq *mp-dialog-edit-mode* T)
  (setq fn (urb:temp-file "maipore_editar_v14" ".dcl"))
  (if (and *mp-dcl-editar-ok* (findfile fn))
    fn
    (progn
  (setq f (open fn "w"))

  (write-line "edit_tramo_red : dialog { label = \"Editar PPTO - Tramo hidrosanitario\";" f)
  (write-line ": boxed_column { label = \"Clasificacion\"; : text { key = \"redtxt\"; } : popup_list { label = \"Etapa\"; key = \"etapa\"; } : popup_list { label = \"Subetapa\"; key = \"subetapa\"; } }" f)
  (write-line ": boxed_column { label = \"Datos\"; : edit_box { label = \"Nodo/pozo inicial\"; key = \"pini\"; edit_width = 22; } : edit_box { label = \"Nodo/pozo final\"; key = \"pfin\"; edit_width = 22; } : popup_list { label = \"Elemento inicial\"; key = \"tipo_ini\"; } : popup_list { label = \"Elemento final\"; key = \"tipo_fin\"; } : popup_list { label = \"Diametro\"; key = \"diam\"; } : popup_list { label = \"Material\"; key = \"mat\"; } : edit_box { label = \"Longitud\"; key = \"long\"; edit_width = 12; } : edit_box { label = \"Pendiente %\"; key = \"pend\"; edit_width = 12; } }" f)
  (write-line ": boxed_column { label = \"Cotas\"; : edit_box { label = \"Cota terreno inicial (automatica SUP_TN)\"; key = \"ctni\"; edit_width = 12; } : edit_box { label = \"Cota terreno final (automatica SUP_TN)\"; key = \"ctnf\"; edit_width = 12; } : edit_box { label = \"Cota clave inicial\"; key = \"ccini\"; edit_width = 12; } : edit_box { label = \"Cota clave final\"; key = \"ccfin\"; edit_width = 12; } }" f)
  (write-line ": boxed_column { label = \"Cantidades de construccion\"; : edit_box { label = \"Ancho de zanja m\"; key = \"anchoz\"; edit_width = 12; } : edit_box { label = \"Espesor de cama m\"; key = \"cama\"; edit_width = 12; } : edit_box { label = \"Ancho de reposicion m\"; key = \"repos\"; edit_width = 12; } : popup_list { label = \"Reposicion de superficie\"; key = \"repotipo\"; } } ok_cancel; }" f)

  (write-line "edit_tramo_mt : dialog { label = \"Editar PPTO - Media tension\"; : boxed_column { : popup_list { label = \"Etapa\"; key = \"etapa\"; } : popup_list { label = \"Subetapa\"; key = \"subetapa\"; } : edit_box { label = \"Desde\"; key = \"desde\"; edit_width = 26; } : edit_box { label = \"Hasta\"; key = \"hasta\"; edit_width = 26; } : popup_list { label = \"Elemento inicial\"; key = \"tipo_ini\"; } : popup_list { label = \"Elemento final\"; key = \"tipo_fin\"; } : popup_list { label = \"Conductor\"; key = \"cond\"; } : popup_list { label = \"Ductos\"; key = \"ductos\"; } : popup_list { label = \"Diametro ducto\"; key = \"diamducto\"; } : popup_list { label = \"Material ducto\"; key = \"matducto\"; } : popup_list { label = \"Ubicacion ducteria\"; key = \"ubic\"; } : edit_box { label = \"Ancho de zanja\"; key = \"anchoz\"; edit_width = 12; } : edit_box { label = \"Espesor de cama\"; key = \"cama\"; edit_width = 12; } : edit_box { label = \"Ancho de reposicion\"; key = \"repos\"; edit_width = 12; } : edit_box { label = \"Longitud\"; key = \"long\"; edit_width = 12; } : text { label = \"Profundidad y excavacion: automaticas por norma CODENSA.\"; } } ok_cancel; }" f)

  (write-line "edit_tramo_bt : dialog { label = \"Editar PPTO - Alumbrado / BT\"; : boxed_column { : popup_list { label = \"Etapa\"; key = \"etapa\"; } : popup_list { label = \"Subetapa\"; key = \"subetapa\"; } : edit_box { label = \"Desde\"; key = \"desde\"; edit_width = 26; } : edit_box { label = \"Hasta\"; key = \"hasta\"; edit_width = 26; } : popup_list { label = \"Elemento inicial\"; key = \"tipo_ini\"; } : popup_list { label = \"Elemento final\"; key = \"tipo_fin\"; } : popup_list { label = \"Conductor\"; key = \"cond\"; } : popup_list { label = \"Ductos\"; key = \"ductos\"; } : popup_list { label = \"Diametro ducto\"; key = \"diamducto\"; } : popup_list { label = \"Material ducto\"; key = \"matducto\"; } : popup_list { label = \"Ubicacion ducteria\"; key = \"ubic\"; } : edit_box { label = \"Ancho de zanja\"; key = \"anchoz\"; edit_width = 12; } : edit_box { label = \"Espesor de cama\"; key = \"cama\"; edit_width = 12; } : edit_box { label = \"Ancho de reposicion\"; key = \"repos\"; edit_width = 12; } : edit_box { label = \"Longitud\"; key = \"long\"; edit_width = 12; } : text { label = \"Profundidad y excavacion: automaticas por norma CODENSA.\"; } } ok_cancel; }" f)

  (write-line "edit_punto_hidro : dialog { label = \"Editar PPTO - Pozo / Sumidero\"; : boxed_column { : text { key = \"redtxt\"; } : popup_list { label = \"Etapa\"; key = \"etapa\"; } : popup_list { label = \"Subetapa\"; key = \"subetapa\"; } : edit_box { label = \"ID / Codigo\"; key = \"id\"; edit_width = 24; } : popup_list { label = \"Diametro\"; key = \"diam\"; } : edit_box { label = \"Cota terreno (automatica SUP_TN)\"; key = \"ctn\"; edit_width = 12; } : edit_box { label = \"Cota clave\"; key = \"cclave\"; edit_width = 12; } : edit_box { label = \"Profundidad\"; key = \"prof\"; edit_width = 12; } } ok_cancel; }" f)

  (write-line "edit_acc_acu : dialog { label = \"Editar PPTO - Accesorio acueducto\"; : boxed_column { : popup_list { label = \"Tipo accesorio\"; key = \"acc\"; } : popup_list { label = \"Etapa\"; key = \"etapa\"; } : popup_list { label = \"Subetapa\"; key = \"subetapa\"; } : edit_box { label = \"ID / Codigo\"; key = \"id\"; edit_width = 24; } : popup_list { label = \"Diametro principal\"; key = \"diam\"; } : popup_list { label = \"Diametro salida\"; key = \"diamsal\"; } : popup_list { label = \"Material\"; key = \"mat\"; } : edit_box { label = \"Lote/Sector\"; key = \"lote\"; edit_width = 26; } } ok_cancel; }" f)

  (write-line "edit_caja_elec : dialog { label = \"Editar PPTO - Caja / camara electrica\"; : boxed_column { : popup_list { label = \"Tipo\"; key = \"tipo\"; } : popup_list { label = \"Etapa\"; key = \"etapa\"; } : popup_list { label = \"Subetapa\"; key = \"subetapa\"; } : edit_box { label = \"ID / Codigo\"; key = \"id\"; edit_width = 24; } : edit_box { label = \"Ductos\"; key = \"ductos\"; edit_width = 12; } : edit_box { label = \"Libres\"; key = \"libres\"; edit_width = 12; } : edit_box { label = \"Profundidad\"; key = \"prof\"; edit_width = 12; } : edit_box { label = \"CD\"; key = \"cd\"; edit_width = 14; } : edit_box { label = \"PF\"; key = \"pf\"; edit_width = 14; } } ok_cancel; }" f)

  (write-line "edit_luminaria : dialog { label = \"Editar PPTO - Luminaria / equipo\"; : boxed_column { : popup_list { label = \"Etapa\"; key = \"etapa\"; } : popup_list { label = \"Subetapa\"; key = \"subetapa\"; } : edit_box { label = \"Codigo / ID\"; key = \"id\"; edit_width = 24; } : popup_list { label = \"Tipo luminaria\"; key = \"lum\"; } : popup_list { label = \"Fuente LED\"; key = \"led\"; } : edit_box { label = \"Altura montaje m\"; key = \"altura\"; edit_width = 12; } : edit_box { label = \"Brazo m\"; key = \"brazo\"; edit_width = 12; } : edit_box { label = \"Avance m\"; key = \"avance\"; edit_width = 12; } : edit_box { label = \"Circuito AP\"; key = \"circuito\"; edit_width = 24; } } ok_cancel; }" f)
  (close f)
  (setq *mp-dcl-editar-ok* T)
  fn)))

(defun mp:edit-dialog-tramo-red (atts base / dcl ok etapa red diamlist matlist res)
  (setq dcl (load_dialog (mp:write-dcl-editar)))
  (if (not (new_dialog "edit_tramo_red" dcl)) (exit))
  (setq red (cond ((= base "TRAMO_ACUEDUCTO") "Acueducto") ((= base "TRAMO_ALLUVIAS") "Alluvias") (T "Aresidual")))
  (set_tile "redtxt" (strcat "Red fija del bloque: " red))
  (setq *mp-edit-subetapa-current* (mp:attval atts "SUBETAPA" ""))
  (mp:fill-popup-val "etapa" *mp-etapa-list* (mp:attval atts "ETAPA" "1"))
  (mp:subetapa-fill-current)
  (setq diamlist (if (= base "TRAMO_ACUEDUCTO") *mp-diam-acu-list* *mp-diam-alc-list*))
  (setq matlist (if (= base "TRAMO_ACUEDUCTO") *mp-material-acu-list* *mp-material-red-list*))
  (mp:fill-popup-val "diam" diamlist (mp:attval atts "DIAMETRO" ""))
  (mp:fill-popup-val "mat" matlist (mp:attval atts "MATERIAL" "PVC"))
  (set_tile "pini" (mp:attval atts "POZO_INI" "")) (set_tile "pfin" (mp:attval atts "POZO_FIN" ""))
  (mp:fill-popup-val "tipo_ini" *mp-extremo-hidro-list* (mp:attval atts "TIPO_EXTREMO_INI" "POZO"))
  (mp:fill-popup-val "tipo_fin" *mp-extremo-hidro-list* (mp:attval atts "TIPO_EXTREMO_FIN" "POZO"))
  (set_tile "long" (mp:attval atts "LONGITUD" "")) (mode_tile "long" 1) (set_tile "pend" (mp:attval atts "PENDIENTE" ""))
  (set_tile "ctni" (mp:attval atts "COTA_TN_INI" "")) (set_tile "ctnf" (mp:attval atts "COTA_TN_FIN" ""))
  (set_tile "ccini" (mp:attval atts "COTA_CLAVE_INI" "")) (set_tile "ccfin" (mp:attval atts "COTA_CLAVE_FIN" ""))
  (set_tile "anchoz" (mp:attval atts "ANCHO_ZANJA" ""))
  (set_tile "cama" (mp:attval atts "ESPESOR_CAMA" "0.10"))
  (set_tile "repos" (mp:attval atts "ANCHO_REPOSICION" ""))
  (mp:fill-popup-val "repotipo" *mp-reposicion-list* (mp:attval atts "TIPO_REPOSICION" "NINGUNA"))
  (action_tile "etapa" "(setq *mp-edit-subetapa-current* \"\")(mp:subetapa-fill-current)")
  (action_tile "accept" "(mp:capture-dialog-values)(setq ok T)(done_dialog 1)")
  (action_tile "cancel" "(setq ok nil)(done_dialog 0)")
  (start_dialog)
  (if ok
    (progn
      (setq etapa (mp:item *mp-etapa-list* "etapa"))
      (setq res (list (cons "RED" red) (cons "ETAPA" etapa) (cons "SUBETAPA" (mp:item (mp:subetapas-for etapa) "subetapa"))
                      (cons "TIPO_REPOSICION" (mp:item *mp-reposicion-list* "repotipo"))
                      (cons "POZO_INI" (mp:gettile "pini")) (cons "POZO_FIN" (mp:gettile "pfin"))
                      (cons "TIPO_EXTREMO_INI" (mp:item *mp-extremo-hidro-list* "tipo_ini"))
                      (cons "TIPO_EXTREMO_FIN" (mp:item *mp-extremo-hidro-list* "tipo_fin"))
                      (cons "DIAMETRO" (mp:item diamlist "diam")) (cons "MATERIAL" (mp:item matlist "mat"))
                      (cons "PENDIENTE" (mp:gettile "pend"))
                      (cons "COTA_TN_INI" (mp:gettile "ctni"))
                      (cons "COTA_TN_FIN" (mp:gettile "ctnf")) (cons "COTA_CLAVE_INI" (mp:gettile "ccini"))
                      (cons "COTA_CLAVE_FIN" (mp:gettile "ccfin"))
                      (cons "ANCHO_ZANJA" (mp:gettile "anchoz"))
                      (cons "ESPESOR_CAMA" (mp:gettile "cama"))
                      (cons "ANCHO_REPOSICION" (mp:gettile "repos"))))))
  (unload_dialog dcl)
  res)

(defun mp:edit-dialog-tramo-mt (atts / dcl ok etapa res)
  (setq dcl (load_dialog (mp:write-dcl-editar)))
  (if (not (new_dialog "edit_tramo_mt" dcl)) (exit))
  (setq *mp-edit-subetapa-current* (mp:attval atts "SUBETAPA" ""))
  (mp:fill-popup-val "etapa" *mp-etapa-list* (mp:attval atts "ETAPA" "1")) (mp:subetapa-fill-current)
  (set_tile "desde" (mp:attval atts "DESDE" "")) (set_tile "hasta" (mp:attval atts "HASTA" ""))
  (mp:fill-popup-val "tipo_ini" *mp-extremo-elec-list* (mp:attval atts "TIPO_EXTREMO_INI" "CAMARA_CS276"))
  (mp:fill-popup-val "tipo_fin" *mp-extremo-elec-list* (mp:attval atts "TIPO_EXTREMO_FIN" "CAMARA_CS276"))
  (mp:fill-popup-val "cond" *mp-cond-mt-list* (mp:attval atts "CONDUCTOR" (mp:attval atts "CONDUCTORES" "")))
  (mp:fill-popup-val "ductos" *mp-ductos-list* (mp:attval atts "DUCTOS" "6"))
  (mp:fill-popup-val "diamducto" *mp-diam-ducto-list* (mp:attval atts "DIAM_DUCTO" "6\""))
  (mp:fill-popup-val "matducto" *mp-mat-ducto-list* (mp:attval atts "MATERIAL_DUCTO" "PVC"))
  (mp:fill-popup-val "ubic" *mp-ubic-elec-list* (mp:attval atts "UBICACION" "Anden o zona verde"))
  (set_tile "long" (mp:attval atts "LONGITUD" "")) (mode_tile "long" 1)
  (set_tile "anchoz" (mp:attval atts "ANCHO_ZANJA" ""))
  (set_tile "cama" (mp:attval atts "ESPESOR_CAMA" "0.10"))
  (set_tile "repos" (mp:attval atts "ANCHO_REPOSICION" ""))
  (action_tile "etapa" "(setq *mp-edit-subetapa-current* \"\")(mp:subetapa-fill-current)")
  (action_tile "accept" "(mp:capture-dialog-values)(setq ok T)(done_dialog 1)") (action_tile "cancel" "(setq ok nil)(done_dialog 0)")
  (start_dialog)
  (if ok (progn (setq etapa (mp:item *mp-etapa-list* "etapa"))
    (setq res (list (cons "ETAPA" etapa) (cons "SUBETAPA" (mp:item (mp:subetapas-for etapa) "subetapa"))
                    (cons "TIPO_RED" "MT") (cons "DESDE" (mp:gettile "desde")) (cons "HASTA" (mp:gettile "hasta"))
                    (cons "CONDUCTORES" (mp:item *mp-cond-mt-list* "cond")) (cons "CONDUCTOR" (mp:item *mp-cond-mt-list* "cond"))
                    (cons "DUCTOS" (mp:item *mp-ductos-list* "ductos")) (cons "DIAM_DUCTO" (mp:item *mp-diam-ducto-list* "diamducto"))
                    (cons "MATERIAL_DUCTO" (mp:item *mp-mat-ducto-list* "matducto"))
                    (cons "UBICACION" (mp:item *mp-ubic-elec-list* "ubic"))
                    (cons "PROFUNDIDAD" "")
                    (cons "ANCHO_ZANJA" (mp:gettile "anchoz"))
                    (cons "ESPESOR_CAMA" (mp:gettile "cama"))
                    (cons "ANCHO_REPOSICION" (mp:gettile "repos"))
              (cons "TIPO_EXTREMO_INI" (mp:item *mp-extremo-elec-list* "tipo_ini"))
              (cons "TIPO_EXTREMO_FIN" (mp:item *mp-extremo-elec-list* "tipo_fin"))))))
  (unload_dialog dcl) res)

(defun mp:edit-dialog-tramo-bt (atts / dcl ok etapa res)
  (setq dcl (load_dialog (mp:write-dcl-editar)))
  (if (not (new_dialog "edit_tramo_bt" dcl)) (exit))
  (setq *mp-edit-subetapa-current* (mp:attval atts "SUBETAPA" ""))
  (mp:fill-popup-val "etapa" *mp-etapa-list* (mp:attval atts "ETAPA" "1")) (mp:subetapa-fill-current)
  (set_tile "desde" (mp:attval atts "DESDE" "")) (set_tile "hasta" (mp:attval atts "HASTA" ""))
  (mp:fill-popup-val "tipo_ini" *mp-extremo-elec-list* (mp:attval atts "TIPO_EXTREMO_INI" "CAMARA_CS276"))
  (mp:fill-popup-val "tipo_fin" *mp-extremo-elec-list* (mp:attval atts "TIPO_EXTREMO_FIN" "CAMARA_CS276"))
  (mp:fill-popup-val "cond" *mp-cond-bt-list* (mp:attval atts "CONDUCTOR" ""))
  (mp:fill-popup-val "ductos" *mp-ductos-list* (mp:attval atts "DUCTOS" "1"))
  (mp:fill-popup-val "diamducto" *mp-diam-ducto-list* (mp:attval atts "DIAM_DUCTO" "3\""))
  (mp:fill-popup-val "matducto" *mp-mat-ducto-list* (mp:attval atts "MATERIAL_DUCTO" "PVC"))
  (mp:fill-popup-val "ubic" *mp-ubic-elec-list* (mp:attval atts "UBICACION" "Anden o zona verde"))
  (set_tile "anchoz" (mp:attval atts "ANCHO_ZANJA" ""))
  (set_tile "cama" (mp:attval atts "ESPESOR_CAMA" "0.10"))
  (set_tile "repos" (mp:attval atts "ANCHO_REPOSICION" ""))
  (set_tile "long" (mp:attval atts "LONGITUD" "")) (mode_tile "long" 1)
  (action_tile "etapa" "(setq *mp-edit-subetapa-current* \"\")(mp:subetapa-fill-current)")
  (action_tile "accept" "(mp:capture-dialog-values)(setq ok T)(done_dialog 1)") (action_tile "cancel" "(setq ok nil)(done_dialog 0)")
  (start_dialog)
  (if ok (progn (setq etapa (mp:item *mp-etapa-list* "etapa"))
    (setq res (list (cons "ETAPA" etapa) (cons "SUBETAPA" (mp:item (mp:subetapas-for etapa) "subetapa"))
                    (cons "TIPO_RED" (mp:attval atts "TIPO_RED" "BT")) (cons "DESDE" (mp:gettile "desde")) (cons "HASTA" (mp:gettile "hasta"))
                    (cons "CONDUCTOR" (mp:item *mp-cond-bt-list* "cond")) (cons "DUCTOS" (mp:item *mp-ductos-list* "ductos"))
                    (cons "DIAM_DUCTO" (mp:item *mp-diam-ducto-list* "diamducto")) (cons "MATERIAL_DUCTO" (mp:item *mp-mat-ducto-list* "matducto"))
                    (cons "UBICACION" (mp:item *mp-ubic-elec-list* "ubic"))
                    (cons "PROFUNDIDAD" "")
                    (cons "ANCHO_ZANJA" (mp:gettile "anchoz"))
                    (cons "ESPESOR_CAMA" (mp:gettile "cama"))
                    (cons "ANCHO_REPOSICION" (mp:gettile "repos"))
              (cons "TIPO_EXTREMO_INI" (mp:item *mp-extremo-elec-list* "tipo_ini")) (cons "TIPO_EXTREMO_FIN" (mp:item *mp-extremo-elec-list* "tipo_fin"))))))
  (unload_dialog dcl) res)

(defun mp:edit-dialog-punto-hidro (atts base / dcl ok etapa red diamlist res)
  (setq dcl (load_dialog (mp:write-dcl-editar)))
  (if (not (new_dialog "edit_punto_hidro" dcl)) (exit))
  (setq red (mp:attval atts "RED" (cond ((= base "POZO_SANITARIO") "Aresidual") ((= base "POZO_PLUVIAL") "Alluvias") (T "Alluvias"))))
  (set_tile "redtxt" (strcat "Red fija del bloque: " red))
  (setq *mp-edit-subetapa-current* (mp:attval atts "SUBETAPA" ""))
  (mp:fill-popup-val "etapa" *mp-etapa-list* (mp:attval atts "ETAPA" "1")) (mp:subetapa-fill-current)
  (set_tile "id" (mp:attval atts "ID" ""))
  (setq diamlist (if (= red "Acueducto") *mp-diam-acu-list* *mp-diam-alc-list*))
  (mp:fill-popup-val "diam" diamlist (mp:attval atts "DIAMETRO" ""))
  (set_tile "ctn" (mp:attval atts "COTA_TN_INI" "")) (set_tile "cclave" (mp:attval atts "COTA_CLAVE_INI" "")) (set_tile "prof" (mp:attval atts "PROFUNDIDAD" ""))
  (action_tile "etapa" "(setq *mp-edit-subetapa-current* \"\")(mp:subetapa-fill-current)")
  (action_tile "accept" "(mp:capture-dialog-values)(setq ok T)(done_dialog 1)") (action_tile "cancel" "(setq ok nil)(done_dialog 0)")
  (start_dialog)
  (if ok (progn (setq etapa (mp:item *mp-etapa-list* "etapa"))
    (setq res (list (cons "ETAPA" etapa) (cons "SUBETAPA" (mp:item (mp:subetapas-for etapa) "subetapa"))
                    (cons "RED" red) (cons "ID" (mp:gettile "id")) (cons "DIAMETRO" (mp:item diamlist "diam"))
                    (cons "COTA_TN_INI" (mp:gettile "ctn")) (cons "COTA_CLAVE_INI" (mp:gettile "cclave")) (cons "PROFUNDIDAD" (mp:gettile "prof"))))))
  (unload_dialog dcl) res)

(defun mp:edit-dialog-acc-acu (atts / dcl ok etapa res)
  (setq dcl (load_dialog (mp:write-dcl-editar)))
  (if (not (new_dialog "edit_acc_acu" dcl)) (exit))
  (setq *mp-edit-subetapa-current* (mp:attval atts "SUBETAPA" ""))
  (mp:fill-popup-val "acc" *mp-acc-acu-list* (mp:attval atts "TIPO_ACCESORIO" ""))
  (mp:fill-popup-val "etapa" *mp-etapa-list* (mp:attval atts "ETAPA" "1")) (mp:subetapa-fill-current)
  (set_tile "id" (mp:attval atts "ID" ""))
  (mp:fill-popup-val "diam" *mp-diam-acu-list* (mp:attval atts "DIAMETRO" ""))
  (mp:fill-popup-val "diamsal" *mp-diam-acu-list* (mp:attval atts "DIAMETRO_SALIDA" ""))
  (mp:fill-popup-val "mat" *mp-material-acu-list* (mp:attval atts "MATERIAL" "PVC"))
  (set_tile "lote" (mp:attval atts "LOTE" ""))
  (action_tile "etapa" "(setq *mp-edit-subetapa-current* \"\")(mp:subetapa-fill-current)")
  (action_tile "accept" "(mp:capture-dialog-values)(setq ok T)(done_dialog 1)") (action_tile "cancel" "(setq ok nil)(done_dialog 0)")
  (start_dialog)
  (if ok (progn (setq etapa (mp:item *mp-etapa-list* "etapa"))
    (setq res (list (cons "TIPO_ACCESORIO" (mp:item *mp-acc-acu-list* "acc")) (cons "ETAPA" etapa) (cons "SUBETAPA" (mp:item (mp:subetapas-for etapa) "subetapa"))
                    (cons "ID" (mp:gettile "id")) (cons "DIAMETRO" (mp:item *mp-diam-acu-list* "diam"))
                    (cons "DIAMETRO_SALIDA" (mp:item *mp-diam-acu-list* "diamsal")) (cons "MATERIAL" (mp:item *mp-material-acu-list* "mat"))
                    (cons "LOTE" (mp:gettile "lote"))))))
  (unload_dialog dcl) res)

(defun mp:edit-dialog-caja-elec (atts base / dcl ok etapa res typelist)
  (setq dcl (load_dialog (mp:write-dcl-editar)))
  (if (not (new_dialog "edit_caja_elec" dcl)) (exit))
  (setq typelist *mp-caja-elec-list*)
  (mp:fill-popup-val "tipo" typelist base)
  (setq *mp-edit-subetapa-current* (mp:attval atts "SUBETAPA" ""))
  (mp:fill-popup-val "etapa" *mp-etapa-list* (mp:attval atts "ETAPA" "1")) (mp:subetapa-fill-current)
  (set_tile "id" (mp:attval atts "ID" "")) (set_tile "ductos" (mp:attval atts "DUCTOS" "")) (set_tile "libres" (mp:attval atts "LIBRES" ""))
  (set_tile "prof" (mp:attval atts "PROFUNDIDAD" "")) (set_tile "cd" (mp:attval atts "CD" "")) (set_tile "pf" (mp:attval atts "PF" ""))
  (action_tile "etapa" "(setq *mp-edit-subetapa-current* \"\")(mp:subetapa-fill-current)")
  (action_tile "accept" "(mp:capture-dialog-values)(setq ok T)(done_dialog 1)") (action_tile "cancel" "(setq ok nil)(done_dialog 0)")
  (start_dialog)
  (if ok (progn (setq etapa (mp:item *mp-etapa-list* "etapa"))
    (setq base (mp:item typelist "tipo"))
    (setq res (list (cons "BLOQUE_BASE" base) (cons "ETAPA" etapa) (cons "SUBETAPA" (mp:item (mp:subetapas-for etapa) "subetapa"))
                    (cons "ID" (mp:gettile "id")) (cons "TIPO_CAJA" (mp:tipo-caja-de base))
                    (cons "DUCTOS" (mp:gettile "ductos")) (cons "LIBRES" (mp:gettile "libres"))
                    (cons "PROFUNDIDAD" (mp:gettile "prof")) (cons "CD" (mp:gettile "cd")) (cons "PF" (mp:gettile "pf"))))))
  (unload_dialog dcl) res)

(defun mp:edit-dialog-luminaria (atts / dcl ok etapa res)
  (setq dcl (load_dialog (mp:write-dcl-editar)))
  (if (not (new_dialog "edit_luminaria" dcl)) (exit))
  (setq *mp-edit-subetapa-current* (mp:attval atts "SUBETAPA" ""))
  (mp:fill-popup-val "etapa" *mp-etapa-list* (mp:attval atts "ETAPA" "1")) (mp:subetapa-fill-current)
  (set_tile "id" (mp:attval atts "CODIGO" (mp:attval atts "ID" "")))
  (mp:fill-popup-val "lum" *mp-lum-list* (mp:attval atts "TIPO_LUMINARIA" ""))
  (mp:fill-popup-val "led" *mp-led-list* (mp:attval atts "FUENTE_LED" ""))
  (set_tile "altura" (mp:attval atts "ALTURA_M" "")) (set_tile "brazo" (mp:attval atts "BRAZO_M" "")) (set_tile "avance" (mp:attval atts "AVANCE_M" ""))
  (set_tile "circuito" (mp:attval atts "CIRCUITO_AP" ""))
  (action_tile "etapa" "(setq *mp-edit-subetapa-current* \"\")(mp:subetapa-fill-current)")
  (action_tile "accept" "(mp:capture-dialog-values)(setq ok T)(done_dialog 1)") (action_tile "cancel" "(setq ok nil)(done_dialog 0)")
  (start_dialog)
  (if ok (progn (setq etapa (mp:item *mp-etapa-list* "etapa"))
    (setq res (list (cons "ETAPA" etapa) (cons "SUBETAPA" (mp:item (mp:subetapas-for etapa) "subetapa"))
                    (cons "CODIGO" (mp:gettile "id")) (cons "ID" (mp:gettile "id"))
                    (cons "TIPO_LUMINARIA" (mp:item *mp-lum-list* "lum")) (cons "FUENTE_LED" (mp:item *mp-led-list* "led"))
                    (cons "ALTURA_M" (mp:gettile "altura")) (cons "BRAZO_M" (mp:gettile "brazo")) (cons "AVANCE_M" (mp:gettile "avance"))
                    (cons "CIRCUITO_AP" (mp:gettile "circuito"))))))
  (unload_dialog dcl) res)


(defun mp:editable-base-p (base)
  (or
    (member base
      '("TRAMO_ARESIDUAL" "TRAMO_ALLUVIAS" "TRAMO_ACUEDUCTO"
        "TRAMO_E_MT" "TRAMO_E_BT_AP" "POZO_SANITARIO"
        "POZO_PLUVIAL" "SUMIDERO" "CABEZAL_PLUVIAL" "ACCESORIO_ACUEDUCTO"
        "CAMARA_CS274" "CAMARA_CS275" "CAMARA_CS276" "CAMARA_CS280"
        "CAJA_BARRAJE_CS281" "LUMINARIA_AP"))))

(defun mp:editable-entity-p (en / obj bname atts base)
  (and en
       (= (cdr (assoc 0 (entget en))) "INSERT")
       (setq obj (vlax-ename->vla-object en))
       (setq bname (vla-get-EffectiveName obj))
       (setq atts (mp:att-alist en))
       (setq base (mp:infer-base bname atts))
       (mp:editable-base-p base))
)

(defun mp:edit-entity (en / obj bname atts base vals saved)
  (if (mp:editable-entity-p en)
    (progn
      (setq obj (vlax-ename->vla-object en))
      (setq bname (vla-get-EffectiveName obj))
      (setq atts (mp:att-alist en))
      (setq base (mp:infer-base bname atts))
      (setq vals
        (cond
          ((member base '("TRAMO_ARESIDUAL" "TRAMO_ALLUVIAS" "TRAMO_ACUEDUCTO")) (mp:edit-dialog-tramo-red atts base))
          ((= base "TRAMO_E_MT") (mp:edit-dialog-tramo-mt atts))
          ((= base "TRAMO_E_BT_AP") (mp:edit-dialog-tramo-bt atts))
          ((member base '("POZO_SANITARIO" "POZO_PLUVIAL" "SUMIDERO" "CABEZAL_PLUVIAL")) (mp:edit-dialog-punto-hidro atts base))
          ((= base "ACCESORIO_ACUEDUCTO") (mp:edit-dialog-acc-acu atts))
          ((member base *mp-caja-elec-list*) (mp:edit-dialog-caja-elec atts base))
          ((= base "LUMINARIA_AP") (mp:edit-dialog-luminaria atts))
          (T nil)))
      (if vals
        (progn
          (setq saved (mp:update-block-after-edit en vals))
          (princ (strcat "\nBloque PPTO actualizado. Atributos guardados: " (itoa saved)))
          T)
        (progn
          (princ "\nEste bloque no tiene formulario de edicion.")
          nil)))
    nil)
)

;;; ============================================================
;;; V13 OPTIMIZADA
;;; - Una sola implementacion activa, sin versiones concatenadas.
;;; - Reutiliza bloques de puntos por tipo.
;;; - Reutiliza bloques de tramos cuando tipo y longitud coinciden.
;;; - Cancelacion segura y formularios de elementos completos.
;;; - Conserva valores heredados que no existan en las listas.
;;; - LONGITUD se calcula desde la geometria y no se edita manualmente.
;;; ============================================================

(setq *mp-popup-lists* nil)

(defun mp:popup-list (key fallback / pair)
  (setq pair (assoc key *mp-popup-lists*))
  (if pair (cdr pair) fallback))

(defun mp:remember-popup (key lst / pair)
  (if (setq pair (assoc key *mp-popup-lists*))
    (setq *mp-popup-lists* (subst (cons key lst) pair *mp-popup-lists*))
    (setq *mp-popup-lists* (cons (cons key lst) *mp-popup-lists*))))

(defun mp:fill-popup (key lst idx)
  ;; 2026-08-12: con etapas deshabilitadas los tiles etapa/subetapa NO se
  ;; emiten en los DCL de creacion (ocultos, no grises) -- llenar un tile
  ;; inexistente truena, asi que se omite aqui centralizadamente. Los
  ;; dialogos de EDICION si conservan los tiles y quedan grises.
  (if (and (member key '("etapa" "subetapa"))
           (not (urb:etapas-enabled-p))
           (not *mp-dialog-edit-mode*))
    nil
    (progn
      (mp:remember-popup key lst)
      (start_list key)
      (mapcar 'add_list lst)
      (end_list)
      (if (not idx) (setq idx 0))
      (set_tile key (itoa idx))
      ;; etapas deshabilitadas -> popup gris (dialogos de edicion)
      (if (and (member key '("etapa" "subetapa"))
               (not (urb:etapas-enabled-p)))
        (mode_tile key 1)))))

(defun mp:item (lst key / raw i use)
  (setq use (mp:popup-list key lst))
  (setq raw (mp:gettile key))
  (if (= raw "") (setq raw "0"))
  (setq i (atoi raw))
  (if (and (>= i 0) (< i (length use))) (nth i use) (if use (car use) "")))

(defun mp:fill-popup-val (key lst val / use)
  (setq val (mp:safe-str val))
  (setq use
    (if (or (= val "") (member (strcase val) (mapcar 'strcase lst)))
      lst
      (cons val lst)))
  (mp:fill-popup key use (mp:idx val use)))

(defun mp:block-token (base)
  (cond
    ((= base "TRAMO_ARESIDUAL") "SAN")
    ((= base "TRAMO_ALLUVIAS") "PLU")
    ((= base "TRAMO_ACUEDUCTO") "ACU")
    ((= base "TRAMO_E_MT") "MT")
    ((= base "TRAMO_E_BT_AP") "BTAP")
    ((= base "POZO_SANITARIO") "POZO_SAN")
    ((= base "POZO_PLUVIAL") "POZO_PLU")
    ((= base "SUMIDERO") "SUMIDERO")
    ((= base "ACCESORIO_ACUEDUCTO") "ACC_ACU")
    ((= base "CABEZAL_PLUVIAL") "CABEZAL")
    ((= base "LUMINARIA_AP") "LUMINARIA")
    (T (vl-string-translate " -" "__" base))))

(defun mp:tramo-block-name (base dist / ds)
  ;; 2 decimales (antes 4): tramos de longitud casi igual comparten una
  ;; misma definicion de bloque y el DWG no acumula definiciones de mas.
  (setq ds (vl-string-translate ".-" "_M" (rtos dist 2 2)))
  (strcat "MP_TRAMO_" (mp:block-token base) "_" ds))

(defun mp:point-block-name (base)
  (strcat "MP_PUNTO_" (mp:block-token base)))

(defun mp:is-cant-blockname (bname)
  (or (member (strcase bname) (mapcar 'strcase *mp-blocks*))
      (mp:starts-with bname "CANT_TRAMO_")
      (mp:starts-with bname "CANT_PUNTO_")
      (mp:starts-with bname "MP_TRAMO_")
      (mp:starts-with bname "MP_PUNTO_")))

(defun mp:is-tramo-name (bname)
  (or (mp:starts-with bname "CANT_TRAMO_")
      (mp:starts-with bname "MP_TRAMO_")))

(defun mp:is-point-name (bname)
  (or (mp:starts-with bname "CANT_PUNTO_")
      (mp:starts-with bname "MP_PUNTO_")))

(defun mp:diametro-label (vals / d)
  (setq d (vl-string-trim " " (mp:getval "DIAMETRO" vals "?")))
  (if (and (> (strlen d) 0) (= (substr d (strlen d) 1) "\""))
    d
    (strcat d "\"")))

;; 5.5.10: "numero de tramos" confirmado como numero de tubos, NO circuitos.
;; El usuario identifica la acometida por el CONDUCTOR de la foto, no pide
;; contar derivaciones/postes. Arriba conductor, abajo longitud y ducteria.
(defun mp:ducteria-label (vals / d)
  (setq d (vl-string-trim " \"" (mp:getval "DIAM_DUCTO" vals "?")))
  (strcat (mp:getval "DUCTOS" vals "?") "%%c" d "\" "
    (mp:getval "MATERIAL_DUCTO" vals "")))

(defun mp:long-label (vals)
  (strcat "L=" (mp:getval "LONGITUD" vals "?") " m | "
    (mp:ducteria-label vals)))

(defun mp:label-tramo (base vals / l d mat)
  (setq l (mp:getval "LONGITUD" vals ""))
  (setq d (mp:diametro-label vals))
  (setq mat (mp:getval "MATERIAL" vals ""))
  (cond
    ;; 2026-08-28: etiqueta compacta estilo plano record ("Ø8" PVC L=34");
    ;; tramos ACU muy cortos (<8 m, conectores entre accesorios de un
    ;; mismo cruce) SIN etiqueta -- eran la causa de cota sobre cota
    ((= base "TRAMO_ACUEDUCTO")
      (if (< (atof (mp:safe-str l)) 8.0)
        ""
        (strcat l "-%%c" d "\"-" mat)))
    ((= base "TRAMO_ALLUVIAS")
      (strcat "ALL L=" l "- %%c" d "-" mat))
    ((= base "TRAMO_ARESIDUAL")
      (strcat "SAN L=" l "- %%c" d "-" mat))
    ((member base '("TRAMO_E_MT" "TRAMO_E_BT_AP"))
      (mp:getval "CONDUCTOR" vals
        (mp:getval "CONDUCTORES" vals "Conductor: sin dato")))
    (T (strcat base " L=" l))))

;; "last" es funcion nativa de AutoLISP; renombrado por prevencion
;; (mismo patron que distance/length/type en otras partes del archivo),
;; aunque aqui no llegaba a colisionar con una llamada real.
(defun mp:pendiente-label (vals / p last-char)
  (setq p (vl-string-trim " " (mp:getval "PENDIENTE" vals "")))
  (if (= p "")
    ""
    (progn
      (setq last-char (substr p (strlen p) 1))
      (if (= last-char "%") p (strcat p "%")))))
;; Codigo corto de norma (CS274..CS281) a partir del nombre de bloque base.
(defun mp:tipo-caja-de (base)
  (cond
    ((= base "CAMARA_CS274") "CS274")
    ((= base "CAMARA_CS275") "CS275")
    ((= base "CAMARA_CS276") "CS276")
    ((= base "CAMARA_CS280") "CS280")
    ((= base "CAJA_BARRAJE_CS281") "CS281")
    (T base)))

;; 2026-08-26 (pedido del usuario): en la caja, ARRIBA solo el numero de
;; norma ("276", "280"...) y ABAJO solo el consecutivo ("1", "2"...).
(defun mp:solo-digitos (s / i c out)
  (setq out "" i 1 s (mp:safe-str s))
  (repeat (strlen s)
    (setq c (substr s i 1))
    (if (wcmatch c "#") (setq out (strcat out c)))
    (setq i (1+ i)))
  out)

(defun mp:caja-tipo-label (base vals / d)
  (setq d (mp:solo-digitos (mp:getval "TIPO_CAJA" vals (mp:tipo-caja-de base))))
  (if (= d "") (mp:tipo-caja-de base) d))

;; Chequeo de nivelacion de caja (2026-08-26): compara la cota de tapa
;; proyectada (COTA_TAPA, rasante en el punto) con el terreno natural
;; muestreado (COTA_TN_INI). |d| <= 0.15 m se considera OK.
(defun mp:caja-nivelacion (vals / tn tapa d)
  (setq tn (mp:numeric-real (mp:getval "COTA_TN_INI" vals "")))
  (setq tapa (mp:numeric-real (mp:getval "COTA_TAPA" vals "")))
  (if (and tn tapa)
    (progn
      (setq d (- tapa tn))
      (cond
        ((> d 0.15) (strcat "COLGADA +" (rtos d 2 2) " (relleno alto)"))
        ((< d -0.15) (strcat "ENTERRADA " (rtos d 2 2) " (corte pendiente)"))
        (T "OK")))
    "PENDIENTE"))

(defun mp:caja-num-label (vals / id p)
  (setq id (mp:getval "ID" vals (mp:getval "CODIGO" vals "")))
  (setq p (vl-string-position (ascii "-") id 0 T))
  (if p (substr id (+ p 2)) id))

(defun mp:label-point (base vals / id)
  (setq id (mp:getval "ID" vals (mp:getval "CODIGO" vals "")))
  (cond
    ((= base "POZO_SANITARIO") id)
    ((= base "POZO_PLUVIAL") id)
    ((= base "SUMIDERO") (strcat "SUM " id))
    ((member base '("CAMARA_CS274" "CAMARA_CS275" "CAMARA_CS276" "CAMARA_CS280" "CAJA_BARRAJE_CS281")) (mp:caja-tipo-label base vals))
    ;; 2026-09-07 (pedido del usuario: "en la cota del accesorio solo
    ;; quiero el numero y ya" -- como los nodos del plano): SOLO el ID;
    ;; sin numero, el token corto como respaldo.
    ((= base "ACCESORIO_ACUEDUCTO")
      (if (/= id "")
        id
        (mp:acc-tipo-token (mp:getval "TIPO_ACCESORIO" vals ""))))
    ((= base "CABEZAL_PLUVIAL") (strcat "CAB " id))
    ((= base "LUMINARIA_AP") (strcat "LUM " (mp:getval "CODIGO" vals id)))
    ((= base "POSTE_ELEC") id)
    ((= base "TRANSFORMADOR_AP") id)
    (T (strcat base " " id))))

(defun mp:alist-set (values tag value / pair)
  (setq tag (strcase tag)
        pair (assoc tag values))
  (if pair
    (subst (cons tag value) pair values)
    (cons (cons tag value) values)))

(defun mp:numeric-real (value / text index character cleaned parsed)
  (setq text (mp:safe-str value)
        index 1
        cleaned "")
  (while (<= index (strlen text))
    (setq character (substr text index 1))
    (if (vl-string-search character "0123456789,.-+")
      (setq cleaned (strcat cleaned character)))
    (setq index (1+ index)))
  (setq parsed (urb:parse-real cleaned))
  parsed)

(defun mp:number-or (value default / parsed)
  (setq parsed (mp:numeric-real value))
  (if parsed parsed default))

(defun mp:join-messages (messages / result message)
  (setq result "")
  (foreach message messages
    (setq result
      (if (= result "") message (strcat result " | " message))))
  result)

(defun mp:hydro-tramo-p (base)
  (member base
    '("TRAMO_ARESIDUAL" "TRAMO_ALLUVIAS" "TRAMO_ACUEDUCTO")))

;; 2026-08-25 (pedido del usuario: MT "quedo muy desorganizado ... circulo a
;; circulo como si fueran pozos"). MT/BT-AP tienen igual que hidrosanitario
;; cajas/postes/trafos como bloques puntuales independientes -- dibujar
;; ademas circulos genericos DENTRO del tramo los hacia ver como pozos
;; identicos entre si en vez de mostrar la caja real (cuadrada, CS276/280).
(defun mp:tramo-own-node-blocks-p (base)
  (or (mp:hydro-tramo-p base)
      (member base '("TRAMO_E_MT" "TRAMO_E_BT_AP"))))

(defun mp:gravity-tramo-p (base)
  (member base '("TRAMO_ARESIDUAL" "TRAMO_ALLUVIAS")))

(defun mp:current-terrain-surface
  (/ ss index ename obj name-result found)
  ;; La busqueda se hace siempre en el dibujo activo. No se reutiliza a
  ;; ciegas una superficie almacenada de otro DWG y no se toman superficies
  ;; anidadas en XREF: SUP_TN debe pertenecer a URB_MASTER_GENERAL.
  (setq ss
    (ssget "_X"
      '((0 . "AECC_TIN_SURFACE,AECC_GRID_SURFACE,AECC_TIN_VOLUME_SURFACE"))))
  (if ss
    (progn
      (setq index 0)
      (while (and (< index (sslength ss)) (not found))
        (setq ename (ssname ss index)
              obj (vlax-ename->vla-object ename)
              name-result
                (vl-catch-all-apply 'vla-get-Name (list obj)))
        (if (and
              (not (vl-catch-all-error-p name-result))
              (urb:string-equal-p
                name-result *mp-terrain-surface-name*))
          (setq found obj))
        (setq index (1+ index)))))
  found)

(defun mp:terrain-elevation-at-point (surface point / result)
  (if (and surface point (car point) (cadr point))
    (progn
      (setq result
        (vl-catch-all-apply
          'vlax-invoke
          (list surface 'FindElevationAtXY
            (float (car point)) (float (cadr point)))))
      (if (or (vl-catch-all-error-p result) (not (numberp result)))
        nil
        result))
    nil))

(defun mp:auto-terrain-values
  (values point-initial point-final
   / surface elevation-initial elevation-final state)
  (setq values
    (mp:alist-set values "SUPERFICIE_TN" *mp-terrain-surface-name*)
        surface (mp:current-terrain-surface))
  (if surface
    (progn
      (setq elevation-initial
              (mp:terrain-elevation-at-point surface point-initial)
            elevation-final
              (if point-final
                (mp:terrain-elevation-at-point surface point-final)
                nil))
      ;; Una consulta fallida nunca borra una cota anterior ni escribe cero.
      (if elevation-initial
        (setq values
          (mp:alist-set values "COTA_TN_INI"
            (rtos elevation-initial 2 3))))
      (if elevation-final
        (setq values
          (mp:alist-set values "COTA_TN_FIN"
            (rtos elevation-final 2 3))))
      (setq state
        (cond
          ((not point-final)
            (if elevation-initial "OK" "FUERA_SUPERFICIE"))
          ((and elevation-initial elevation-final) "OK")
          ((or elevation-initial elevation-final) "PARCIAL")
          (T "FUERA_SUPERFICIE"))))
    (setq state "SIN_SUPERFICIE"))
  (mp:alist-set values "ESTADO_COTA_TN" state))

;; Tabla literal de la hoja "Anchos Exc. PVC (Ent)" del presupuesto de redes
;; (tuberia NOVAFORT/NOVALOC, alcantarillado). Se copian los anchos ya
;; calculados en Excel -no se reconstruye la formula de holguras variables
;; por rango de diametro- para no arriesgar un error de traduccion; si el
;; Excel cambia, esta tabla se debe resincronizar a mano.
;; Cada entrada: diametro-nominal-en-pulgadas . anchos-por-rango-de-profundidad
;; Rangos de profundidad, columnas H..Q del Excel, en metros: hasta 1.5,
;; hasta 2.5, hasta 3.5, hasta 4.5, hasta 5.5, hasta 6.5, hasta 7.5,
;; hasta 8.5, hasta 9.5, hasta 10.5 (y mas alla de 10.5 usa la ultima).
(setq *mp-pvc-trench-width-table*
  '((4 . (0.90 1.00 1.10 1.20 1.20 1.20 1.20 1.20 1.20 1.20))
    (6 . (0.90 1.00 1.10 1.20 1.20 1.20 1.20 1.20 1.20 1.20))
    (8 . (0.90 1.00 1.10 1.20 1.20 1.20 1.20 1.20 1.20 1.20))
    (10 . (0.90 1.00 1.10 1.20 1.20 1.20 1.20 1.20 1.20 1.20))
    (12 . (0.90 1.00 1.10 1.20 1.20 1.20 1.20 1.20 1.20 1.20))
    (14 . (0.95 1.00 1.10 1.20 1.20 1.20 1.20 1.20 1.20 1.20))
    (16 . (1.15 1.15 1.25 1.25 1.25 1.25 1.25 1.25 1.25 1.25))
    (18 . (1.20 1.20 1.30 1.30 1.30 1.30 1.30 1.30 1.30 1.30))
    (20 . (1.25 1.25 1.35 1.35 1.35 1.35 1.35 1.35 1.35 1.35))
    (24 . (1.40 1.40 1.50 1.50 1.50 1.50 1.50 1.50 1.50 1.50))
    (27 . (1.45 1.45 1.55 1.55 1.55 1.55 1.55 1.55 1.55 1.55))
    (30 . (1.70 1.70 1.80 1.80 1.80 1.80 1.80 1.80 1.80 1.80))
    (33 . (1.75 1.75 1.85 1.85 1.85 1.85 1.85 1.85 1.85 1.85))
    (36 . (1.85 1.85 1.95 1.95 1.95 1.95 1.95 1.95 1.95 1.95))
    (39 . (1.95 1.95 2.05 2.05 2.05 2.05 2.05 2.05 2.05 2.05))
    (42 . (2.00 2.00 2.10 2.10 2.10 2.10 2.10 2.10 2.10 2.10))
    (45 . (2.10 2.10 2.20 2.20 2.20 2.20 2.20 2.20 2.20 2.20))
    (48 . (2.15 2.15 2.25 2.25 2.25 2.25 2.25 2.25 2.25 2.25))
    (51 . (2.40 2.40 2.50 2.50 2.50 2.50 2.50 2.50 2.50 2.50))
    (54 . (2.45 2.45 2.55 2.55 2.55 2.55 2.55 2.55 2.55 2.55))
    (57 . (2.55 2.55 2.65 2.65 2.65 2.65 2.65 2.65 2.65 2.65))
    (60 . (2.60 2.60 2.70 2.70 2.70 2.70 2.70 2.70 2.70 2.70))))

(defun mp:trench-width-bracket-index (depth)
  (cond
    ((<= depth 1.5) 0) ((<= depth 2.5) 1) ((<= depth 3.5) 2)
    ((<= depth 4.5) 3) ((<= depth 5.5) 4) ((<= depth 6.5) 5)
    ((<= depth 7.5) 6) ((<= depth 8.5) 7) ((<= depth 9.5) 8)
    (T 9)))

;; 2026-09-13 (pedido del usuario: "no quiero que ningun diametro de
;; tuberia quede sin ancho de excavacion sino que al reves, si agrego un
;; numero, dependiendo de normativa lo clasifique automaticamente").
;; La tabla de arriba es la del Excel de redes y solo trae los diametros
;; comerciales. ANTES, un diametro fuera de la tabla devolvia nil y el
;; llamador caia a un generico (Ø + 0,40 m, minimo 0,60) que se queda
;; CORTO frente a la norma: el 15" -- que esta en la lista y ademas es el
;; que traen por defecto los dialogos de sanitario/pluvial -- daba 0,78 m
;; contra los 1,05 m que le corresponden, y el 64" daba 2,03 contra 2,70.
;; Para excavacion quedarse corto es peor que quedarse largo.
;; AHORA se clasifica solo: se INTERPOLA linealmente entre los dos
;; diametros vecinos de la tabla, tramo de profundidad por tramo, y se
;; redondea al siguiente multiplo de 0,05 m (no se excava menos de lo que
;; da la norma). Por encima del ultimo diametro se extrapola con la
;; pendiente del ultimo par; por debajo del primero se usa la primera fila.
(defun mp:trench-round-up-005 (v)
  (/ (float (fix (+ (* v 20.0) 0.999999))) 20.0))

;; ancho de UN tramo de profundidad (idx) para un diametro cualquiera
(defun mp:trench-width-at (d idx / lst lo hi prev vlo vhi w)
  (setq lst *mp-pvc-trench-width-table* lo nil hi nil)
  (foreach entry lst
    (if (<= (car entry) d)
      (setq lo entry)
      (if (null hi) (setq hi entry))))
  (cond
    ((and lo (= (car lo) d)) (nth idx (cdr lo)))
    ((null lo) (nth idx (cdr (car lst))))
    ((null hi)
      ;; mas grande que toda la tabla: pendiente del ultimo par
      (setq prev (nth (- (length lst) 2) lst)
            vlo (nth idx (cdr prev))
            vhi (nth idx (cdr lo))
            w (+ vhi (* (- d (car lo))
                  (/ (- vhi vlo) (float (- (car lo) (car prev)))))))
      (mp:trench-round-up-005 w))
    (T
      (setq vlo (nth idx (cdr lo))
            vhi (nth idx (cdr hi))
            w (+ vlo (* (- d (car lo))
                  (/ (- vhi vlo) (float (- (car hi) (car lo)))))))
      (setq w (mp:trench-round-up-005 w))
      ;; el redondeo no puede pasarse del vecino mayor: romperia el orden
      ;; creciente de la tabla
      (if (> w vhi) vhi w))))

(defun mp:pvc-trench-width (diameter-in depth / d)
  (setq d (fix (+ (mp:number-or diameter-in 0.0) 0.5)))
  (if (<= d 0)
    nil
    (mp:trench-width-at d
      (mp:trench-width-bracket-index (max 0.0 (mp:number-or depth 0.0))))))

;; ¿el ancho de este diametro sale de la tabla o se interpolo?
(defun mp:trench-width-exacto-p (d)
  (if (assoc (fix (+ (mp:number-or d 0.0) 0.5)) *mp-pvc-trench-width-table*)
    T nil))

(defun mp:max-nonnil (values / result v)
  (foreach v values
    (if (and v (or (null result) (> v result))) (setq result v)))
  result)

;; 2026-08-03: modo de referencia del relleno de tramos, configurado UNA
;; VEZ desde URBANISMO -> Configuracion (no se pregunta en cada tramo).
;; Persistido en el dibujo igual que URB_DRAWING_ID (urb:config-read/write).
(defun mp:network-fill-reference-command (/ current choice)
  (setq current (urb:safe-string (urb:config-read "MP_TRAMO_RELLENO_MODO") "Terreno"))
  (prompt
    (strcat "\nReferencia de relleno actual para tramos de red (sanitario/pluvial): "
      current "."))
  (initget "Terreno Subrasante")
  (setq choice
    (getkword
      (strcat "\nNueva referencia [Terreno/Subrasante_via] <" current ">: ")))
  (if (null choice) (setq choice current))
  (urb:config-write "MP_TRAMO_RELLENO_MODO" choice)
  (prompt
    (strcat "\nQuedo configurado: " choice
      (if (= choice "Subrasante")
        ". Al crear un tramo a gravedad se pedira seleccionar la via de referencia."
        ". El relleno vuelve a calcularse hasta el terreno natural (como siempre).")))
  (princ)
)

;; 2026-08-04: recalculo en lote de tramos ya existentes contra la
;; referencia de relleno ACTUAL (MP_TRAMO_RELLENO_MODO). Cambiar la
;; configuracion no actualiza solos los tramos ya creados (el modo se lee
;; una sola vez al crearlos, ver mp:insert-tramo-forced); este comando
;; recorre todos los tramos a gravedad del dibujo y vuelve a llamar
;; mp:sync-tramo-values (via mp:update-block-after-edit) para cada uno.
;; En modo Subrasante pide la via por cada tramo (nentsel/entsel no se
;; puede automatizar de forma confiable: podria haber mas de una via
;; candidata sobre un mismo tramo), igual que al crearlo. Si el usuario
;; cancela la seleccion de un tramo puntual, ese tramo se deja como estaba
;; (no se pisa con un calculo a terreno natural sin que lo pida).
(defun mp:recalc-tramos-earthworks-command
  (/ ss i en obj bname atts base doc undo-open modo-relleno
   found updated skipped ref *error*)
  (vl-load-com)
  (setq doc (vla-get-ActiveDocument (vlax-get-acad-object)))
  (defun *error* (message)
    (setq *mp-tramo-road-ref* nil)
    (if undo-open
      (progn (vl-catch-all-apply 'vla-EndUndoMark (list doc)) (setq undo-open nil)))
    (if (and message (not (member message '("Function cancelled" "quit / exit abort"))))
      (prompt (strcat "\nError al recalcular tramos: " message)))
    (princ))
  (setq modo-relleno (urb:safe-string (urb:config-read "MP_TRAMO_RELLENO_MODO") "Terreno"))
  (prompt (strcat "\nReferencia de relleno actual: " modo-relleno "."))
  (setq ss (ssget "X" '((0 . "INSERT"))))
  (setq found 0 updated 0 skipped 0)
  (if ss
    (progn
      (vla-StartUndoMark doc)
      (setq undo-open T)
      (setq i 0)
      (while (< i (sslength ss))
        (setq en (ssname ss i))
        (setq obj (vlax-ename->vla-object en))
        (setq bname (vla-get-EffectiveName obj))
        (if (mp:is-cant-blockname bname)
          (progn
            (setq atts (mp:att-alist en))
            (setq base (mp:infer-base bname atts))
            (if (and (/= base "") (mp:gravity-tramo-p base))
              (progn
                (setq found (1+ found))
                (setq *mp-tramo-road-ref* nil)
                (setq ref T)
                (if (urb:string-equal-p modo-relleno "Subrasante")
                  (progn
                    (prompt
                      (strcat "\nTramo " (mp:getval "ETIQUETA" atts "(sin etiqueta)") ":"))
                    (setq ref (mp:select-road-subrasante-reference))
                    (setq *mp-tramo-road-ref* ref)))
                (if ref
                  (progn
                    (mp:update-block-after-edit en nil)
                    (setq updated (1+ updated)))
                  (setq skipped (1+ skipped)))
                (setq *mp-tramo-road-ref* nil)))))
        (setq i (1+ i)))
      (vla-Regen doc 1)
      (vl-catch-all-apply 'vla-EndUndoMark (list doc))
      (setq undo-open nil)))
  (prompt
    (strcat "\nRecalculo terminado. Tramos a gravedad encontrados: " (itoa found)
      " | Actualizados: " (itoa updated)
      (if (> skipped 0) (strcat " | Omitidos (sin via seleccionada): " (itoa skipped)) "")))
  (princ))

;; referencia opcional de subrasante (ver mp:tramo-depth-profile
;; y *mp-tramo-road-ref*). Reusa el mismo mecanismo de seleccion/lectura de
;; rasante que ya usa el anden (urb:select-anden-road-grade), pero agrega la
;; PROFUNDIDAD DEL PERFIL de la via para poder restarla y llegar a la
;; subrasante (bajo la estructura de pavimento), no solo a la rasante.
(defun mp:select-road-subrasante-reference
  (/ selected road data mov axis axis-handle via-id records c0 c1 span profile depth)
  (setq selected (entsel "\nSeleccione la via que define la subrasante: "))
  (if selected (setq road (urb:road-parent-from-entity (car selected))))
  (if (and road (setq data (urb:get-xdata-strings road "URB_VIA")))
    (progn
      (setq profile (urb:safe-string (if (> (length data) 4) (nth 4 data) nil) ""))
      (setq depth (urb:road-profile-depth profile))
      (setq via-id (if (> (length data) 22) (nth 22 data) ""))
      (setq axis-handle
        (if (> (length data) 5) (urb:safe-string (nth 5 data) "") ""))
      ;; or de AutoLISP devuelve T, no el valor -- cadena if explicita
      (setq axis (if (/= axis-handle "") (handent axis-handle) nil))
      (if (and axis (not (urb:curve-entity-p axis))) (setq axis nil))
      (if (and (null axis) (/= via-id ""))
        (setq axis (urb:cached-road-axis via-id)))
      (if (and axis (not (urb:curve-entity-p axis))) (setq axis nil))
      (if (not axis) (setq axis (urb:select-or-draw-road-axis "Existente")))
      (setq mov (urb:road-movement-data road))
      (setq records (urb:road-design-grade-records road data))
      (if (not (urb:grade-records-valid-p records)) (setq records nil))
      (setq span
        (atof
          (urb:safe-string
            (if (> (length data) 18) (nth 18 data) nil) "0")))
      (if (and (null records) mov (> (length mov) 8))
        (progn
          (setq c0 (urb:parse-real (nth 7 mov)))
          (setq c1 (urb:parse-real (nth 8 mov)))
          (if (and c0 c1 (> span 1e-6))
            (setq records (list (list 0.0 c0) (list span c1))))))
      (setq axis-start
        (atof
          (urb:safe-string
            (if (> (length data) 21) (nth 21 data) nil) "0")))
      (cond
        ((not (and depth (> depth 0.0)))
          (prompt
            (strcat "\nEl perfil " profile " de esa via no tiene profundidad definida; no se puede calcular subrasante."))
          nil)
        ((and axis records)
          (list axis records axis-start span
            (urb:safe-string (if (> (length data) 12) (nth 12 data) nil) "Inicio")
            "LOCAL" depth))
        (T
          (prompt "\nLa via seleccionada no tiene rasante calculada.")
          nil)))
    (progn (prompt "\nEl objeto seleccionado no es una via cuantificable.") nil))
)

(defun mp:subrasante-at-point
  (point reference / axis records axis-start span direction depth
   closest raw-distance station zaxis)
  (setq axis (nth 0 reference) records (nth 1 reference)
        axis-start (nth 2 reference) span (nth 3 reference)
        direction (nth 4 reference) depth (nth 6 reference))
  (setq closest
    (vl-catch-all-apply 'vlax-curve-getClosestPointTo (list axis point)))
  (if (vl-catch-all-error-p closest)
    nil
    (progn
      (setq raw-distance
        (vl-catch-all-apply 'vlax-curve-getDistAtPoint (list axis closest)))
      (if (vl-catch-all-error-p raw-distance)
        nil
        (progn
          (setq station
            (if (urb:string-equal-p direction "Final")
              (- (+ axis-start span) raw-distance)
              (- raw-distance axis-start)))
          (setq zaxis (urb:cota-at-axis-distance station records))
          (if zaxis (- zaxis depth) nil)))))
)

;; BUG (2026-08-03, encontrado por el usuario en vivo): las etiquetas
;; reales de cota (MLeader/MText) traen la cota pozo Y la cota clave
;; apiladas en el MISMO objeto, y vla-get-TextString devuelve el texto
;; CRUDO con codigos de formato MTEXT (ej. "\pxt6;{\Fsimplex|c0;2559.63
;; \P2557.83}" -- \P separa las 2 lineas). Intentar parsear ese string
;; completo como un numero mezclaba digitos sueltos de los codigos (el
;; "6" de "pxt6", el "0" de "c0") con la cota real, dando basura como
;; "62556.310" en vez de "2556.31".
;; mp:last-decimal-number busca especificamente numeros CON PUNTO
;; DECIMAL (los codigos de formato solo tienen digitos sueltos, sin
;; punto) y devuelve el ULTIMO -- que es la cota clave, la linea de
;; abajo en la etiqueta apilada, tanto en texto crudo con codigos como
;; en texto plano simple (un TEXT sin formato tambien funciona igual).
(defun mp:last-decimal-number (text / i n c buf best)
  (setq text (mp:safe-str text) n (strlen text) i 1 buf "" best nil)
  (while (<= i n)
    (setq c (substr text i 1))
    (cond
      ((wcmatch c "#") (setq buf (strcat buf c)))
      ((and (= c ".") (> (strlen buf) 0) (not (vl-string-search "." buf)))
        (setq buf (strcat buf c)))
      (T
        (if (and (> (strlen buf) 0) (vl-string-search "." buf)
                 (/= (substr buf (strlen buf) 1) "."))
          (setq best buf))
        (setq buf "")))
    (setq i (1+ i)))
  (if (and (> (strlen buf) 0) (vl-string-search "." buf)
           (/= (substr buf (strlen buf) 1) "."))
    (setq best buf))
  best
)

;; Lee una cota clave directamente de una etiqueta ya dibujada (evita
;; transcribir el numero a mano). nentsel (no entsel) porque estas
;; etiquetas suelen vivir dentro de un xref (ej. el plano de residual).
(defun mp:prompt-clave-from-label (prompt-text / selected ename obj txt clean val)
  (setq selected (nentsel prompt-text))
  (if (not selected)
    nil
    (progn
      (setq ename (car selected))
      (setq obj (vl-catch-all-apply 'vlax-ename->vla-object (list ename)))
      (if (vl-catch-all-error-p obj)
        (progn (prompt "\nNo se pudo leer el objeto seleccionado.") nil)
        (progn
          (setq txt (vl-catch-all-apply 'vla-get-TextString (list obj)))
          (if (vl-catch-all-error-p txt)
            (progn (prompt "\nEl objeto seleccionado no tiene texto legible.") nil)
            (progn
              (setq clean (mp:last-decimal-number txt))
              (setq val (if clean (mp:numeric-real clean) nil))
              (if val
                (progn (prompt (strcat "\nCota leida: " (rtos val 2 3))) val)
                (progn
                  (prompt
                    (strcat "\nNo se encontro un numero valido en el texto seleccionado (\""
                      (mp:safe-str txt) "\")."))
                  nil))))))))
)

(defun mp:tramo-depth-profile
  (surface p1 p2 key-ini key-fin diameter-m bedding n road-ref
   / i frac x y terrain reference subrasante key depth depths max-depth samples)
  ;; Muestrea la superficie a lo largo del tramo (no solo los 2 pozos) porque
  ;; el terreno entre pozos puede no ser perfectamente lineal; con esto el
  ;; ancho de zanja y el volumen de excavacion usan la profundidad real, no
  ;; un promedio que podria subestimar una loma intermedia.
  ;; road-ref (opcional, ver mp:select-road-subrasante-reference): si viene,
  ;; en cada punto se usa min(terreno,subrasante) en vez de solo terreno --
  ;; asi el relleno del tramo no cuenta material que la via va a volver a
  ;; cortar por separado hasta su subrasante.
  (setq *mp-last-tramo-memory-samples* nil
        depths nil max-depth nil samples nil i 0)
  (if (and surface p1 p2 key-ini key-fin (> n 1))
    (repeat (1+ n)
      (setq frac (/ (float i) (float n))
            x (+ (car p1) (* frac (- (car p2) (car p1))))
            y (+ (cadr p1) (* frac (- (cadr p2) (cadr p1))))
            terrain (mp:terrain-elevation-at-point surface (list x y))
            key (+ key-ini (* frac (- key-fin key-ini))))
      (if terrain
        (progn
          (setq reference terrain)
          (if road-ref
            (progn
              (setq subrasante
                (vl-catch-all-apply 'mp:subrasante-at-point (list (list x y) road-ref)))
              (if (and (not (vl-catch-all-error-p subrasante)) subrasante)
                (setq reference (min terrain subrasante)))))
          (setq depth (+ (- reference key) diameter-m bedding)
                depths (cons depth depths)
                samples
                  (cons (list frac reference key depth) samples)
                max-depth (if max-depth (max max-depth depth) depth))))
      (setq i (1+ i))))
  (setq *mp-last-tramo-memory-samples* (reverse samples))
  (list (reverse depths) max-depth))

;; BUG (2026-08-03, mismo patron que distance/length/type/last ya
;; documentados en este archivo): el parametro se llamaba "length" y tapaba
;; la funcion nativa mientras (setq n (length depths)) intentaba usarla --
;; "bad function: 10.0" (el valor de longitud pasado). Nunca se habia
;; ejercitado porque *mp-network-construction-enabled* estaba en nil.
;; Renombrado a total-length.
(defun mp:integrate-trench-volume (depths total-length width / n seg-length i vol)
  (setq n (length depths))
  (if (or (< n 2) (<= total-length 1e-9))
    0.0
    (progn
      (setq seg-length (/ total-length (float (1- n))) vol 0.0 i 0)
      (repeat (1- n)
        (setq vol
          (+ vol
            (* width seg-length
              (/ (+ (nth i depths) (nth (1+ i) depths)) 2.0))))
        (setq i (1+ i)))
      vol)))

(defun mp:store-tramo-memory-samples (tramo samples / serialized item)
  (if (and tramo (listp samples) (> (length samples) 1))
    (progn
      (foreach item samples
        ;; Cada fila contiene solo numeros y cabe holgadamente en una
        ;; cadena XDATA; vl-princ-to-string conserva un formato leible.
        (setq serialized (append serialized (list (vl-princ-to-string item)))))
      (urb:set-xdata-strings tramo "MP_TRAMO_MEMORIA" serialized))
    nil))

(defun mp:read-tramo-memory-samples (tramo / raw text item result valid)
  (setq raw (urb:get-xdata-strings tramo "MP_TRAMO_MEMORIA"))
  (foreach text raw
    (setq item (urb:read-lisp-safe text)
          valid
            (and (listp item) (> (length item) 3)
                 (numberp (nth 0 item)) (numberp (nth 1 item))
                 (numberp (nth 2 item)) (numberp (nth 3 item))))
    (if valid (setq result (append result (list item)))))
  (if (> (length result) 1) result nil))

;; Profundidad normativa de zanja electrica (CODENSA Likinormas CS203/CS207):
;; recubrimiento minimo sobre el banco de ductos de 0.60 m bajo anden o
;; zona verde y 0.80 m bajo calzada, mas la altura del banco. El banco se
;; arma en columnas (mismas columnas que mp:default-trench-width:
;; ceil(sqrt(ductos))), con 0.05 m de separacion entre filas y 0.05 m de
;; base de asiento.
(defun mp:elec-normative-depth (vals ducts duct-d / ubic recub columns filas altura)
  (setq ubic (strcase (mp:safe-str (mp:getval "UBICACION" vals ""))))
  (setq recub (if (vl-string-search "CALZADA" ubic) 0.80 0.60))
  (setq ducts (max 1.0 ducts))
  (setq columns (max 1 (fix (+ (sqrt ducts) 0.999999))))
  (setq filas (max 1 (fix (+ (/ ducts (float columns)) 0.999999))))
  (setq altura (+ 0.05 (* filas duct-d) (* (1- filas) 0.05)))
  (+ recub altura))

(defun mp:default-trench-width
  (base vals depth / diameter ducts columns width minimum diameter-in table-width)
  (if (mp:hydro-tramo-p base)
    (progn
      (setq diameter-in (mp:number-or (mp:getval "DIAMETRO" vals "0") 0.0)
            diameter (* 0.0254 diameter-in)
            table-width
              (if (and (mp:gravity-tramo-p base) depth)
                (mp:pvc-trench-width diameter-in depth)
                nil))
      (if table-width table-width (max 0.60 (+ diameter 0.40))))
    (progn
      (setq diameter (* 0.0254 (mp:number-or (mp:getval "DIAM_DUCTO" vals "0") 0.0))
            ducts (max 1.0 (mp:number-or (mp:getval "DUCTOS" vals "1") 1.0))
            columns (max 1 (fix (+ (sqrt ducts) 0.999999)))
            minimum (if (= base "TRAMO_E_MT") 0.80 0.60)
            width
              (+ 0.30
                (* columns diameter)
                (* (max 0 (1- columns)) 0.05)))
      (max minimum width))))

(defun mp:validate-tramo-values
  (base vals / messages stage substage length-value diameter material
   type-ini type-fin handle-ini handle-fin slope slope-calculated ducts
   free-ducts depth depth-ini depth-fin conductor width bedding endpoint
   endpoint-base actual-type id-ini id-fin diameter-number duct-diameter
   duct-material type-red link-data minimum-width tn-ini tn-fin key-ini key-fin
   terrain-state check-depth)
  (setq stage (mp:getval "ETAPA" vals "")
        substage (mp:getval "SUBETAPA" vals "")
        length-value (mp:number-or (mp:getval "LONGITUD" vals "0") 0.0)
        type-ini (strcase (mp:getval "TIPO_EXTREMO_INI" vals "NINGUNO"))
        type-fin (strcase (mp:getval "TIPO_EXTREMO_FIN" vals "NINGUNO"))
        handle-ini (mp:getval "HANDLE_EXTREMO_INI" vals "")
        handle-fin (mp:getval "HANDLE_EXTREMO_FIN" vals "")
        id-ini
          (mp:getval
            (if (member base '("TRAMO_E_MT" "TRAMO_E_BT_AP"))
              "DESDE" "POZO_INI") vals "")
        id-fin
          (mp:getval
            (if (member base '("TRAMO_E_MT" "TRAMO_E_BT_AP"))
              "HASTA" "POZO_FIN") vals "")
        width (mp:number-or (mp:getval "ANCHO_ZANJA" vals "0") 0.0)
        bedding (mp:number-or (mp:getval "ESPESOR_CAMA" vals "0") 0.0)
        terrain-state
          (strcase (mp:getval "ESTADO_COTA_TN" vals "PENDIENTE")))
  (cond
    ((= terrain-state "SIN_SUPERFICIE")
      (setq messages
        (cons
          (strcat "No se encontro la superficie "
            *mp-terrain-surface-name*) messages)))
    ((= terrain-state "FUERA_SUPERFICIE")
      (setq messages
        (cons "Los extremos estan fuera de la superficie de terreno" messages)))
    ((= terrain-state "PARCIAL")
      (setq messages
        (cons "Solo se obtuvo la cota de terreno de un extremo" messages))))
  (if (= stage "") (setq messages (cons "Falta la etapa" messages)))
  (if (= substage "") (setq messages (cons "Falta la subetapa" messages)))
  (if (<= length-value 1e-9)
    (setq messages (cons "La longitud no es valida" messages)))
  (if (and (/= type-ini "NINGUNO") (= handle-ini ""))
    (setq messages (cons "El extremo inicial no esta vinculado" messages)))
  (if (and (/= type-fin "NINGUNO") (= handle-fin ""))
    (setq messages (cons "El extremo final no esta vinculado" messages)))
  (if (and (= type-ini "NINGUNO") (/= handle-ini ""))
    (setq messages (cons "El extremo inicial tiene vinculo pero tipo NINGUNO" messages)))
  (if (and (= type-fin "NINGUNO") (/= handle-fin ""))
    (setq messages (cons "El extremo final tiene vinculo pero tipo NINGUNO" messages)))
  (if (and (/= type-ini "NINGUNO") (= id-ini ""))
    (setq messages (cons "Falta el identificador del extremo inicial" messages)))
  (if (and (/= type-fin "NINGUNO") (= id-fin ""))
    (setq messages (cons "Falta el identificador del extremo final" messages)))
  (if (and (/= handle-ini "") (null (handent handle-ini)))
    (setq messages (cons "El vinculo del extremo inicial esta roto" messages)))
  (if (and (/= handle-fin "") (null (handent handle-fin)))
    (setq messages (cons "El vinculo del extremo final esta roto" messages)))
  (foreach link-data (list (list handle-ini type-ini "inicial")
                            (list handle-fin type-fin "final"))
    (if (and (/= (car link-data) "")
             (setq endpoint (handent (car link-data))))
      (progn
        (setq endpoint-base (mp:point-reference-base endpoint)
              actual-type
                (strcase
                  (mp:safe-str (mp:endpoint-type-for-base endpoint-base))))
        (if (not (mp:endpoint-compatible-p base endpoint-base))
          (setq messages
            (cons
              (strcat "El extremo " (caddr link-data)
                " apunta a un elemento incompatible") messages)))
        (if (/= actual-type (cadr link-data))
          (setq messages
            (cons
              (strcat "El tipo declarado del extremo " (caddr link-data)
                " no coincide con el elemento vinculado") messages))))))
  (if (and (/= handle-ini "") (= (strcase handle-ini) (strcase handle-fin)))
    (setq messages (cons "Los dos extremos apuntan al mismo elemento" messages)))
  (if (<= width 1e-9)
    (setq messages (cons "Falta el ancho de zanja" messages)))
  ;; PROFUNDIDAD_MEDIA ya viene calculada en vals (mp:derive-tramo-values la
  ;; llena antes de validar); se usa para elegir el rango correcto de la
  ;; tabla de anchos en vez de asumir el rango mas superficial.
  (setq check-depth (mp:numeric-real (mp:getval "PROFUNDIDAD_MEDIA" vals "")))
  ;; BUG (2026-08-03): mp:default-trench-width con la formula generica
  ;; (max 0.60 (+ diametro 0.40)) casi nunca da un numero limpio a 2
  ;; decimales (ej. 8" -> 0.6032). ANCHO_ZANJA se guarda redondeado a 2
  ;; decimales (rtos ... 2 2), pero minimum-width se recalculaba aqui SIN
  ;; redondear -- la comparacion fallaba (0.60 < 0.6032) aunque el ancho
  ;; guardado fuera exactamente el minimo real. Se redondea minimum-width
  ;; igual que se redondeo width al guardarlo, para comparar a la misma
  ;; precision.
  (setq minimum-width (atof (rtos (mp:default-trench-width base vals check-depth) 2 2)))
  (if (< width (- minimum-width 1e-6))
    (setq messages
      (cons
        (strcat "El ancho de zanja es menor al minimo geometrico de "
          (rtos minimum-width 2 2) " m") messages)))
  (if (< bedding 0.0)
    (setq messages (cons "El espesor de cama no puede ser negativo" messages)))
  (if (mp:hydro-tramo-p base)
    (progn
      (setq diameter (mp:getval "DIAMETRO" vals "")
            diameter-number (mp:numeric-real diameter)
            material (mp:getval "MATERIAL" vals "")
            tn-ini (mp:numeric-real (mp:getval "COTA_TN_INI" vals ""))
            tn-fin (mp:numeric-real (mp:getval "COTA_TN_FIN" vals ""))
            key-ini (mp:numeric-real (mp:getval "COTA_CLAVE_INI" vals ""))
            key-fin (mp:numeric-real (mp:getval "COTA_CLAVE_FIN" vals ""))
            depth-ini (mp:numeric-real (mp:getval "PROFUNDIDAD_INI" vals ""))
            depth-fin (mp:numeric-real (mp:getval "PROFUNDIDAD_FIN" vals "")))
      (if (or (null diameter-number) (<= diameter-number 0.0))
        (setq messages (cons "Falta un diametro valido" messages)))
      (if (= material "") (setq messages (cons "Falta el material" messages)))
      (if (or (null depth-ini) (<= depth-ini 0.0)
              (null depth-fin) (<= depth-fin 0.0))
        (setq messages
          (cons "Faltan cotas completas para calcular la profundidad" messages)))
      (if (and tn-ini key-ini (<= tn-ini key-ini))
        (setq messages
          (cons "La cota de terreno inicial debe estar sobre la clave" messages)))
      (if (and tn-fin key-fin (<= tn-fin key-fin))
        (setq messages
          (cons "La cota de terreno final debe estar sobre la clave" messages)))
      ;; 2026-09-01: PLUVIAL sin cotas de clave = modo NORMATIVO (como las
      ;; redes secas) -- no se exige pendiente ni cotas; la profundidad ya
      ;; quedo por reglamentacion en mp:derive-tramo-values.
      (if (and (mp:gravity-tramo-p base)
               (not (and (= base "TRAMO_ALLUVIAS")
                         (null key-ini) (null key-fin))))
        (progn
          (setq slope (mp:numeric-real (mp:getval "PENDIENTE" vals ""))
                slope-calculated
                  (mp:numeric-real
                    (mp:getval "PENDIENTE_CALCULADA" vals "")))
          (if (null slope)
            (setq messages (cons "Falta la pendiente" messages)))
          (if (and slope (<= slope 0.0))
            (setq messages (cons "La pendiente debe bajar del inicio al final" messages)))
          (if (null slope-calculated)
            (setq messages (cons "Faltan cotas de clave para calcular la pendiente" messages)))
          (if (and slope-calculated (<= slope-calculated 0.0))
            (setq messages (cons "Las cotas no producen flujo descendente" messages)))
          (if (and slope slope-calculated (> (abs (- slope slope-calculated)) 0.05))
            (setq messages
              (cons "La pendiente digitada no coincide con las cotas" messages))))))
    (progn
      (setq ducts (mp:number-or (mp:getval "DUCTOS" vals "0") 0.0)
            free-ducts (mp:number-or (mp:getval "LIBRES" vals "0") 0.0)
            depth (mp:number-or (mp:getval "PROFUNDIDAD" vals "0") 0.0)
            conductor (mp:getval "CONDUCTOR" vals
              (mp:getval "CONDUCTORES" vals ""))
            duct-diameter
              (mp:numeric-real (mp:getval "DIAM_DUCTO" vals ""))
            duct-material (mp:getval "MATERIAL_DUCTO" vals "")
            type-red (strcase (mp:getval "TIPO_RED" vals "")))
      (if (<= ducts 0.0) (setq messages (cons "Falta la cantidad de ductos" messages)))
      (if (/= ducts (fix ducts))
        (setq messages (cons "La cantidad de ductos debe ser entera" messages)))
      (if (or (< free-ducts 0.0) (> free-ducts ducts))
        (setq messages (cons "Los ductos libres no son coherentes" messages)))
      (if (/= free-ducts (fix free-ducts))
        (setq messages (cons "La cantidad de ductos libres debe ser entera" messages)))
      (if (<= depth 0.0) (setq messages (cons "Falta la profundidad" messages)))
      (if (and (> depth 0.0) (<= depth bedding))
        (setq messages
          (cons "La profundidad debe ser mayor que el espesor de cama" messages)))
      (if (or (null duct-diameter) (<= duct-diameter 0.0))
        (setq messages (cons "Falta un diametro de ducto valido" messages)))
      (if (= duct-material "")
        (setq messages (cons "Falta el material del ducto" messages)))
      (if (= conductor "") (setq messages (cons "Falta el conductor" messages)))
      (if (and (= base "TRAMO_E_MT") (/= type-red "MT"))
        (setq messages (cons "El tipo de red debe ser MT" messages)))
      (if (and (= base "TRAMO_E_BT_AP")
               (not (member type-red '("BT" "AP"))))
        (setq messages (cons "El tipo de red debe ser BT o AP" messages)))))
  (setq messages (reverse messages))
  (setq vals
    (mp:alist-set vals "CONTROL_ESTADO" (if messages "REVISAR" "OK")))
  (mp:alist-set vals "CONTROL_MENSAJES" (mp:join-messages messages)))

;; Figura 4 del estudio de suelos (tuberias flexibles, K=0.083): la cama
;; bajo el tubo es Bc/4 (Bc = diametro exterior), con minimo 0.10 m y
;; maximo 0.15 m. Antes del 2026-08-03 el codigo usaba 0.10 m fijo para
;; cualquier diametro -- correcto solo para el extremo inferior del rango.
(defun mp:pipe-bedding-thickness (diameter-m)
  (min 0.15 (max 0.10 (/ diameter-m 4.0)))
)

;; 2026-08-14 v4.24.0 -- Modelo de cimentacion 2 (tuberias flexibles) del
;; APU de alcantarillado: la zanja NO se rellena con un solo material.
;; De abajo hacia arriba: cama + atraque del tubo + relleno inicial hasta
;; *mp-triturado-sobre-clave* sobre la clave en MATERIAL TRITURADO tamano
;; grava; de ahi hasta la rasante, RECEBO compactado (o material de la
;; excavacion si no pasan vias sobre el corredor -- decision de
;; presupuesto, aqui se reporta el volumen como recebo). El RELLENO_M3
;; historico (exc - cama - tubo) se conserva intacto por compatibilidad:
;; TRITURADO_M3 + RECEBO_M3 + CAMA_M3 = RELLENO_M3 + CAMA_M3 = exc - tubo.
;; Entibado del APU por tipologia: <=3 m y >3 m de profundidad, medido en
;; m2 de pared de zanja (2 caras x longitud x profundidad), repartido por
;; el perfil muestreado cuando existe.
(setq *mp-triturado-sobre-clave* 0.30)
(setq *mp-entibado-umbral* 3.0)

;; Integra ambas caras y divide en los cruces de profundidad 0/2/3 m.
;; Clasificar toda la longitud por su profundidad media pierde tipologias.
(defun mp:entibado-segment-areas (lng d1 d2 / cuts h u lo hi dm ar out idx)
  (setq cuts '(0.0 1.0) out '(0.0 0.0 0.0))
  (if (> (abs (- d2 d1)) 1e-12)
    (foreach h '(0.0 2.0 3.0)
      (setq u (/ (- h d1) (- d2 d1)))
      (if (and (> u 0.0) (< u 1.0)) (setq cuts (cons u cuts)))))
  (setq cuts (vl-sort cuts '<))
  (while (cdr cuts)
    (setq lo (car cuts) hi (cadr cuts)
          dm (+ d1 (* (- d2 d1) (/ (+ lo hi) 2.0)))
          ar (* 2.0 (max 0.0 lng) (- hi lo) (max 0.0 dm))
          idx (cond ((<= dm 2.0) 0) ((<= dm 3.0) 1) (T 2)))
    (setq out (list (+ (car out) (if (= idx 0) ar 0.0))
                    (+ (cadr out) (if (= idx 1) ar 0.0))
                    (+ (caddr out) (if (= idx 2) ar 0.0))) cuts (cdr cuts)))
  out)

(defun mp:derive-tramo-values
  (base p1 p2 vals
   / length-2d length-3d length-center-2d length-center-3d length-value
   gaps mode diameter-m diameter-in ducts width
   bedding bedding-raw replacement-raw replacement-width tn-ini tn-fin key-ini key-fin
   cover-ini cover-fin depth-ini depth-fin depth-mean slope-calculated
   entered-slope excavation bedding-volume element-volume fill surplus
   replacement duct-diameter surface depth-profile depths max-depth-sampled
   critical-depth sample-count env-height env-vol triturado recebo
   ent-le3 ent-gt3 seg-len seg-index d1 d2 dmid ent-parts
   recub-e envb-e arena-e baseg-e)
  (setq *mp-last-tramo-memory-samples* nil)
  (setq length-center-2d (if (and p1 p2) (mp:distance-2d p1 p2)
                    (mp:number-or (mp:getval "LONGITUD_2D" vals
                      (mp:getval "LONGITUD" vals "0")) 0.0))
        length-center-3d (if (and p1 p2) (distance p1 p2)
                    (mp:number-or (mp:getval "LONGITUD_3D" vals
                      (mp:getval "LONGITUD" vals "0")) 0.0))
        gaps (mp:tramo-end-gaps base vals length-center-2d)
        length-value
          (max 0.0 (- length-center-2d (car gaps) (cadr gaps)))
        length-2d length-value
        length-3d
          (if (> length-center-2d 1e-9)
            (* length-center-3d (/ length-value length-center-2d))
            length-value)
        mode "PLANTA"
        width (mp:number-or (mp:getval "ANCHO_ZANJA" vals "") 0.0))
  ;; diametro adelantado (se vuelve a leer mas abajo dentro de la rama
  ;; hidraulica, sin costo, para no reordenar el resto de la funcion) --
  ;; solo para poder resolver la cama por Bc/4 antes de que se necesite.
  (if (mp:hydro-tramo-p base)
    (setq diameter-in (mp:number-or (mp:getval "DIAMETRO" vals "0") 0.0)
          diameter-m (* 0.0254 diameter-in)))
  (setq bedding-raw (mp:getval "ESPESOR_CAMA" vals ""))
  (setq bedding
    (max 0.0
      (if (/= (vl-string-trim " " (mp:safe-str bedding-raw)) "")
        (mp:number-or bedding-raw 0.10)
        (if diameter-m (mp:pipe-bedding-thickness diameter-m) 0.10))))
  (if (mp:hydro-tramo-p base)
    (progn
      (setq diameter-in (mp:number-or (mp:getval "DIAMETRO" vals "0") 0.0)
            diameter-m (* 0.0254 diameter-in)
            tn-ini (mp:numeric-real (mp:getval "COTA_TN_INI" vals ""))
            tn-fin (mp:numeric-real (mp:getval "COTA_TN_FIN" vals ""))
            key-ini (mp:numeric-real (mp:getval "COTA_CLAVE_INI" vals ""))
            key-fin (mp:numeric-real (mp:getval "COTA_CLAVE_FIN" vals "")))
      (if (and tn-ini key-ini)
        (setq cover-ini (- tn-ini key-ini)
              depth-ini (+ cover-ini diameter-m bedding)))
      (if (and tn-fin key-fin)
        (setq cover-fin (- tn-fin key-fin)
              depth-fin (+ cover-fin diameter-m bedding)))
      (setq depth-mean
        (cond
          ((and depth-ini depth-fin) (/ (+ depth-ini depth-fin) 2.0))
          (depth-ini depth-ini)
          (depth-fin depth-fin)
          (T 0.0)))
      ;; 2026-09-02 (pedido del usuario): ACUEDUCTO sin cotas de diseno --
      ;; excavacion NORMATIVA como las electricas: RAS 0330 (Res. 0330/
      ;; 2017 art. 89): recubrimiento minimo 1.0 m sobre la clave en zonas
      ;; vehiculares. Zanja = 1.0 + diametro + cama.
      ;; 2026-09-01 (2a ronda): tambien PLUVIAL sin cotas -- recubrimiento
      ;; normativo 1.2 m a clave (RAS 0330 alcantarillados bajo calzada).
      ;; (Desde v4.71 el libro pluvial ya NO usa bandas Hex: la
      ;; PROFUNDIDAD_MEDIA alimenta la zanja/entibados como en sanitario.)
      (if (<= depth-mean 1e-9)
        (cond
          ((= base "TRAMO_ACUEDUCTO")
            (setq depth-ini (+ 1.0 diameter-m bedding)
                  depth-fin depth-ini
                  depth-mean depth-ini))
          ((= base "TRAMO_ALLUVIAS")
            (setq depth-ini (+ 1.2 diameter-m bedding)
                  depth-fin depth-ini
                  depth-mean depth-ini))))
      ;; Muestreo de superficie a lo largo del tramo (no solo los 2 pozos):
      ;; la superficie de terreno ya existe en el dibujo, asi que se usa un
      ;; perfil real de profundidad en vez de solo el promedio de extremos,
      ;; que podria subestimar una loma o vaguada intermedia.
      (if (mp:gravity-tramo-p base)
        (progn
          (setq surface (mp:current-terrain-surface))
          (setq sample-count
            (min 200
              (max 2 (fix (+ 0.999999 (/ length-2d 2.50))))))
          (setq depth-profile
            (if (and surface p1 p2 key-ini key-fin)
              (mp:tramo-depth-profile surface p1 p2 key-ini key-fin
                diameter-m bedding sample-count
                (if (boundp '*mp-tramo-road-ref*) *mp-tramo-road-ref* nil))
              (list nil nil)))
          (setq depths (car depth-profile)
                max-depth-sampled (cadr depth-profile))))
      (setq critical-depth (mp:max-nonnil (list depth-ini depth-fin max-depth-sampled)))
      (if (and key-ini key-fin (> length-2d 1e-9))
        (setq slope-calculated (* 100.0 (/ (- key-ini key-fin) length-2d))))
      (setq entered-slope (mp:numeric-real (mp:getval "PENDIENTE" vals "")))
      (if (and (null entered-slope) slope-calculated)
        (setq vals (mp:alist-set vals "PENDIENTE" (rtos slope-calculated 2 3))))
      (setq vals (mp:alist-set vals "PROFUNDIDAD_INI"
                   (if depth-ini (rtos depth-ini 2 3) ""))
            vals (mp:alist-set vals "PROFUNDIDAD_FIN"
                   (if depth-fin (rtos depth-fin 2 3) ""))
            vals (mp:alist-set vals "PROFUNDIDAD_MEDIA"
                   (if (> depth-mean 0.0) (rtos depth-mean 2 3) ""))
            vals (mp:alist-set vals "PENDIENTE_CALCULADA"
                   (if slope-calculated (rtos slope-calculated 2 3) ""))
            element-volume (* pi 0.25 diameter-m diameter-m length-value))
      (if (<= width 1e-9)
        (setq width (mp:default-trench-width base vals critical-depth))))
    (progn
      (setq ducts (max 0.0 (mp:number-or (mp:getval "DUCTOS" vals "0") 0.0))
            duct-diameter
              (* 0.0254 (mp:number-or (mp:getval "DIAM_DUCTO" vals "0") 0.0))
            element-volume
              (* ducts pi 0.25 duct-diameter duct-diameter length-value))
      ;; Tramos electricos: profundidad SIEMPRE normativa (CODENSA) a
      ;; partir de la ubicacion (anden/calzada) y el banco de ductos.
      ;; Antes dependia de un dato manual que casi nunca se digitaba y la
      ;; excavacion salia en 0.
      (setq depth-mean
        (if (and (> ducts 0.0) (> duct-diameter 0.0))
          (mp:elec-normative-depth vals ducts duct-diameter)
          (max 0.0 (mp:number-or (mp:getval "PROFUNDIDAD" vals "0") 0.0))))
      (setq depth-ini depth-mean
            depth-fin depth-mean)
      (setq vals (mp:alist-set vals "PROFUNDIDAD"
                   (if (> depth-mean 0.0) (rtos depth-mean 2 3) "")))
      (setq vals (mp:alist-set vals "PROFUNDIDAD_INI"
                   (if (> depth-mean 0.0) (rtos depth-mean 2 3) ""))
            vals (mp:alist-set vals "PROFUNDIDAD_FIN"
                   (if (> depth-mean 0.0) (rtos depth-mean 2 3) ""))
            vals (mp:alist-set vals "PROFUNDIDAD_MEDIA"
                   (if (> depth-mean 0.0) (rtos depth-mean 2 3) ""))
            vals (mp:alist-set vals "PENDIENTE_CALCULADA" ""))
      (if (<= width 1e-9) (setq width (mp:default-trench-width base vals nil)))))
  ;; Vacio hereda el ancho de zanja; cero explicito significa que no hay
  ;; reposicion superficial (por ejemplo, excavacion en zona verde).
  (setq replacement-raw (mp:getval "ANCHO_REPOSICION" vals "")
        replacement-width
          (if (= (vl-string-trim " " replacement-raw) "")
            width
            (max 0.0 (mp:number-or replacement-raw 0.0))))
  (setq vals (mp:alist-set vals "LONGITUD" (rtos length-value 2 2))
        vals (mp:alist-set vals "LONGITUD_2D" (rtos length-2d 2 2))
        vals (mp:alist-set vals "LONGITUD_3D" (rtos length-3d 2 2))
        vals (mp:alist-set vals "LONGITUD_CENTROS_2D"
               (rtos length-center-2d 2 2))
        vals (mp:alist-set vals "LONGITUD_CENTROS_3D"
               (rtos length-center-3d 2 2))
        vals (mp:alist-set vals "MODO_LONGITUD" mode)
        vals (mp:alist-set vals "ANCHO_ZANJA" (rtos width 2 2))
        vals (mp:alist-set vals "ESPESOR_CAMA" (rtos bedding 2 2))
        vals (mp:alist-set vals "ANCHO_REPOSICION" (rtos replacement-width 2 2)))
  (if *mp-network-construction-enabled*
    (progn
      (setq excavation
              (cond
                ((and depths (> (length depths) 1))
                  (mp:integrate-trench-volume depths length-value width))
                ((> depth-mean 0.0) (* length-value width depth-mean))
                (T 0.0))
            bedding-volume (* length-value width bedding)
            fill (max 0.0 (- excavation bedding-volume element-volume))
            ;; 5.7.14: el relleno es recebo importado -> sale todo lo excavado
            surplus excavation
            replacement (* length-value replacement-width)
            vals (mp:alist-set vals "EXCAVACION_M3" (rtos excavation 2 3))
            vals (mp:alist-set vals "CAMA_M3" (rtos bedding-volume 2 3))
            vals (mp:alist-set vals "VOLUMEN_ELEMENTO_M3" (rtos element-volume 2 3))
            vals (mp:alist-set vals "RELLENO_M3" (rtos fill 2 3))
            vals (mp:alist-set vals "SOBRANTE_M3" (rtos surplus 2 3))
            vals (mp:alist-set vals "REPOSICION_M2" (rtos replacement 2 3))
            vals (mp:alist-set vals "METODO_CANTIDADES"
                   (strcat
                     (if depths "PERFIL_MUESTREADO" "PRELIMINAR_GEOMETRICO")
                     (if (and (boundp '*mp-tramo-road-ref*) *mp-tramo-road-ref*)
                       " (ref. subrasante via)" ""))))
      ;; Electricas: desglose del relleno con los MISMOS materiales del
      ;; presupuesto (2026-08-26): arena limpia envolviendo el banco hasta
      ;; el recubrimiento normativo (0.60 anden / 0.80 calzada) y base
      ;; granular clase B de ahi a la rasante. Misma formula que
      ;; urb:ppto-rows-tramos para que el panel y las filas coincidan.
      (if (and (not (mp:hydro-tramo-p base)) (> excavation 1e-9))
        (progn
          (setq recub-e
            (if (vl-string-search "CALZADA"
                  (strcase (mp:getval "UBICACION" vals "")))
              0.80 0.60))
          (setq envb-e (max 0.0 (* (- depth-mean recub-e) width length-value)))
          (setq arena-e (max 0.0 (- (min excavation envb-e) element-volume)))
          (setq baseg-e (max 0.0 (- excavation envb-e)))
          (setq vals (mp:alist-set vals "ARENA_M3" (rtos arena-e 2 3))
                vals (mp:alist-set vals "BASE_GRANULAR_M3" (rtos baseg-e 2 3)))))
      ;; Cimentacion (modelo 2) y entibado: TODOS los tramos humedos
      ;; (2026-09-07, reclamo "falta el MT completo de tuberia ACU"):
      ;; gravedad (san/plu) cimienta en GRAVILLA con el colchon
      ;; *mp-triturado-sobre-clave*; presion (ACU) cimienta en ARENA DE
      ;; PENA con 0.10 m sobre la clave (RAS 0330). El export nombra el
      ;; APU segun la red (gravilla vs arena), aqui solo cambia la
      ;; altura de la envolvente.
      (if (and (mp:hydro-tramo-p base) (> excavation 1e-9)
               diameter-m (> diameter-m 0.0))
        (progn
          ;; envolvente de cimentacion: cama + tubo + colchon sobre la
          ;; clave, recortada a la excavacion real (zanjas muy someras
          ;; no pueden contener la envolvente completa)
          (setq env-height
                  (+ bedding diameter-m
                     (if (mp:gravity-tramo-p base)
                       *mp-triturado-sobre-clave* 0.10))
                env-vol (min excavation
                          (* length-value width env-height))
                triturado (max 0.0 (- env-vol element-volume))
                recebo (max 0.0 (- excavation env-vol)))
          ;; entibado por tipologia: reparte 2 caras x ds x profundidad
          ;; segmento a segmento del perfil muestreado; sin perfil, toda la
          ;; pared va a la tipologia de la profundidad media.
          (setq ent-le3 0.0 ent-gt3 0.0)
          (if (and depths (> (length depths) 1))
            (progn
              (setq seg-len
                      (/ length-value (float (1- (length depths))))
                    seg-index 0)
              (repeat (1- (length depths))
                (setq d1 (nth seg-index depths)
                      d2 (nth (1+ seg-index) depths)
                      ent-parts (mp:entibado-segment-areas seg-len d1 d2)
                      ent-le3 (+ ent-le3 (car ent-parts) (cadr ent-parts))
                      ent-gt3 (+ ent-gt3 (caddr ent-parts)))
                (setq seg-index (1+ seg-index))))
            (if (> depth-mean 0.0)
              (progn
                (setq ent-parts (mp:entibado-segment-areas length-value
                  (if depth-ini depth-ini depth-mean) (if depth-fin depth-fin depth-mean)))
                (setq ent-le3 (+ (car ent-parts) (cadr ent-parts))
                      ent-gt3 (caddr ent-parts)))))
          (setq vals (mp:alist-set vals "TRITURADO_M3" (rtos triturado 2 3))
                vals (mp:alist-set vals "RECEBO_M3" (rtos recebo 2 3))
                vals (mp:alist-set vals "ENTIBADO_LE3_M2" (rtos ent-le3 2 3))
                vals (mp:alist-set vals "ENTIBADO_GT3_M2" (rtos ent-gt3 2 3))))
        (setq vals (mp:alist-set vals "TRITURADO_M3" "")
              vals (mp:alist-set vals "RECEBO_M3" "")
              vals (mp:alist-set vals "ENTIBADO_LE3_M2" "")
              vals (mp:alist-set vals "ENTIBADO_GT3_M2" ""))))
    (setq vals (mp:alist-set vals "EXCAVACION_M3" "")
          vals (mp:alist-set vals "CAMA_M3" "")
          vals (mp:alist-set vals "VOLUMEN_ELEMENTO_M3" "")
          vals (mp:alist-set vals "RELLENO_M3" "")
          vals (mp:alist-set vals "SOBRANTE_M3" "")
          vals (mp:alist-set vals "REPOSICION_M2" "")
          vals (mp:alist-set vals "TRITURADO_M3" "")
          vals (mp:alist-set vals "RECEBO_M3" "")
          vals (mp:alist-set vals "ENTIBADO_LE3_M2" "")
          vals (mp:alist-set vals "ENTIBADO_GT3_M2" "")
          vals
            (mp:alist-set vals "METODO_CANTIDADES"
              "PENDIENTE_PARAMETROS")))
  (mp:validate-tramo-values base vals))

;; Recorte por CADA extremo hasta la cara del pozo/caja. Desde 4.75.0 la
;; longitud de presupuesto es tambien cara-a-cara; se conservan aparte las
;; longitudes centro-a-centro para trazabilidad.
(defun mp:point-base-gap (point-base)
  (cond
    ((member point-base '("POZO_SANITARIO" "POZO_PLUVIAL")) 0.60)
    ((= point-base "SUMIDERO") 0.35)
    ((= point-base "CAMARA_CS280") 1.00)
    ((= point-base "CAMARA_CS276") 1.00)
    ((member point-base '("CAMARA_CS274" "CAMARA_CS275")) 0.54)
    ((= point-base "CAJA_BARRAJE_CS281") 2.00)
    ;; En accesorios de acueducto la linea llega al eje y el simbolo
    ;; abierto la cubre; no se descuenta longitud.
    (T 0.0)))

(defun mp:tramo-end-gap (tramo vals is-final / handle en point-base tipo)
  (setq handle
    (mp:getval
      (if is-final "HANDLE_EXTREMO_FIN" "HANDLE_EXTREMO_INI") vals ""))
  (if (= handle "")
    0.0
    (progn
      (setq en (handent handle))
      (setq point-base
        (if (and en (entget en)) (mp:point-reference-base en) nil))
      (if (or (null point-base) (= point-base ""))
        (progn
          (setq tipo
            (mp:getval
              (if is-final "TIPO_EXTREMO_FIN" "TIPO_EXTREMO_INI")
              vals "NINGUNO"))
          (setq point-base (mp:endpoint-base tramo tipo))))
      (mp:point-base-gap point-base))))

(defun mp:tramo-end-gaps (tramo vals dist / g1 g2 total factor)
  (setq g1 (mp:tramo-end-gap tramo vals nil)
        g2 (mp:tramo-end-gap tramo vals T)
        total (+ g1 g2))
  ;; Tramos muy cortos: conserva al menos 1 cm visible y reparte el recorte
  ;; proporcionalmente, sin producir escalas negativas.
  (if (and (> total 0.0) (> total (- dist 0.01)))
    (progn
      (setq factor (/ (max 0.0 (- dist 0.01)) total))
      (setq g1 (* g1 factor) g2 (* g2 factor))))
  (list g1 g2))

(defun mp:insert-cant-tramo
  (baseb p1 p2 vals / doc ms dist ang blk br vals2 en lay added sync-result
   gaps gap-ini gap-fin p1v distv)
  (vl-load-com)
  ;; La referencia grafica siempre se dibuja en planta. La longitud 3D se
  ;; conserva por separado para trazabilidad, evitando que un desnivel Z
  ;; haga que el bloque sobrepase el extremo final en la vista en planta.
  (setq dist (mp:distance-2d p1 p2)
        ang (angle p1 p2))
  (if (> dist 1e-9)
    (progn
      (setq vals2
        (mp:auto-terrain-values vals p1 p2))
      (setq vals2 (mp:derive-tramo-values baseb p1 p2 vals2))
      (setq vals2
        (mp:alist-set vals2 "BLOQUE_BASE" baseb))
      (setq vals2
        (mp:alist-set vals2 "ETIQUETA" (mp:label-tramo baseb vals2)))
      (setq vals2
        (mp:alist-set vals2 "PENDIENTE_VIS" (mp:pendiente-label vals2)))
      (if (member baseb '("TRAMO_E_MT" "TRAMO_E_BT_AP"))
        (setq vals2
          (mp:alist-set vals2 "LONG_VIS" (mp:long-label vals2))))
      ;; recorte cara-a-cara: el bloque y las cantidades excluyen el area
      ;; ocupada por el pozo/caja; p1-p2 se conserva en LONGITUD_CENTROS_*.
      (setq gaps (mp:tramo-end-gaps baseb vals2 dist)
            gap-ini (car gaps)
            gap-fin (cadr gaps))
      (setq p1v
        (if (> gap-ini 0.0)
          (list (+ (car p1) (* gap-ini (cos ang)))
                (+ (cadr p1) (* gap-ini (sin ang))))
          p1))
      (setq distv (- dist gap-ini gap-fin))
      (setq blk (mp:tramo-block-name baseb distv))
      (if (not (tblsearch "BLOCK" blk))
        (mp:make-cant-tramo-block blk baseb distv vals2))
      (setq added (mp:ensure-block-schema blk baseb T))
      (if (> added 0)
        (setq sync-result
          (vl-catch-all-apply 'vl-cmdf
            (list "_.ATTSYNC" "_N" blk))))
      (setq doc (vla-get-ActiveDocument (vlax-get-acad-object)))
      (setq ms (vla-get-ModelSpace doc))
      (setq br (vla-InsertBlock ms (mp:3d p1v) blk 1.0 1.0 1.0 (float ang)))
      (setq en (vlax-vla-object->ename br))
      (setq lay (mp:vis-layer baseb))
      (if (tblsearch "LAYER" lay) (vla-put-Layer br lay))
      (mp:setatts en vals2)
      (mp:store-tramo-memory-samples en *mp-last-tramo-memory-samples*)
      (setq *mp-last-tramo-memory-samples* nil)
      (vl-catch-all-apply 'urb:attach-memory-reactor-to-block (list en))
      ;; 5.6.1: el tramo recien creado se dibuja encima de todo; los
      ;; simbolos de red vuelven a quedar por encima de la tuberia
      (vl-catch-all-apply 'mp:points-to-top (list nil))
      (princ
        (strcat
          "\nTramo PPTO creado en " lay ": " blk
          " | Cota TN "
          (mp:getval "ESTADO_COTA_TN" vals2 "PENDIENTE") "."))
      en)
    (progn
      (princ "\nNo se creo el tramo: los puntos coinciden.")
      nil)))

;; 2026-09-02 (pedido del usuario: "las cotas de los tramos no estan
;; quedando centradas"): reposiciona las etiquetas visibles de un TRAMO a
;; su sitio de diseno -- el punto del attdef del bloque transformado por
;; la insercion. Rotacion: todas las redes acompanan al tramo (5.6.1).
(defun mp:recenter-tramo-attribs (en / obj ed ip rot bname blk map a tag
                                  item local x y tgt base res flip)
  (setq obj (vlax-ename->vla-object en)
        ed (entget en)
        ip (cdr (assoc 10 ed))
        rot (cdr (assoc 50 ed))
        bname (vla-get-EffectiveName obj)
        base (mp:infer-base bname (mp:att-alist en))
        flip (mp:tramo-text-flipped-p en))
  ;; 2026-09-03 (optimizacion de velocidad): el mapa de attdefs de cada
  ;; DEFINICION se cachea por nombre de bloque -- las definiciones son
  ;; compartidas por longitud, asi que en pasadas masivas (RECENTRA,
  ;; ETIQUETAS) el def se recorre UNA vez, no una por insert.
  (setq map (cdr (assoc bname
    (if (boundp '*mp-recenter-defcache*) *mp-recenter-defcache* nil))))
  (setq blk
    (if map
      nil
      (vl-catch-all-apply 'vla-Item
        (list (vla-get-Blocks (vla-get-ActiveDocument (vlax-get-acad-object)))
              bname))))
  (if (and (null map) (vl-catch-all-error-p blk))
    nil
    (progn
      (if (null map)
        (progn
          (vlax-for item blk
            (if (= (vla-get-ObjectName item) "AcDbAttributeDefinition")
              (setq map
                (cons (list (strcase (vla-get-TagString item))
                            (vl-catch-all-apply 'vlax-get
                              (list item 'TextAlignmentPoint))
                            (vla-get-Rotation item)
                            (vla-get-Alignment item)
                            (vlax-get item 'InsertionPoint))
                  map))))
          (setq *mp-recenter-defcache*
            (cons (cons bname map)
              (if (boundp '*mp-recenter-defcache*)
                *mp-recenter-defcache* nil)))))
      (foreach a (vlax-invoke obj 'GetAttributes)
        (setq tag (strcase (vla-get-TagString a)))
        (if (and (member tag '("ETIQUETA" "PENDIENTE_VIS" "LONG_VIS"))
                 (setq item (assoc tag map)))
          (progn
            (setq local
              (if (and (/= (nth 3 item) 0)
                       (not (vl-catch-all-error-p (nth 1 item))))
                (nth 1 item)
                (nth 4 item)))
            (setq x (car local) y (cadr local))
            ;; 5.6.0 VOLTEADO: el texto se lee al derecho girandolo 180
            ;; grados sobre su propio centro (alineacion centro-medio) y
            ;; cambiando de lado del eje, para que la etiqueta siga
            ;; quedando ARRIBA y la pendiente ABAJO vistas en pantalla.
            (if flip (setq y (- y)))
            (setq tgt
              (list (+ (car ip) (- (* x (cos rot)) (* y (sin rot))))
                    (+ (cadr ip) (+ (* x (sin rot)) (* y (cos rot))))
                    0.0))
            (if (/= (nth 3 item) 0)
              (setq res (vl-catch-all-apply 'vlax-put
                (list a 'TextAlignmentPoint tgt)))
              (setq res (vl-catch-all-apply 'vlax-put
                (list a 'InsertionPoint tgt))))
            ;; 5.6.1 (reporte del usuario: "las cotas de acueducto no estan
            ;; quedando alineadas igual que el resto de tramos, sino
            ;; perpendicular"): ACU tenia aqui una excepcion que forzaba el
            ;; texto a 0 grados. Desde 5.6.0 Apariencia recentra TODOS los
            ;; tramos, asi que cada ACU vertical quedo con el texto
            ;; horizontal. Ahora todas las redes acompanan al tramo; si uno
            ;; queda boca abajo, EDITAR > Voltear texto.
            (vl-catch-all-apply 'vla-put-Rotation
              (list a (+ rot (nth 2 item) (if flip pi 0.0)))))))
      T)))

;; ---------- 5.6.0 voltear el texto de tramos puntuales ----------
;; Pedido del usuario: "hay tramos que el texto quedo boca abajo, pero son
;; tramos en especifico, no todos". La marca vive en XDATA de la
;; REFERENCIA (no de la definicion, que se comparte entre tramos de la
;; misma longitud) y la respeta cualquier recentrado posterior: Apariencia,
;; ETIQUETAS, edicion. Copiar el tramo copia tambien la marca.
(defun mp:tramo-text-flipped-p (en)
  (= "1" (car (urb:get-xdata-strings en "URB_TXT_VOLTEO"))))

(defun mp:toggle-tramo-text-flip (en)
  (urb:set-xdata-strings en "URB_TXT_VOLTEO"
    (list (if (mp:tramo-text-flipped-p en) "0" "1")))
  (mp:recenter-tramo-attribs en))

(defun mp:flip-tramo-texts (ents / en n)
  (setq n 0)
  (foreach en ents
    (if (mp:base-is-tramo
          (mp:infer-base
            (vla-get-EffectiveName (vlax-ename->vla-object en))
            (mp:att-alist en)))
      (progn
        (mp:toggle-tramo-text-flip en)
        (setq n (1+ n)))))
  (prompt
    (strcat "\nTexto volteado en " (itoa n) " tramo(s)."
      (if (> n 0) " Repita la opcion para devolverlo." "")))
  n)

;; Deja horizontales las ETIQUETAS de un insert rotado (los ATTRIB llevan
;; su propio angulo DXF 50): el simbolo gira, el texto se lee derecho.
(defun mp:level-etiqueta-atts (en / a ed)
  (setq a (entnext en))
  (while (and a (= (cdr (assoc 0 (setq ed (entget a)))) "ATTRIB"))
    (if (wcmatch (strcase (cdr (assoc 2 ed))) "ETIQUETA*,NUM_VIS,PENDIENTE_VIS")
      (entmod (subst (cons 50 0.0) (assoc 50 ed) ed)))
    (setq a (entnext a))))

(defun mp:insert-cant-point
  (base p vals / doc ms blk br en vals2 lay added sync-result rot tapa clave)
  (vl-load-com)
  ;; rotacion opcional (2026-09-02, accesorios ACU orientables): viaja en
  ;; la pseudo-clave __ROT (radianes) y NO se guarda como atributo.
  (setq rot (mp:numeric-real (mp:getval "__ROT" vals "")))
  (if (null rot) (setq rot 0.0))
  (setq vals (vl-remove-if '(lambda (x) (= (car x) "__ROT")) vals))
  (setq vals2 (mp:auto-terrain-values vals p nil))
  ;; 2026-09-07: pozos/sumideros -- PROFUNDIDAD derivada sola:
  ;; tapa (la digitada, o el terreno automatico del punto) - clave
  (if (and (member base '("POZO_SANITARIO" "POZO_PLUVIAL" "SUMIDERO"))
           (= (mp:getval "PROFUNDIDAD" vals2 "") ""))
    (progn
      (setq tapa (mp:numeric-real (mp:getval "COTA_TN_INI" vals2 "")))
      (setq clave (mp:numeric-real (mp:getval "COTA_CLAVE_INI" vals2 "")))
      (if (and tapa clave)
        (setq vals2 (mp:alist-set vals2 "PROFUNDIDAD"
          (rtos (- tapa clave) 2 3))))))
  (if (= (mp:getval "ORIGEN_CREACION" vals2 "") "")
    (setq vals2
      (mp:alist-set vals2 "ORIGEN_CREACION" "MANUAL")))
  (setq vals2 (mp:alist-set vals2 "BLOQUE_BASE" base))
  (setq vals2 (append vals2 (list (cons "ETIQUETA" (mp:label-point base vals2)))))
  (if (mp:caja-plan-p base)
    (setq vals2
      (mp:alist-set
        (mp:alist-set vals2 "NUM_VIS" (mp:caja-num-label vals2))
        "NIVELACION" (mp:caja-nivelacion vals2))))
  (setq blk
    (if (= base "ACCESORIO_ACUEDUCTO")
      (mp:acc-block-name vals2)          ;; un bloque por tipo (simbolo del plano)
      (mp:point-block-name base)))
  (if (not (tblsearch "BLOCK" blk))
    (mp:make-cant-punto-block blk base vals2))
  ;; 5.6.0: una definicion homonima traida de otro plano puede venir con
  ;; wipeout; se quita al reusarla para que el simbolo no tape nada
  (mp:strip-wipeouts-in-block blk)
  (setq added (mp:ensure-block-schema blk base nil))
  (if (> added 0)
    (setq sync-result
      (vl-catch-all-apply 'vl-cmdf
        (list "_.ATTSYNC" "_N" blk))))
  (setq doc (vla-get-ActiveDocument (vlax-get-acad-object)))
  (setq ms (vla-get-ModelSpace doc))
  (setq br (vla-InsertBlock ms (mp:3d p) blk 1.0 1.0 1.0 rot))
  (setq en (vlax-vla-object->ename br))
  (setq lay (mp:point-layer base))
  (if (tblsearch "LAYER" lay) (vla-put-Layer br lay))
  (mp:setatts en vals2)
  (if (> (abs rot) 1e-9) (mp:level-etiqueta-atts en))
  ;; 5.6.1: numero pegado al accesorio y todo simbolo encima de tuberias
  (if (= base "ACCESORIO_ACUEDUCTO")
    (vl-catch-all-apply 'mp:place-acc-label (list en)))
  (vl-catch-all-apply 'mp:points-to-top (list (list en)))
  (princ
    (strcat
      "\nPunto PPTO creado en " lay ": " blk
      " | Cota TN "
      (mp:getval "ESTADO_COTA_TN" vals2 "PENDIENTE") "."))
  en)

(defun mp:dialog-elem-elec (/ dcl ok res etapa)
  (setq dcl (load_dialog (mp:write-dcl)))
  (if (and dcl (new_dialog "maipore_elem_elec" dcl))
    (progn
      (mp:fill-popup "blk" *mp-elem-elec-list* 2)
      (set_tile "id" (mp:next-elec-id (nth 2 *mp-elem-elec-list*)))
      (action_tile "blk"
        "(set_tile \"id\" (mp:next-elec-id (nth (atoi (get_tile \"blk\")) *mp-elem-elec-list*)))")
      (mp:fill-popup "etapa" *mp-etapa-list* 0)
      (mp:update-subetapa)
      (mp:fill-popup "lum" *mp-lum-list* 0)
      (mp:fill-popup "led" *mp-led-list* 0)
      (set_tile "serie" "1")
      (set_tile "altura" "8.4")
      (set_tile "brazo" "0.5")
      (set_tile "avance" "0.3")
      (action_tile "etapa" "(mp:update-subetapa)")
      (action_tile "accept" "(mp:capture-dialog-values)(setq ok T)(done_dialog 1)")
      (action_tile "cancel" "(setq ok nil)(done_dialog 0)")
      (start_dialog)
      (if ok
        (progn
          (setq etapa (mp:item *mp-etapa-list* "etapa"))
          (setq res
            (list
              (cons "BLK" (mp:item *mp-elem-elec-list* "blk"))
              (cons "ID" (mp:gettile "id"))
              (cons "CODIGO" (mp:gettile "id"))
              (cons "SERIE" (mp:gettile "serie"))
              (cons "ETAPA" etapa)
              (cons "SUBETAPA" (mp:item (mp:subetapas-for etapa) "subetapa"))
              (cons "LOTE" (mp:gettile "lote"))
              (cons "CIRCUITO_AP" (mp:gettile "lote"))
              (cons "CIRCUITO" (mp:gettile "lote"))
              (cons "CD" (mp:gettile "cd"))
              (cons "PF" (mp:gettile "pf"))
              (cons "TIPO_LUMINARIA" (mp:item *mp-lum-list* "lum"))
              (cons "FUENTE_LED" (mp:item *mp-led-list* "led"))
              (cons "ALTURA_M" (mp:gettile "altura"))
              (cons "BRAZO_M" (mp:gettile "brazo"))
              (cons "AVANCE_M" (mp:gettile "avance"))))))))
  (if dcl (unload_dialog dcl))
  res)

(defun mp:dialog-acc-acu (/ dcl ok res etapa)
  (setq dcl (load_dialog (mp:write-dcl)))
  (if (and dcl (new_dialog "maipore_acc_acu" dcl))
    (progn
      (mp:fill-popup "acc" *mp-acc-acu-list* 0)
      (mp:fill-popup "etapa" *mp-etapa-list* 0)
      (mp:update-subetapa)
      (urb:fill-diam-popup "diam" *mp-diam-acu-list* "4")
      (mp:fill-popup "diamsal" *mp-diam-acu-list* 0)
      (mp:fill-popup "mat" *mp-material-acu-list* 0)
      (action_tile "etapa" "(mp:update-subetapa)")
      (action_tile "accept" "(mp:capture-dialog-values)(setq ok T)(done_dialog 1)")
      (action_tile "cancel" "(setq ok nil)(done_dialog 0)")
      (start_dialog)
      (if ok
        (progn
          (setq etapa (mp:item *mp-etapa-list* "etapa"))
          (setq res
            (list
              (cons "TIPO_ACCESORIO" (mp:item *mp-acc-acu-list* "acc"))
              (cons "ID" (mp:gettile "accid"))
              (cons "ETAPA" etapa)
              (cons "SUBETAPA" (mp:item (mp:subetapas-for etapa) "subetapa"))
              (cons "DIAMETRO" (mp:item *mp-diam-acu-list* "diam"))
              (cons "DIAMETRO_SALIDA" (mp:item *mp-diam-acu-list* "diamsal"))
              (cons "MATERIAL" (mp:item *mp-material-acu-list* "mat"))
              ;; LOTE retirado del dialogo (2026-09-02); queda vacio por
              ;; compatibilidad con el esquema de atributos existente
              (cons "LOTE" "")))))))
  (if dcl (unload_dialog dcl))
  res)

(defun mp:endpoint-base (tramo tipo)
  (cond
    ((or (= tipo "") (= tipo "NINGUNO")) nil)
    ((= tipo "POZO")
      (cond
        ((= tramo "TRAMO_ARESIDUAL") "POZO_SANITARIO")
        ((= tramo "TRAMO_ALLUVIAS") "POZO_PLUVIAL")
        ;; Compatibilidad con tramos de acueducto creados antes de 4.13.
        ((= tramo "TRAMO_ACUEDUCTO") "ACCESORIO_ACUEDUCTO")
        (T nil)))
    ((and (= tipo "SUMIDERO") (= tramo "TRAMO_ALLUVIAS")) "SUMIDERO")
    ((and (= tipo "ACCESORIO_ACUEDUCTO")
          (= tramo "TRAMO_ACUEDUCTO"))
      "ACCESORIO_ACUEDUCTO")
    ((member tipo *mp-extremo-elec-list*) tipo)
    (T nil)))

(defun mp:distance-2d (p1 p2)
  (distance (list (car p1) (cadr p1)) (list (car p2) (cadr p2))))

(defun mp:point-reference-base (en / obj bname atts base)
  (if (and en (= (cdr (assoc 0 (entget en))) "INSERT"))
    (progn
      (setq obj (vlax-ename->vla-object en))
      (setq bname (vla-get-EffectiveName obj))
      (setq atts (mp:att-alist en))
      (setq base (mp:infer-base bname atts))
      (if (and (/= base "") (not (mp:base-is-tramo base))) base ""))))

(defun mp:point-z (point)
  (if (and point (caddr point)) (float (caddr point)) 0.0))

(defun mp:point-distance-3d (p1 p2)
  (distance
    (list (car p1) (cadr p1) (mp:point-z p1))
    (list (car p2) (cadr p2) (mp:point-z p2))))

(defun mp:entity-handle (ename / obj)
  (if ename
    (progn
      (setq obj (vlax-ename->vla-object ename))
      (vla-get-Handle obj))
    ""))

(defun mp:entity-insertion-point (ename / obj point)
  (if ename
    (progn
      (setq obj (vlax-ename->vla-object ename)
            point (vlax-get obj 'InsertionPoint))
      point)))

(defun mp:entity-point-id (ename / atts)
  (if ename
    (progn
      (setq atts (mp:att-alist ename))
      (mp:getval "ID" atts (mp:getval "CODIGO" atts "")))
    ""))

(defun mp:find-point-reference
  (base point id / ss index ename found ip candidate-id positional positional-count)
  ;; Coincidencia estricta: tipo, identificador y posicion 3D dentro de 5 cm.
  ;; Evita confundir redes superpuestas a distintas cotas o nodos cercanos.
  (setq id (strcase (vl-string-trim " " (mp:safe-str id)))
        ss (ssget "_X" '((0 . "INSERT")))
        index 0)
  (if ss
    (while (< index (sslength ss))
        (setq ename (ssname ss index)
              ip (cdr (assoc 10 (entget ename))))
        (if (and ip
                 (<= (mp:point-distance-3d point ip) 0.05)
                 (= (mp:point-reference-base ename) base))
          (progn
            (setq candidate-id
              (strcase
                (vl-string-trim " " (mp:entity-point-id ename))))
            (cond
              ((or (= id "") (= id candidate-id))
                (if (null found) (setq found ename)))
              (T
                ;; Respaldo espacial: si existe UN solo pozo compatible en
                ;; la misma coordenada se reutiliza aunque el segundo tramo
                ;; haya escrito otro ID o lo haya dejado vacio. El merge
                ;; posterior adopta el ID real del bloque conservado.
                (setq positional ename
                      positional-count (1+ (if positional-count positional-count 0)))))))
        (setq index (1+ index))))
  (if found found
    (if (= positional-count 1) positional nil)))

(defun mp:point-exists-p (base point)
  (if (mp:find-point-reference base point "") T nil))

(defun mp:endpoint-compatible-p (tramo base)
  (cond
    ((= tramo "TRAMO_ARESIDUAL") (= base "POZO_SANITARIO"))
    ((= tramo "TRAMO_ALLUVIAS")
      (member base '("POZO_PLUVIAL" "SUMIDERO")))
    ((= tramo "TRAMO_ACUEDUCTO") (= base "ACCESORIO_ACUEDUCTO"))
    ((member tramo '("TRAMO_E_MT" "TRAMO_E_BT_AP"))
      (member base (cdr *mp-extremo-elec-list*)))
    (T nil)))

(defun mp:endpoint-type-for-base (base)
  (cond
    ((member base '("POZO_SANITARIO" "POZO_PLUVIAL")) "POZO")
    ((= base "SUMIDERO") "SUMIDERO")
    ((= base "ACCESORIO_ACUEDUCTO") "ACCESORIO_ACUEDUCTO")
    (T base)))

(defun mp:getpoint-wcs (base-point prompt-text / raw-point)
  ;; GETPOINT entrega coordenadas del UCS actual; ActiveX e INSERT usan WCS.
  ;; Esta conversion evita tramos desplazados con UCS girados o trasladados.
  (setq raw-point
    (if base-point
      (getpoint (trans base-point 0 1) prompt-text)
      (getpoint prompt-text)))
  (if raw-point (trans raw-point 1 0) nil))

;; 2026-08-14 v4.24.0 (pedido del usuario): UN solo paso por extremo. Se
;; marca el PUNTO del extremo (con osnap) y el programa detecta solo si ya
;; existe un pozo/elemento compatible en ese lugar; antes habia doble
;; opcion (seleccionar el pozo, o Enter y luego el punto). El radio de
;; reconocimiento es generoso porque el simbolo del pozo mide ~1 m y el
;; clic puede caer en su borde; los pozos reales estan separados varios
;; metros, asi que no hay riesgo de agarrar el pozo equivocado.
(setq *mp-endpoint-snap-radius* 0.50)

(defun mp:find-endpoint-near
  (tramo point radius / ss index ename ip base d best best-d)
  ;; extremo compatible ya existente mas cercano al punto (2D) dentro de
  ;; radius; nil si no hay ninguno.
  (setq ss (ssget "_X" '((0 . "INSERT"))) index 0)
  (if ss
    (repeat (sslength ss)
      (setq ename (ssname ss index)
            ip (cdr (assoc 10 (entget ename))))
      (if ip
        (progn
          (setq d (mp:distance-2d point ip))
          (if (and (<= d radius)
                   (or (null best-d) (< d best-d))
                   (setq base (mp:point-reference-base ename))
                   (mp:endpoint-compatible-p tramo base))
            (setq best ename best-d d))))
      (setq index (1+ index))))
  best)

(defun mp:select-network-endpoint
  (tramo prompt-text base-point / point found base)
  (setq point (mp:getpoint-wcs base-point prompt-text))
  (if point
    (progn
      (setq found
        (mp:find-endpoint-near tramo point *mp-endpoint-snap-radius*))
      (if found
        (progn
          (setq base (mp:point-reference-base found))
          (prompt
            (strcat "\nExtremo sobre " (mp:safe-str base) " existente "
              (mp:safe-str (mp:entity-point-id found))
              ": se reutiliza automaticamente."))
          (list (mp:entity-insertion-point found) found))
        (list point nil)))
    nil))

(defun mp:last-number-token (text / i n c buf best)
  ;; Numeros de pozo suelen ser enteros (32, 33...), a diferencia de las
  ;; cotas. Devuelve el ultimo token numerico del texto seleccionado.
  (setq text (mp:safe-str text) i 1 n (strlen (mp:safe-str text))
        buf "" best nil)
  (while (<= i n)
    (setq c (substr text i 1))
    (if (or (wcmatch c "#")
            (and (= c ".") (> (strlen buf) 0)
                 (not (vl-string-search "." buf))))
      (setq buf (strcat buf c))
      (progn
        (if (> (strlen (vl-string-trim "." buf)) 0) (setq best buf))
        (setq buf "")))
    (setq i (1+ i)))
  (if (> (strlen (vl-string-trim "." buf)) 0) (setq best buf))
  best)

(defun mp:number-from-label-selection (selected / ename obj txt layer value)
  (if selected
    (progn
      (setq ename (car selected)
            obj (vl-catch-all-apply 'vlax-ename->vla-object (list ename))
            layer (cdr (assoc 8 (entget ename))))
      (if (and obj (not (vl-catch-all-error-p obj)))
        (setq txt (vl-catch-all-apply 'vla-get-TextString (list obj))))
      (if (vl-catch-all-error-p txt) (setq txt nil))
      (if (null txt) (setq txt (cdr (assoc 1 (entget ename)))))
      (setq value (mp:last-number-token txt))
      (if (and value layer)
        (progn
          (setq *mp-node-number-layer* layer)
          (urb:config-write "MP_NODE_NUMBER_LAYER" layer)))
      (if value
        (prompt
          (strcat "\nNumero " value " reconocido en la capa "
            (urb:safe-string layer "sin nombre") "."))
        (prompt "\nEl objeto seleccionado no contiene un numero legible."))))
  value)

(defun mp:number-from-selected-label (prompt-text / selected)
  (setq selected (nentsel prompt-text))
  (mp:number-from-label-selection selected))

(defun mp:prompt-new-endpoint-id
  (is-final / label event code buffer done selected value char)
  ;; Entrada unica, sin palabras clave: el usuario puede hacer clic sobre un
  ;; TEXT/MTEXT/ATRIBUTO (incluido XREF), escribir el numero o pulsar Enter.
  ;; grread permite aceptar esas tres acciones dentro del mismo paso.
  (setq label (if is-final "final" "inicial"))
  (setq buffer "" done nil value nil)
  (prompt
    (strcat "\nNumero del extremo " label
      ": seleccione el texto, escriba el numero o Enter para omitir: "))
  (while (not done)
    (setq event (grread T 2 0)
          code (car event))
    (cond
      ;; Clic izquierdo: nentselp reconoce tambien objetos anidados/XREF.
      ((= code 3)
        (setq selected (nentselp (cadr event))
              value (mp:number-from-label-selection selected))
        (if value (setq buffer value done T)))
      ;; Teclado: Enter confirma, retroceso edita y los caracteres imprimibles
      ;; se acumulan igual que en getstring.
      ((= code 2)
        (setq char (cadr event))
        (cond
          ((= char 13) (setq done T))
          ((= char 8)
            (if (> (strlen buffer) 0)
              (progn
                (setq buffer (substr buffer 1 (1- (strlen buffer))))
                (princ "\b \b"))))
          ((and (>= char 32) (<= char 126))
            (setq buffer (strcat buffer (chr char)))
            (princ (chr char)))))
      ;; Clic derecho se interpreta como Enter/omitir.
      ((= code 25) (setq done T))))
  (princ)
  (vl-string-trim " " buffer))

(defun mp:reuse-existing-endpoint-selection
  (tramo selection vals is-final / tipo base existing)
  (if (and selection (null (cadr selection)))
    (progn
      (setq tipo
        (mp:getval
          (if is-final "TIPO_EXTREMO_FIN" "TIPO_EXTREMO_INI") vals "NINGUNO")
            base (mp:endpoint-base tramo tipo))
      (if base
        (setq existing (mp:find-point-reference base (car selection) "")))
      (if existing (list (car selection) existing) selection))
    selection))

(defun mp:resolve-new-endpoint-ids
  (tramo vals selection-ini selection-fin / tag)
  ;; Un extremo existente conserva su ID. Solo se solicita el de los
  ;; extremos nuevos y despues de haber definido la geometria.
  (if (cadr selection-ini)
    (setq vals (mp:merge-endpoint-data tramo vals (cadr selection-ini) nil))
    (progn
      (setq tag
        (if (member tramo '("TRAMO_E_MT" "TRAMO_E_BT_AP"))
          "DESDE" "POZO_INI"))
      (setq vals (mp:alist-set vals tag (mp:prompt-new-endpoint-id nil)))))
  (if (cadr selection-fin)
    (setq vals (mp:merge-endpoint-data tramo vals (cadr selection-fin) T))
    (progn
      (setq tag
        (if (member tramo '("TRAMO_E_MT" "TRAMO_E_BT_AP"))
          "HASTA" "POZO_FIN"))
      (setq vals (mp:alist-set vals tag (mp:prompt-new-endpoint-id T)))))
  vals)

(defun mp:endpoint-values (tramo vals is-final base / id result)
  (setq id
    (if is-final
      (mp:getval
        (if (member tramo '("TRAMO_E_MT" "TRAMO_E_BT_AP")) "HASTA" "POZO_FIN")
        vals
        "")
      (mp:getval
        (if (member tramo '("TRAMO_E_MT" "TRAMO_E_BT_AP")) "DESDE" "POZO_INI")
        vals
        "")))
  (setq result
    (list
      (cons "ETAPA" (mp:getval "ETAPA" vals ""))
      (cons "SUBETAPA" (mp:getval "SUBETAPA" vals ""))
      (cons "RED" (mp:getval "RED" vals ""))
      (cons "ID" id)
      (cons "DIAMETRO" (mp:getval "DIAMETRO" vals ""))
      (cons "DUCTOS" (mp:getval "DUCTOS" vals ""))
      (cons "LIBRES" (mp:getval "LIBRES" vals ""))
      (cons "PROFUNDIDAD" (mp:getval "PROFUNDIDAD" vals ""))))
  (if is-final
    (setq result
      (append result
        (list
          (cons "COTA_TN_INI" (mp:getval "COTA_TN_FIN" vals ""))
          (cons "COTA_CLAVE_INI" (mp:getval "COTA_CLAVE_FIN" vals "")))))
    (setq result
      (append result
        (list
          (cons "COTA_TN_INI" (mp:getval "COTA_TN_INI" vals ""))
          (cons "COTA_CLAVE_INI" (mp:getval "COTA_CLAVE_INI" vals ""))))))
  (if (member base *mp-caja-elec-list*)
    (setq result
      (append result
        (list (cons "TIPO_CAJA" (mp:tipo-caja-de base))))))
  (if (= base "ACCESORIO_ACUEDUCTO")
    (setq result
      (append result
        (list
          (cons "TIPO_ACCESORIO" "OTRO")
          (cons "DIAMETRO_SALIDA" (mp:getval "DIAMETRO" vals ""))
          (cons "MATERIAL" (mp:getval "MATERIAL" vals ""))))))
  result)

(defun mp:insert-auto-endpoint (tramo p vals is-final / tipo base id existing)
  (setq tipo
    (mp:getval
      (if is-final "TIPO_EXTREMO_FIN" "TIPO_EXTREMO_INI")
      vals
      "NINGUNO"))
  (setq base (mp:endpoint-base tramo tipo)
        id
          (mp:getval
            (if is-final
              (if (member tramo '("TRAMO_E_MT" "TRAMO_E_BT_AP")) "HASTA" "POZO_FIN")
              (if (member tramo '("TRAMO_E_MT" "TRAMO_E_BT_AP")) "DESDE" "POZO_INI"))
            vals ""))
  (if base
    (progn
      (setq existing (mp:find-point-reference base p id))
      (if existing
        existing
        (mp:insert-cant-point base p
          (mp:alist-set
            (mp:endpoint-values tramo vals is-final base)
            "ORIGEN_CREACION" "AUTO_TRAMO"))))))

(defun mp:merge-endpoint-data
  (tramo vals ename is-final / atts base id tag terrain-value)
  (if ename
    (progn
      (setq atts (mp:att-alist ename)
            base (mp:point-reference-base ename)
            id (mp:getval "ID" atts (mp:getval "CODIGO" atts ""))
            tag
              (if (member tramo '("TRAMO_E_MT" "TRAMO_E_BT_AP"))
                (if is-final "HASTA" "DESDE")
                (if is-final "POZO_FIN" "POZO_INI"))
            vals (mp:alist-set vals tag id)
            vals
              (mp:alist-set vals
                (if is-final "TIPO_EXTREMO_FIN" "TIPO_EXTREMO_INI")
                (mp:endpoint-type-for-base base))
            vals
              (mp:alist-set vals
                (if is-final "HANDLE_EXTREMO_FIN" "HANDLE_EXTREMO_INI")
                (mp:entity-handle ename)))
      ;; La cota de terreno del elemento puntual sirve tambien como respaldo
      ;; para redes secas cuando SUP_TN no pueda consultarse temporalmente.
      (setq terrain-value (mp:getval "COTA_TN_INI" atts ""))
      (if (/= terrain-value "")
        (setq vals
          (mp:alist-set vals
            (if is-final "COTA_TN_FIN" "COTA_TN_INI")
            terrain-value)))
      (if (mp:hydro-tramo-p tramo)
        (progn
          (setq vals
            (mp:alist-set vals
              (if is-final "COTA_CLAVE_FIN" "COTA_CLAVE_INI")
              (mp:getval "COTA_CLAVE_INI" atts "")))))
      (if (and (not (mp:hydro-tramo-p tramo))
               (= (mp:getval "PROFUNDIDAD" vals "") ""))
        (setq vals
          (mp:alist-set vals "PROFUNDIDAD"
            (mp:getval "PROFUNDIDAD" atts ""))))))
  vals)

(defun mp:prepare-linked-endpoints
  (tramo selection-ini selection-fin vals / p1 p2 ename-ini ename-fin)
  (setq p1 (car selection-ini)
        p2 (car selection-fin)
        ename-ini (cadr selection-ini)
        ename-fin (cadr selection-fin))
  (if ename-ini (setq vals (mp:merge-endpoint-data tramo vals ename-ini nil)))
  (if ename-fin (setq vals (mp:merge-endpoint-data tramo vals ename-fin T)))
  (if (null ename-ini)
    (setq ename-ini (mp:insert-auto-endpoint tramo p1 vals nil)))
  (if (null ename-fin)
    (setq ename-fin (mp:insert-auto-endpoint tramo p2 vals T)))
  (if ename-ini (setq vals (mp:merge-endpoint-data tramo vals ename-ini nil)))
  (if ename-fin (setq vals (mp:merge-endpoint-data tramo vals ename-fin T)))
  (if (null ename-ini)
    (setq vals (mp:alist-set vals "HANDLE_EXTREMO_INI" "")))
  (if (null ename-fin)
    (setq vals (mp:alist-set vals "HANDLE_EXTREMO_FIN" "")))
  (list vals ename-ini ename-fin))

(defun mp:insert-auto-endpoints (tramo p1 p2 vals / ename-ini ename-fin)
  (setq ename-ini (mp:insert-auto-endpoint tramo p1 vals nil)
        ename-fin (mp:insert-auto-endpoint tramo p2 vals T))
  (list ename-ini ename-fin))

(defun mp:get-two-points (msg1 msg2 / p1 p2)
  (setq p1 (getpoint msg1))
  (if p1 (setq p2 (getpoint p1 msg2)))
  (if (and p1 p2) (list p1 p2) nil))

(defun mp:create-linked-tramo
  (base vals msg1 msg2
   / doc selection-ini selection-fin p1 p2 prepared ename-ini ename-fin
   new-ini new-fin segment undo-open *error*)
  (vl-load-com)
  (setq doc (vla-get-ActiveDocument (vlax-get-acad-object)))
  (defun *error* (message)
    (if segment (vl-catch-all-apply 'entdel (list segment)))
    (if new-ini (vl-catch-all-apply 'entdel (list new-ini)))
    (if new-fin (vl-catch-all-apply 'entdel (list new-fin)))
    (if undo-open
      (progn
        (vl-catch-all-apply 'vla-EndUndoMark (list doc))
        (setq undo-open nil)))
    (if (and message
             (not (member message '("Function cancelled" "quit / exit abort"))))
      (prompt (strcat "\nError al crear el tramo vinculado: " message)))
    (princ))
  (setq selection-ini (mp:select-network-endpoint base msg1 nil))
  (if selection-ini
    (setq selection-fin
      (mp:select-network-endpoint base msg2 (car selection-ini))))
  (if (and selection-ini selection-fin)
    (progn
      (setq p1 (car selection-ini)
            p2 (car selection-fin))
      (if (<= (mp:distance-2d p1 p2) 1e-9)
        (prompt "\nNo se creo el tramo: los extremos coinciden en planta.")
        (progn
          ;; Si el usuario marco exactamente un pozo/camara existente sin
          ;; seleccionarlo, se reconoce espacialmente (5 cm) antes de pedir
          ;; numeros. Asi 32-33 seguido de 33-34 hereda 33 automaticamente.
          (setq selection-ini
            (mp:reuse-existing-endpoint-selection base selection-ini vals nil)
                selection-fin
            (mp:reuse-existing-endpoint-selection base selection-fin vals T)
                vals
            (mp:resolve-new-endpoint-ids
              base vals selection-ini selection-fin))
          (vla-StartUndoMark doc)
          (setq undo-open T
                prepared
                  (mp:prepare-linked-endpoints
                    base selection-ini selection-fin vals)
                vals (car prepared)
                ename-ini (cadr prepared)
                ename-fin (caddr prepared)
                new-ini (if (and (null (cadr selection-ini)) ename-ini) ename-ini nil)
                new-fin (if (and (null (cadr selection-fin)) ename-fin) ename-fin nil)
                segment (mp:insert-cant-tramo base p1 p2 vals))
          (if segment
            (progn
              (setq vals (mp:att-alist segment))
              (if (= (mp:getval "CONTROL_ESTADO" vals "REVISAR") "OK")
                (prompt "\nTramo vinculado y validado correctamente.")
                (prompt
                  (strcat "\nTramo creado con observaciones: "
                    (mp:getval "CONTROL_MENSAJES" vals "Revisar datos."))))
              (setq new-ini nil new-fin nil segment nil))
            (progn
              (if new-ini (entdel new-ini))
              (if new-fin (entdel new-fin))
              (setq new-ini nil new-fin nil)))
          (if undo-open
            (progn
              (vla-EndUndoMark doc)
              (setq undo-open nil)))))))
  (princ))

(defun mp:insert-electrical-tramo
  (base msg1 msg2 dialog-fn type-red / vals)
  (mp:ensure-layers)
  (if (setq vals (apply dialog-fn nil))
    (progn
      (setq vals (mp:alist-set vals "TIPO_RED" type-red))
      (mp:create-linked-tramo base vals msg1 msg2)))
  (princ))

(defun urb:create-network-segment-command (/ tipo)
  (if (urb:confirm-meter-units)
    (progn
      (initget "Sanitario Pluvial Acueducto MediaTension BajaTension Alumbrado")
      (setq tipo
        (getkword
          "\nTipo de tramo [Sanitario/Pluvial/Acueducto/MediaTension/BajaTension/Alumbrado] <Sanitario>: "))
      (if (null tipo) (setq tipo "Sanitario"))
      (cond
        ((= tipo "Sanitario")
          (mp:insert-tramo-forced "Aresidual"))
        ((= tipo "Pluvial")
          (mp:insert-tramo-forced "Alluvias"))
        ((= tipo "Acueducto")
          (mp:insert-tramo-forced "Acueducto"))
        ((= tipo "MediaTension")
          (mp:insert-electrical-tramo
            "TRAMO_E_MT"
            "\nExtremo inicial tramo MT: "
            "\nExtremo final tramo MT: "
            'mp:dialog-tramo-mt
            "MT"))
        ((= tipo "BajaTension")
          (mp:insert-electrical-tramo
            "TRAMO_E_BT_AP"
            "\nExtremo inicial tramo BT: "
            "\nExtremo final tramo BT: "
            'mp:dialog-tramo-bt
            "BT"))
        ((= tipo "Alumbrado")
          (mp:insert-electrical-tramo
            "TRAMO_E_BT_AP"
            "\nExtremo inicial tramo alumbrado: "
            "\nExtremo final tramo alumbrado: "
            'mp:dialog-tramo-bt
            "AP"))))
    (prompt "\nCreacion de tramo cancelada: confirme primero las unidades del dibujo."))
  (princ))

(defun urb:create-sanitary-manhole (/ vals p)
  (mp:ensure-layers)
  (if (setq vals (mp:dialog-punto-hidro "Aresidual" "POZO_SANITARIO"))
    (if (setq p (mp:getpoint-wcs nil "\nPunto de pozo sanitario: "))
      (mp:insert-cant-point "POZO_SANITARIO" p vals)))
  (princ))

;; 5.6.0 (pedido del usuario: "unificame el icono de sumidero y pozo, que en
;; tipo me deje elegir si es un pozo o un sumidero, falta incluir tambien
;; la opcion de cabezal"). El boton Pozo del panel pluvial abre esta
;; ventana. CABEZAL_PLUVIAL ya existia completo en el motor (simbolo del
;; plano PLUVIAL.dwg, capa, etiqueta CAB, cruce con presupuesto por rango de
;; diametro) pero no tenia forma de crearse desde la cinta.
;; 5.6.1: el boton se llama "Accesorios" y la canuela entro como un tipo mas
;; (pedido del usuario: "que la canuela este incluida en pozo/sumidero y
;; cambies ese nombre a accesorios").
(setq *mp-pluvial-tipos*
  '(("Pozo de inspeccion" . "POZO_PLUVIAL")
    ("Sumidero" . "SUMIDERO")
    ("Cabezal de descarga" . "CABEZAL_PLUVIAL")
    ("Canuela (recorrido, ML)" . "CANUELA_PLU")))

(defun mp:dialog-punto-pluvial (/ dcl ok etapa res tipo idx)
  (setq dcl (load_dialog (mp:write-dcl-puntos)))
  (if (not (new_dialog "maipore_punto_pluvial" dcl)) (exit))
  (setq idx (if (and (boundp '*mp-last-tipo-plu*) *mp-last-tipo-plu*
                     (< *mp-last-tipo-plu* (length *mp-pluvial-tipos*)))
              *mp-last-tipo-plu* 0))
  (mp:fill-popup "tipo_plu" (mapcar 'car *mp-pluvial-tipos*) idx)
  (mp:fill-popup "etapa" *mp-etapa-list* 0)
  (mp:update-subetapa)
  (action_tile "etapa" "(mp:update-subetapa)")
  (action_tile "accept" "(mp:capture-dialog-values)(setq ok T)(done_dialog 1)")
  (action_tile "cancel" "(setq ok nil)(done_dialog 0)")
  (start_dialog)
  (if ok
    (progn
      (setq idx (atoi (mp:gettile "tipo_plu")))
      (if (or (< idx 0) (>= idx (length *mp-pluvial-tipos*))) (setq idx 0))
      (setq *mp-last-tipo-plu* idx
            tipo (cdr (nth idx *mp-pluvial-tipos*)))
      (setq etapa (mp:item *mp-etapa-list* "etapa"))
      ;; sin diametro ni cotas (pedido del usuario): cota de terreno
      ;; automatica de SUP_TN; clave y profundidad se completan con EDITAR
      (setq res
        (cons tipo
          (list (cons "ETAPA" etapa)
                (cons "SUBETAPA" (mp:item (mp:subetapas-for etapa) "subetapa"))
                (cons "RED" "Alluvias")
                (cons "ID" (mp:gettile "id"))
                (cons "DIAMETRO" "")
                (cons "COTA_TN_INI" "")
                (cons "COTA_CLAVE_INI" "")
                (cons "PROFUNDIDAD" ""))))))
  (unload_dialog dcl)
  res)

;; Diametro del tramo PLUVIAL que llega al punto (extremo a <= 2.5 m: los
;; tramos arrancan en el borde del simbolo, no en su centro). Lo usa el
;; cabezal. Desde 2026-09-23 el presupuesto del cabezal NO depende del
;; diametro (una sola actividad a todo costo); el dato se conserva porque
;; alimenta el simbolo, los cuadros y el perfil.
(defun mp:pluvial-diam-near (p / ss i en obj nm ed ip rot sx span end d bestd diam spans hit blk)
  (setq ss (ssget "_X" '((0 . "INSERT"))) i 0 bestd 2.5 diam nil spans nil)
  (if ss
    (repeat (sslength ss)
      (setq en (ssname ss i) obj (vlax-ename->vla-object en)
            nm (vla-get-EffectiveName obj))
      (if (and (wcmatch (strcase nm) "*TRAMO*")
               (= (mp:infer-base nm (mp:att-alist en)) "TRAMO_ALLUVIAS"))
        (progn
          (setq ed (entget en) ip (cdr (assoc 10 ed))
                rot (cdr (assoc 50 ed)) sx (cdr (assoc 41 ed)))
          (if (setq hit (assoc nm spans))
            (setq span (cdr hit))
            (progn
              (setq blk (vl-catch-all-apply 'vla-Item
                          (list (vla-get-Blocks (urb:doc)) nm)))
              (setq span (if (vl-catch-all-error-p blk) 0.0
                           (mp:block-tramo-length blk)))
              (setq spans (cons (cons nm span) spans))))
          (setq end (list (+ (car ip) (* sx span (cos rot)))
                          (+ (cadr ip) (* sx span (sin rot)))))
          (setq d (min (distance (list (car p) (cadr p)) (list (car ip) (cadr ip)))
                       (distance (list (car p) (cadr p)) end)))
          (if (< d bestd)
            (setq bestd d
                  diam (mp:getval "DIAMETRO" (mp:att-alist en) "")))))
      (setq i (1+ i))))
  (if (and diam (/= diam "")) diam nil))

(defun urb:create-storm-manhole (/ data base vals p dir diam ancho)
  (mp:ensure-layers)
  (if (setq data (mp:dialog-punto-pluvial))
    (progn
      (setq base (car data) vals (cdr data))
      (if (= base "CANUELA_PLU")
        ;; canuela: recorrido dibujado, por ML (ancho de Ajustes)
        (progn
          (setq ancho (urb:canuela-plu-ancho-default))
          (urb:canuela-plu-draw-one
            (mp:getval "ETAPA" vals "1")
            (mp:getval "SUBETAPA" vals "1")
            ancho (mp:getval "ID" vals "")))
        (if (setq p (mp:getpoint-wcs nil
                      (cond
                        ((= base "SUMIDERO") "\nPunto de sumidero: ")
                        ((= base "CABEZAL_PLUVIAL") "\nPunto del cabezal (boca de descarga): ")
                        (T "\nPunto de pozo pluvial: "))))
          (progn
            ;; el cabezal tiene frente: se orienta hacia donde descarga
            ;; (Enter = sin girar). Viaja en la pseudo-clave __ROT que ya
            ;; entiende mp:insert-cant-point (la etiqueta queda horizontal).
            (if (= base "CABEZAL_PLUVIAL")
              (progn
                (setq diam (mp:pluvial-diam-near p))
                (if diam
                  (progn
                    (setq vals (mp:alist-set vals "DIAMETRO" diam))
                    (prompt (strcat "\nDiametro tomado del tramo que llega: " diam "\"")))
                  (prompt "\nNo hay tramo pluvial llegando a este punto: el cabezal queda sin diametro (asignelo con EDITAR). El presupuesto no se afecta."))
                (setq dir (getangle p "\nDireccion de descarga <sin girar>: "))
                (if dir
                  (setq vals (mp:alist-set vals "__ROT"
                               (rtos (- dir (/ pi 2.0)) 2 8))))))
            (mp:insert-cant-point base p vals))))))
  (princ))

(defun urb:create-inlet (/ vals p)
  (mp:ensure-layers)
  (if (setq vals (mp:dialog-punto-hidro "Alluvias" "SUMIDERO"))
    (if (setq p (mp:getpoint-wcs nil "\nPunto de sumidero: "))
      (mp:insert-cant-point "SUMIDERO" p vals)))
  (princ))

(defun urb:create-electrical-chamber (/ data vals p base)
  (mp:ensure-layers)
  (if (setq data (mp:dialog-caja-electrica))
    (if (setq p (mp:getpoint-wcs nil "\nPunto de caja/camara electrica: "))
      (progn
        (setq base (cdr (assoc "BLK" data)))
        (setq vals (vl-remove (assoc "BLK" data) data))
        (if (= (urb:safe-string (cdr (assoc "ID" vals)) "") "")
          (setq vals (mp:alist-set vals "ID" (mp:next-elec-id base))))
        (mp:insert-cant-point base p vals))))
  (princ))

;; 2026-09-02: deducir el TIPO de accesorio desde el nombre del bloque de
;; un XREF/plano (clic sobre el simbolo dibujado): se busca el token por
;; subcadena en el nombre efectivo del insert anidado.
(defun mp:acc-token-from-blockname (bname / up)
  (setq up (strcase (mp:safe-str bname)))
  (cond
    ((vl-string-search "HIDRANT" up) "HIDRANTE_TORRE")
    ((vl-string-search "VENTOSA" up) "VALVULA_VENTOSA")
    ((vl-string-search "PURGA" up) "VALVULA_PURGA")
    ((vl-string-search "VALV" up) "VALVULA_RED_MENOR")
    ((vl-string-search "TEE" up) "TEE")
    ((vl-string-search "TAPON" up) "TAPON")
    ((vl-string-search "REDUC" up) "REDUCCION")
    ((vl-string-search "UNION" up) "JUNTA_CONSTRUCCION")
    ((vl-string-search "PASAMURO" up) "NIPLE_PASAMUROS")
    ((vl-string-search "NIPLE" up) "NIPLE_PASAMUROS")
    ((vl-string-search "CODO" up)
      (cond
        ((vl-string-search "11" up) "CODO_11_5")
        ((vl-string-search "22" up) "CODO_22_5")
        ((vl-string-search "45" up) "CODO_45")
        (T "CODO_90")))
    (T nil)))

;; toma un accesorio DIBUJADO en un xref: nentsel sobre el simbolo,
;; devuelve (token punto-wcs rotacion) o nil. El punto y la rotacion
;; salen del INSERT anidado transformado con la matriz MCS->WCS que
;; entrega nentsel (4x4 en el 3er elemento).
(defun mp:acc-pick-from-xref (/ sel ename parents cand obj bname token
                              ed ip rot mat r c fila p wx wy ang0 ang1)
  (setq sel (nentsel "\nClic sobre el accesorio del XREF/plano: "))
  (if (null sel) nil
    (progn
      (setq parents (if (> (length sel) 3) (nth 3 sel) nil))
      ;; candidato: el insert anidado mas profundo cuyo nombre revele tipo
      (foreach cand (append parents (list (car sel)))
        (if (and (null token) cand
                 (= (cdr (assoc 0 (entget cand))) "INSERT"))
          (progn
            (setq obj (vl-catch-all-apply 'vlax-ename->vla-object (list cand)))
            (setq bname
              (if (vl-catch-all-error-p obj) ""
                (vl-catch-all-apply 'vla-get-EffectiveName (list obj))))
            (if (vl-catch-all-error-p bname) (setq bname ""))
            (if (setq token (mp:acc-token-from-blockname bname))
              (setq ed (entget cand))))))
      (if (null token)
        (progn
          (prompt "\nNo se reconocio el tipo de accesorio en ese bloque.")
          nil)
        (progn
          (setq ip (cdr (assoc 10 ed)) rot (cdr (assoc 50 ed)))
          ;; transformar insercion + rotacion del espacio del xref al WCS
          (setq mat (if (> (length sel) 2) (caddr sel) nil))
          (if (and mat (listp mat) (>= (length mat) 4))
            (progn
              ;; convencion nentsel: p_wcs = p_ecs (fila) x M + M[3]
              (setq wx (+ (* (car ip) (nth 0 (nth 0 mat)))
                          (* (cadr ip) (nth 0 (nth 1 mat)))
                          (* (caddr ip) (nth 0 (nth 2 mat)))
                          (nth 0 (nth 3 mat)))
                    wy (+ (* (car ip) (nth 1 (nth 0 mat)))
                          (* (cadr ip) (nth 1 (nth 1 mat)))
                          (* (caddr ip) (nth 1 (nth 2 mat)))
                          (nth 1 (nth 3 mat))))
              ;; rotacion adicional de la matriz: imagen del eje X local
              (setq ang0 (angle '(0.0 0.0)
                           (list (nth 0 (nth 0 mat)) (nth 1 (nth 0 mat)))))
              (setq ang1 (+ rot ang0))
              (list token (list wx wy 0.0) ang1))
            ;; sin matriz (objeto directo): usar el punto tal cual
            (list token (list (car ip) (cadr ip) 0.0) rot)))))))

(defun urb:create-water-accessory (/ vals p kw xr ang)
  (mp:ensure-layers)
  (if (setq vals (mp:dialog-acc-acu))
    (progn
      ;; punto directo o [Xref] = tomar simbolo ya dibujado en el plano
      (initget "Xref")
      (setq p (getpoint "\nPunto del accesorio de acueducto o [Xref]: "))
      (cond
        ((and p (= (type p) 'STR) (= p "Xref"))
          (if (setq xr (mp:acc-pick-from-xref))
            (progn
              (setq vals (mp:alist-set vals "TIPO_ACCESORIO" (nth 0 xr)))
              (setq vals (mp:alist-set vals "__ROT" (rtos (nth 2 xr) 2 8)))
              (prompt (strcat "\nReconocido del plano: " (nth 0 xr)))
              (mp:insert-cant-point "ACCESORIO_ACUEDUCTO" (nth 1 xr) vals))))
        (p
          ;; direccion opcional (2026-09-02): girar el accesorio al crearlo
          (setq ang (getangle p "\nDireccion del accesorio <horizontal>: "))
          (if ang (setq vals (mp:alist-set vals "__ROT" (rtos ang 2 8))))
          (mp:insert-cant-point "ACCESORIO_ACUEDUCTO" (trans p 1 0) vals)))))
  (princ))

(defun urb:create-luminaire (/ data vals p base)
  (mp:ensure-layers)
  (if (setq data (mp:dialog-elem-elec))
    (if (setq p (mp:getpoint-wcs nil "\nPunto de insercion elemento electrico: "))
      (progn
        (setq base (cdr (assoc "BLK" data)))
        (setq vals (vl-remove (assoc "BLK" data) data))
        (if (= (urb:safe-string (cdr (assoc "ID" vals)) "") "")
          (progn
            (setq vals (mp:alist-set vals "ID" (mp:next-elec-id base)))
            (setq vals (mp:alist-set vals "CODIGO" (mp:next-elec-id base)))))
        (mp:insert-cant-point base p vals))))
  (princ))

(defun urb:update-quantity-labels-command
  (/ ss i en obj bname atts base lab)
  ;; cache de defs del recentrado: fresco por corrida (los attdefs pueden
  ;; haberse normalizado desde la ultima pasada)
  (setq *mp-recenter-defcache* nil)
  (setq ss (ssget "X" '((0 . "INSERT"))))
  (if ss
    (progn
      (setq i 0)
      (while (< i (sslength ss))
        (setq en (ssname ss i) obj (vlax-ename->vla-object en) bname (vla-get-EffectiveName obj))
        (if (mp:is-cant-blockname bname)
          (progn
            (setq atts (mp:att-alist en))
            (setq base (mp:infer-base bname atts))
            (if (/= base "")
              (progn
                (setq lab
                  (if (mp:base-is-tramo base)
                    (mp:label-tramo base atts)
                    (mp:label-point base atts)))
                (mp:setatt-one en "ETIQUETA" lab)
                (if (mp:base-is-tramo base)
                  (progn
                    (mp:setatt-one en "PENDIENTE_VIS" (mp:pendiente-label atts))
                    ;; 2026-09-02: recentrar la etiqueta al punto de
                    ;; diseno del tramo (reporte "no quedan centradas")
                    (mp:recenter-tramo-attribs en))
                  ;; puntos (accesorios girados con ROTATE): etiqueta
                  ;; horizontal, sin tocar tramos (sus etiquetas acompanan
                  ;; la linea). 5.6.1: accesorio con su numero pegado.
                  (progn
                    (mp:level-etiqueta-atts en)
                    (if (= base "ACCESORIO_ACUEDUCTO")
                      (vl-catch-all-apply 'mp:place-acc-label (list en)))))))))
        (setq i (1+ i)))
      (princ "\nEtiquetas de cantidades actualizadas."))
    (princ "\nNo se encontraron bloques."))
  (princ))

(defun mp:merge-atts (old new / res pair)
  (setq res old)
  (foreach pair new
    (if (assoc (strcase (car pair)) res)
      (setq res (subst (cons (strcase (car pair)) (cdr pair)) (assoc (strcase (car pair)) res) res))
      (setq res (cons (cons (strcase (car pair)) (cdr pair)) res))))
  res)
(defun mp:reference-geometry-length (obj / doc blks blk bname span scale)
  (setq doc (vla-get-ActiveDocument (vlax-get-acad-object)))
  (setq blks (vla-get-Blocks doc))
  (setq bname (vla-get-EffectiveName obj))
  (setq blk (vl-catch-all-apply 'vla-Item (list blks bname)))
  (if (vl-catch-all-error-p blk)
    ""
    (progn
      (setq span (mp:block-tramo-length blk))
      (setq scale (abs (vla-get-XScaleFactor obj)))
      (if (> span 1e-9) (rtos (* span scale) 2 2) ""))))

(defun mp:ensure-reference-length (en obj atts / value)
  (setq value (mp:getval "LONGITUD" atts ""))
  (if (= value "")
    (progn
      (setq value (mp:reference-geometry-length obj))
      (if (/= value "") (mp:setatt-one en "LONGITUD" value))))
  value)

;; 2026-08-14 v4.24.0: local ANGLE renombrado (tapaba la funcion nativa;
;; preventivo, mismo patron que el TYPE de mp:auto-link-endpoint-value).
(defun mp:reference-plan-points (obj / doc blocks block span scale length-value rot-angle p1 p2)
  (setq doc (vla-get-ActiveDocument (vlax-get-acad-object))
        blocks (vla-get-Blocks doc)
        block
          (vl-catch-all-apply 'vla-Item
            (list blocks (vla-get-EffectiveName obj))))
  (if (vl-catch-all-error-p block)
    nil
    (progn
      (setq span (mp:block-tramo-length block)
            scale (abs (vla-get-XScaleFactor obj))
            length-value (* span scale)
            rot-angle (vla-get-Rotation obj)
            p1 (vlax-get obj 'InsertionPoint)
            p2
              (list
                (+ (car p1) (* length-value (cos rot-angle)))
                (+ (cadr p1) (* length-value (sin rot-angle)))
                (mp:point-z p1)))
      (list p1 p2 span))))

;; 2026-08-14 v4.24.0: el local se llamaba TYPE y tapaba la funcion nativa
;; (type ...) que urb:safe-string usa por debajo -> "bad function: POZO" al
;; editar cualquier tramo hidrosanitario (5o caso del patron documentado:
;; distance, length, type x2, last). Renombrado a endpoint-tipo.
(defun mp:auto-link-endpoint-value (base point vals is-final / endpoint-tipo endpoint-base id found)
  (setq endpoint-tipo
    (mp:getval
      (if is-final "TIPO_EXTREMO_FIN" "TIPO_EXTREMO_INI")
      vals "NINGUNO")
        endpoint-base (mp:endpoint-base base endpoint-tipo)
        id
          (mp:getval
            (if (member base '("TRAMO_E_MT" "TRAMO_E_BT_AP"))
              (if is-final "HASTA" "DESDE")
              (if is-final "POZO_FIN" "POZO_INI"))
            vals ""))
  (if endpoint-base
    (progn
      (setq found (mp:find-point-reference endpoint-base point id))
      (if found (mp:merge-endpoint-data base vals found is-final) vals))
    vals))

(defun mp:save-edited-claves (en before edits / stored out suffix idtag tag oldid id key pair)
  ;; Cotas de conexion propias del tramo: EDITAR prevalece sobre el pozo.
  ;; XDATA persiste la eleccion durante regeneraciones y posteriores aperturas.
  ;; Campo vacio vuelve a heredar; cambiar de pozo invalida la excepcion anterior.
  (setq stored (urb:get-xdata-strings en "MP_CLAVES_EDITADAS") out nil)
  (foreach suffix '("INI" "FIN")
    (setq idtag (strcat "POZO_" suffix) tag (strcat "COTA_CLAVE_" suffix)
          oldid (mp:getval idtag before "") id (mp:getval idtag edits oldid)
          key (if (= id (car stored)) (cadr stored) "")
          pair (assoc tag edits))
    (if (and pair (or (/= (cdr pair) (mp:getval tag before "")) (/= id oldid)))
      (setq key (cdr pair)))
    (setq out (append out (list id (urb:safe-string key ""))) stored (cddr stored)))
  (urb:set-xdata-strings en "MP_CLAVES_EDITADAS" out))

(defun mp:apply-edited-claves (en vals / stored suffix key)
  (setq stored (urb:get-xdata-strings en "MP_CLAVES_EDITADAS"))
  (foreach suffix '("INI" "FIN")
    (setq key (cadr stored))
    (if (and (= (car stored) (mp:getval (strcat "POZO_" suffix) vals ""))
             (= (type key) 'STR) (/= key ""))
      (setq vals (mp:alist-set vals (strcat "COTA_CLAVE_" suffix) key)))
    (setq stored (cddr stored)))
  vals)

(defun mp:sync-tramo-values
  (ename obj base vals
   / reference p1 p2 span handle-ini handle-fin endpoint-ini endpoint-fin
   linked-p1 linked-p2 length-2d scale derived gaps gap-ini gap-fin p1v)
  (setq reference (mp:reference-plan-points obj))
  (if reference
    (progn
      (setq p1 (car reference)
            p2 (cadr reference)
            span (caddr reference)
            vals (mp:auto-link-endpoint-value base p1 vals nil)
            vals (mp:auto-link-endpoint-value base p2 vals T)
            handle-ini (mp:getval "HANDLE_EXTREMO_INI" vals "")
            handle-fin (mp:getval "HANDLE_EXTREMO_FIN" vals "")
            endpoint-ini (if (/= handle-ini "") (handent handle-ini) nil)
            endpoint-fin (if (/= handle-fin "") (handent handle-fin) nil))
      (if endpoint-ini
        (progn
          (setq linked-p1 (mp:entity-insertion-point endpoint-ini)
                vals (mp:merge-endpoint-data base vals endpoint-ini nil))))
      (if endpoint-fin
        (progn
          (setq linked-p2 (mp:entity-insertion-point endpoint-fin)
                vals (mp:merge-endpoint-data base vals endpoint-fin T))))
      (if (and linked-p1 linked-p2)
        (progn
          (setq p1 linked-p1
                p2 linked-p2
                length-2d (mp:distance-2d p1 p2))
          (if (and (> span 1e-9) (> length-2d 1e-9))
            (progn
              ;; recorte hasta el borde tambien al re-sincronizar (EDITAR):
              ;; insercion, escala y cantidades usan la longitud cara-a-cara.
              (setq gaps (mp:tramo-end-gaps base vals length-2d)
                    gap-ini (car gaps)
                    gap-fin (cadr gaps))
              (setq p1v
                (if (> gap-ini 0.0)
                  (list
                    (+ (car p1) (* gap-ini (cos (angle p1 p2))))
                    (+ (cadr p1) (* gap-ini (sin (angle p1 p2)))))
                  p1))
              (setq scale (/ (- length-2d gap-ini gap-fin) span))
              (vla-put-InsertionPoint obj (mp:3d p1v))
              (vla-put-Rotation obj (angle p1 p2))
              (vla-put-XScaleFactor obj (float scale))))))
      (setq vals (mp:auto-terrain-values vals p1 p2)
            vals (mp:apply-edited-claves ename vals)
            derived (mp:derive-tramo-values base p1 p2 vals))
      (mp:store-tramo-memory-samples
        ename *mp-last-tramo-memory-samples*)
      (setq *mp-last-tramo-memory-samples* nil)
      derived)
    (mp:validate-tramo-values base vals)))

(defun mp:update-segments-for-endpoint (endpoint / handle ss index ename obj atts base merged)
  (setq handle (strcase (mp:entity-handle endpoint))
        ss (ssget "_X" '((0 . "INSERT")))
        index 0)
  (if ss
    (while (< index (sslength ss))
      (setq ename (ssname ss index)
            atts (mp:att-alist ename)
            base (mp:infer-base
              (vla-get-EffectiveName (vlax-ename->vla-object ename)) atts))
      (if (and (mp:base-is-tramo base)
               (or (= handle (strcase (mp:getval "HANDLE_EXTREMO_INI" atts "")))
                   (= handle (strcase (mp:getval "HANDLE_EXTREMO_FIN" atts "")))))
        (progn
          (setq obj (vlax-ename->vla-object ename)
                merged (mp:sync-tramo-values ename obj base atts))
          (mp:setatts ename merged)
          (mp:setatt-one ename "ETIQUETA" (mp:label-tramo base merged))
          (mp:setatt-one ename "PENDIENTE_VIS" (mp:pendiente-label merged))
          (vla-Update obj)))
      (setq index (1+ index)))))

(defun mp:update-block-after-edit (en vals / obj atts merged base lab lay bname doc saved)
  (setq obj (vlax-ename->vla-object en))
  (setq atts (mp:att-alist en))
  (setq bname (vla-get-EffectiveName obj))
  (setq base (mp:infer-base bname atts))
  (setq merged (mp:merge-atts atts vals))
  (if (/= base "")
    (progn
      (setq lay (mp:edit-layer-for-base base))
      (if (tblsearch "LAYER" lay) (vla-put-Layer obj lay))
      (cond
        ((mp:base-is-tramo base)
          ;; 2026-08-14 v4.24.0: tramos creados antes de esta version no
          ;; tienen los ATTDEF de triturado/recebo/entibado; editarlos los
          ;; agrega aqui mismo (mismo patron que la creacion) para que los
          ;; valores recalculados tengan donde guardarse.
          (if (> (mp:ensure-block-schema bname base T) 0)
            (vl-catch-all-apply 'vl-cmdf (list "_.ATTSYNC" "_N" bname)))
          (if (mp:hydro-tramo-p base) (mp:save-edited-claves en atts vals))
          (setq merged (mp:sync-tramo-values en obj base merged)
                saved (mp:setatts en merged))
          (setq lab (mp:label-tramo base merged))
          (mp:setatt-one en "ETIQUETA" lab)
          (mp:setatt-one en "PENDIENTE_VIS" (mp:pendiente-label merged))
          (if (member base '("TRAMO_E_MT" "TRAMO_E_BT_AP"))
            (mp:setatt-one en "LONG_VIS" (mp:long-label merged))))
        ((not (mp:base-is-tramo base))
          (setq merged
            (mp:auto-terrain-values
              merged (mp:entity-insertion-point en) nil))
          (setq saved (mp:setatts en merged))
          (setq lab (mp:label-point base merged))
          (mp:setatt-one en "ETIQUETA" lab)
          (if (mp:caja-plan-p base)
            (progn
              (mp:setatt-one en "NUM_VIS" (mp:caja-num-label merged))
              (mp:setatt-one en "NIVELACION" (mp:caja-nivelacion merged))))
          (mp:update-segments-for-endpoint en)))
      ;; Fuerza la actualizacion visual inmediata de atributos y referencia.
      (vla-Update obj)
      (entupd en)
      (redraw en 1)
      (if (not *mp-suppress-regen*)
        (progn
          (setq doc (vla-get-ActiveDocument (vlax-get-acad-object)))
          (vla-Regen doc 1)))
      (vl-catch-all-apply 'vla-Update (list obj))
      (entupd en)))
  (if (null saved) (setq saved (mp:setatts en vals)))
  saved)

(defun urb:export-networks-csv-command
  (/ fn f ss i en obj bname pt row atts val count h)
  (setq fn (getfiled "Guardar cantidades CSV" (strcat (getvar "DWGPREFIX") "cantidades_maipore.csv") "csv" 1))
  (if fn
    (if (setq f (open fn "w"))
      (progn
        (write-line (vl-string-right-trim *mp-csv-sep* (apply 'strcat (mapcar '(lambda (x) (strcat (mp:csv-safe x) *mp-csv-sep*)) *mp-csv-tags*))) f)
        (setq ss (ssget "X" '((0 . "INSERT"))) count 0)
        (if ss
          (progn
            (setq i 0)
            (while (< i (sslength ss))
              (setq en (ssname ss i) obj (vlax-ename->vla-object en) bname (vla-get-EffectiveName obj))
              (if (mp:is-cant-blockname bname)
                (progn
                  (setq pt (vlax-get obj 'InsertionPoint))
                  (setq atts (mp:att-alist en))
                  (setq row "")
                  (foreach h *mp-csv-tags*
                    (setq val
                      (cond
                        ((= h "BLOQUE") (mp:getval "BLOQUE_BASE" atts bname))
                        ((= h "HANDLE") (vla-get-Handle obj))
                        ((= h "LAYER") (vla-get-Layer obj))
                        ((= h "X") (rtos (car pt) 2 3))
                        ((= h "Y") (rtos (cadr pt) 2 3))
                        (T (cdr (assoc (strcase h) atts)))))
                    (setq row (strcat row (mp:csv-safe val) *mp-csv-sep*)))
                  (write-line (vl-string-right-trim *mp-csv-sep* row) f)
                  (setq count (1+ count))))
              (setq i (1+ i)))))
        (close f)
        (princ (strcat "\nCSV exportado: " fn " | Registros: " (itoa count))))
      (princ "\nNo se pudo abrir el archivo CSV para escritura.")))
  (princ))

(defun mp:block-attdef-tags (blk / tags item)
  (setq tags nil)
  (vlax-for item blk
    (if (= (vla-get-ObjectName item) "AcDbAttributeDefinition")
      (setq tags (cons (strcase (vla-get-TagString item)) tags))))
  tags)

(defun mp:infer-base (bname atts / up red tipo)
  (setq up (strcase (mp:safe-str bname)))
  (cond
    ((/= (mp:getval "BLOQUE_BASE" atts "") "")
      (mp:getval "BLOQUE_BASE" atts ""))
    ((member up (mapcar 'strcase *mp-blocks*)) up)
    ((mp:starts-with up "MP_TRAMO_SAN_") "TRAMO_ARESIDUAL")
    ((mp:starts-with up "MP_TRAMO_PLU_") "TRAMO_ALLUVIAS")
    ((mp:starts-with up "MP_TRAMO_ACU_") "TRAMO_ACUEDUCTO")
    ((mp:starts-with up "MP_TRAMO_MT_") "TRAMO_E_MT")
    ((mp:starts-with up "MP_TRAMO_BTAP_") "TRAMO_E_BT_AP")
    ((= up "MP_PUNTO_POZO_SAN") "POZO_SANITARIO")
    ((= up "MP_PUNTO_POZO_PLU") "POZO_PLUVIAL")
    ((= up "MP_PUNTO_SUMIDERO") "SUMIDERO")
    ;; 2026-08-28: tambien los nombres por tipo (MP_PUNTO_ACC_ACU_TEE...)
    ((mp:starts-with up "MP_PUNTO_ACC_ACU") "ACCESORIO_ACUEDUCTO")
    ((= up "MP_PUNTO_CABEZAL") "CABEZAL_PLUVIAL")
    ((= up "MP_PUNTO_LUMINARIA") "LUMINARIA_AP")
    ((mp:starts-with up "MP_PUNTO_")
      (substr up 10))
    ((mp:starts-with up "CANT_TRAMO_")
      (setq red (strcase (mp:getval "RED" atts "")))
      (setq tipo (strcase (mp:getval "TIPO_RED" atts "")))
      (cond
        ((= red "ACUEDUCTO") "TRAMO_ACUEDUCTO")
        ((= red "ALLUVIAS") "TRAMO_ALLUVIAS")
        ((= red "ARESIDUAL") "TRAMO_ARESIDUAL")
        ((= tipo "MT") "TRAMO_E_MT")
        ((= tipo "BT/AP") "TRAMO_E_BT_AP")
        (T "")))
    (T "")))

(defun mp:base-is-tramo (base)
  (member base '("TRAMO_ARESIDUAL" "TRAMO_ALLUVIAS" "TRAMO_ACUEDUCTO" "TRAMO_E_MT" "TRAMO_E_BT_AP")))

(defun mp:desired-atts (base is-tramo / specs visible)
  (setq specs (if is-tramo (mp:base-atts-for base) (mp:base-atts-for-point base)))
  (setq visible
    (if (and is-tramo (member base '("TRAMO_ARESIDUAL" "TRAMO_ALLUVIAS" "TRAMO_ACUEDUCTO")))
      (list
        (list "ETIQUETA" "Etiqueta visible" "")
        (list "PENDIENTE_VIS" "Pendiente visible" ""))
      (if (and is-tramo (member base '("TRAMO_E_MT" "TRAMO_E_BT_AP")))
        '(("ETIQUETA" "Conductor / acometida" "")
          ("LONG_VIS" "Longitud y ducteria" ""))
        (list (list "ETIQUETA" "Etiqueta visible" "")))))
  (if is-tramo
    (append visible specs)
    (append visible (list (list "BLOQUE_BASE" "Bloque base" base)) specs)))

(defun mp:block-tramo-circle-span (blk / item center x minx maxx)
  ;; Los centros de los circulos definen la longitud geometrica completa.
  (setq minx nil maxx nil)
  (vlax-for item blk
    (if (= (vla-get-ObjectName item) "AcDbCircle")
      (progn
        (setq center
          (vlax-safearray->list
            (vlax-variant-value (vla-get-Center item))))
        (setq x (car center))
        (if (or (null minx) (< x minx)) (setq minx x))
        (if (or (null maxx) (> x maxx)) (setq maxx x)))))
  (if (and minx maxx (> (- maxx minx) 1e-9))
    (- maxx minx)
    0.0))

(defun mp:tramo-span-from-name (name / parts p tail)
  ;; MP_TRAMO_XXX_12_35 -> 12.35. El nombre lo genera
  ;; mp:tramo-block-name con rtos 2 2 ("."->"_"), asi que los DOS
  ;; ultimos campos separados por "_" son la parte entera y decimal.
  (setq name (mp:safe-str name) parts nil tail name)
  (while (setq p (vl-string-search "_" tail))
    (setq parts (cons (substr tail 1 p) parts))
    (setq tail (substr tail (+ p 2))))
  (setq parts (cons tail parts)) ;; parts en orden inverso
  (if (and (> (length parts) 1)
           (distof (car parts)) (distof (cadr parts)))
    (atof (strcat (cadr parts) "." (car parts)))
    0.0))

(defun mp:block-tramo-length (blk / item value best span)
  ;; Prioriza la distancia centro a centro para que el recorte visual
  ;; no reduzca LONGITUD ni las cantidades.
  (setq span (mp:block-tramo-circle-span blk))
  ;; 2026-08-28: los tramos sin circulos (hidro/MT/BT) devolvian el
  ;; largo de la POLILINEA actual -- si esta ya venia recortada, cada
  ;; re-normalizacion recortaba sobre lo recortado (los tramos ACU
  ;; quedaron "corticos" tras dos pasadas). El largo VERDADERO esta en
  ;; el nombre del bloque (inmutable): usarlo como segunda fuente.
  (if (< span 1e-9)
    (setq span (mp:tramo-span-from-name (vla-get-Name blk))))
  (if (> span 1e-9)
    span
    (progn
      (setq best 0.0)
      (vlax-for item blk
        (if (and (= (vla-get-ObjectName item) "AcDbPolyline")
                 (vlax-property-available-p item 'Length))
          (progn
            (setq value (vla-get-Length item))
            (if (> value best) (setq best value)))))
      best)))

(defun mp:normalize-tramo-graphics (blk base / item span cut width victims removed)
  ;; Ajusta definiciones existentes al borde de sus circulos.
  ;; 2026-08-26 FIX: usaba mp:hydro-tramo-p (copia duplicada desactualizada
  ;; de la logica de mp:make-cant-tramo-block) -- MT/BT-AP caian siempre
  ;; en la rama "cut" (circulos/recorte de pozo generico) porque no son
  ;; hydro, aunque YA tienen sus propios bloques punto (caja/poste) y
  ;; jamas debieron recortarse asi. Esta funcion corre SIEMPRE despues de
  ;; crear cualquier tramo (via mp:ensure-block-schema, llamado desde
  ;; mp:insert-cant-tramo) y estaba deshaciendo silenciosamente el fix de
  ;; "borde de caja" cada vez que se creaba/reconstruia un tramo MT/BTAP.
  (setq span (mp:block-tramo-length blk))
  (setq cut (min (max 2.0 *mp-vis-radius*) (/ span 4.0)))
  ;; 2026-08-28: MISMAS reglas de ancho que mp:make-cant-tramo-block --
  ;; esta copia usaba *mp-vis-width* (2.0) a secas y deshacia el trazo
  ;; delgado cada vez que se creaba/editaba un tramo (el mismo patron
  ;; del bug del gap MT del 26/08: logica duplicada sin sincronizar).
  (setq width (max 0.01 (mp:cfg-tramo-width *mp-vis-width*)))
  ;; Los circulos de extremos de un tramo hidrosanitario/MT/BT-AP no son
  ;; pozos: eran geometria duplicada. El nodo real es su INSERT puntual
  ;; enlazado (pozo/caja/poste).
  (if (mp:tramo-own-node-blocks-p base)
    (progn
      (vlax-for item blk
        (if (= (vla-get-ObjectName item) "AcDbCircle")
          (setq victims (cons item victims))))
      (foreach item victims
        (if (urb:safe-delete item) (setq removed (1+ (if removed removed 0)))))))
  (if (> span 1e-9)
    (vlax-for item blk
      (if (= (vla-get-ObjectName item) "AcDbPolyline")
        (progn
          (vla-put-Coordinates
            item
            (mp:var-dbls
              (cond
                ((mp:tramo-own-node-blocks-p base)
                  (list 0.0 0.0 span 0.0))
                (T (list cut 0.0 (- span cut) 0.0)))))
          (vla-put-ConstantWidth item (float width))
          (vla-Update item)))))
  (list span (if removed removed 0)))

(defun mp:repair-hydro-tramo-definitions
  (/ blocks blk bname base result removed)
  ;; Migra definiciones compartidas ya existentes. No borra ningun INSERT
  ;; de pozo ni modifica sus atributos; solo retira los anillos falsos de
  ;; los bloques lineales CANT_TRAMO/MP_TRAMO hidrosanitarios.
  (setq blocks (vla-get-Blocks (urb:doc)) removed 0)
  (vlax-for blk blocks
    (if (and (= (vla-get-IsLayout blk) :vlax-false)
             (= (vla-get-IsXRef blk) :vlax-false))
      (progn
        (setq bname (vla-get-Name blk)
              base (mp:infer-base bname nil))
        (if (and (mp:base-is-tramo base) (mp:hydro-tramo-p base))
          (progn
            (setq result (mp:normalize-tramo-graphics blk base))
            (setq removed (+ removed (cadr result))))))))
  removed)

(defun mp:normalize-visible-attdefs (blk is-tramo base / item tag span pos)
  (if is-tramo
    (progn
      (setq span (mp:block-tramo-length blk))
      (vlax-for item blk
        (if (= (vla-get-ObjectName item) "AcDbAttributeDefinition")
          (progn
            (setq tag (strcase (vla-get-TagString item)))
            (if (member tag '("ETIQUETA" "PENDIENTE_VIS" "LONG_VIS"))
              (progn
                (setq pos
                  (list
                    (/ span 2.0)
                    (if (= tag "ETIQUETA")
                      (mp:tramo-label-offset *mp-vis-tramo-text-height*)
                      (- (mp:tramo-label-offset *mp-vis-tramo-text-height*)))
                    0.0))
                (mp:center-visible-att item pos *mp-vis-tramo-text-height*)))))))
    (if (member base '("POZO_SANITARIO" "POZO_PLUVIAL"))
      (vlax-for item blk
        (if (and
              (= (vla-get-ObjectName item) "AcDbAttributeDefinition")
              (= (strcase (vla-get-TagString item)) "ETIQUETA"))
          (mp:center-visible-att item '(0.0 0.0 0.0) *mp-vis-text-height*))))))

(defun mp:ensure-block-schema (bname base is-tramo / doc blks blk tags specs lay col y added spec tag invisible span pos height display-height)
  (setq doc (vla-get-ActiveDocument (vlax-get-acad-object)))
  (setq blks (vla-get-Blocks doc))
  (setq blk (vl-catch-all-apply 'vla-Item (list blks bname)))
  (if (vl-catch-all-error-p blk)
    0
    (progn
      (if is-tramo (mp:normalize-tramo-graphics blk base))
      (mp:normalize-visible-attdefs blk is-tramo base)
      (setq tags (mp:block-attdef-tags blk))
      (setq specs (mp:desired-atts base is-tramo))
      (setq lay (if is-tramo (mp:vis-layer base) (mp:point-layer base)))
      (setq col (if is-tramo (mp:vis-color base) (mp:point-color base)))
      (setq display-height
        (if is-tramo *mp-vis-tramo-text-height* *mp-vis-text-height*))
      (setq span (if is-tramo (mp:block-tramo-length blk) 0.0))
      (setq y -100.0 added 0)
      (foreach spec specs
        (setq tag (strcase (car spec)))
        (if (not (member tag tags))
          (progn
            (setq invisible (not (member tag '("ETIQUETA" "PENDIENTE_VIS" "LONG_VIS"))))
            (setq pos
              (cond
                ((= tag "ETIQUETA") (list (/ span 2.0) (mp:tramo-label-offset display-height) 0.0))
                ((member tag '("PENDIENTE_VIS" "LONG_VIS")) (list (/ span 2.0) (- (mp:tramo-label-offset display-height)) 0.0))
                (T (list 0.0 y 0.0))))
            (setq height (if invisible 0.10 (max 0.10 display-height)))
            (mp:vla-add-att
              blk
              tag
              (cadr spec)
              (if (caddr spec) (caddr spec) "")
              pos
              height
              invisible
              lay
              col)
            (setq tags (cons tag tags))
            (setq y (- y 0.20))
            (setq added (1+ added)))))
      added)))

(defun mp:definition-record (bname defs)
  (assoc (strcase bname) defs))

;; 5.5.10: migracion SOLO de presentacion electrica, una vez por DWG.
;; No llama sync-tramo-values: no recalcula TN, longitudes ni presupuesto.
;; ATTSYNC se agrupa por definicion. Respaldar TODAS las referencias antes
;; de sincronizar y restaurarlas despues evita que defaults sobrescriban XDATA.
(defun mp:ensure-electrical-display-schema (bname / blk tags span lay col spec tag pos att added)
  (setq blk (vla-Item (vla-get-Blocks (urb:doc)) bname)
        tags (mp:block-attdef-tags blk)
        span (mp:block-tramo-length blk)
        lay (mp:vis-layer (mp:infer-base bname nil))
        col (mp:vis-color (mp:infer-base bname nil)) added 0)
  (foreach spec '(("DUCTOS" "Numero de tubos")
                  ("DIAM_DUCTO" "Diametro de tubo (pulgadas)")
                  ("CONDUCTOR" "Conductor / acometida")
                  ("ETIQUETA" "Conductor / acometida visible")
                  ("LONG_VIS" "Longitud y ducteria"))
    (setq tag (car spec))
    (if (not (member tag tags))
      (progn
        (setq pos (if (member tag '("ETIQUETA" "LONG_VIS"))
                    (list (/ span 2.0)
                      (* (mp:tramo-label-offset *mp-vis-tramo-text-height*)
                         (if (= tag "ETIQUETA") 1.0 -1.0)) 0.0)
                    (list 0.0 (- -100.0 added) 0.0)))
        (setq att (mp:vla-add-att blk tag (cadr spec) "" pos
                    (if (member tag '("ETIQUETA" "LONG_VIS")) *mp-vis-tramo-text-height* 0.10)
                    (not (member tag '("ETIQUETA" "LONG_VIS"))) lay col))
        (if (member tag '("ETIQUETA" "LONG_VIS"))
          (mp:center-visible-att att pos *mp-vis-tramo-text-height*))
        (setq added (1+ added)))))
  added)

(defun mp:electrical-display-values (vals / conductor)
  ;; Canonizar el alias legado solo si contiene un dato real. Vacio NO es 6".
  (setq conductor (mp:getval "CONDUCTOR" vals (mp:getval "CONDUCTORES" vals "")))
  (setq vals (mp:alist-set vals "CONDUCTOR" conductor)
        vals (mp:alist-set vals "DUCTOS" (mp:getval "DUCTOS" vals ""))
        vals (mp:alist-set vals "DIAM_DUCTO" (mp:getval "DIAM_DUCTO" vals "")))
  (setq vals (mp:alist-set vals "ETIQUETA" (if (/= conductor "") conductor "Conductor: sin dato")))
  (mp:alist-set vals "LONG_VIS" (mp:long-label vals)))

(defun mp:refresh-electrical-display
  (/ ss i en obj vals base name refs defs rec result failed count missing doc old-echo)
  (setq ss (ssget "_X" '((0 . "INSERT") (66 . 1)))
        i 0 count 0 failed 0 missing 0)
  (if ss (repeat (sslength ss)
    (setq en (ssname ss i) i (1+ i) obj (vlax-ename->vla-object en)
          name (vla-get-EffectiveName obj) vals (mp:att-alist en)
          base (mp:infer-base name vals))
    (if (member base '("TRAMO_E_MT" "TRAMO_E_BT_AP"))
      (progn
        (setq refs (cons (list en name vals) refs))
        (if (not (member name defs)) (setq defs (cons name defs)))))))
  (setq doc (urb:doc) old-echo (getvar "CMDECHO"))
  (vla-StartUndoMark doc)
  (setvar "CMDECHO" 0)
  (setq result (vl-catch-all-apply
    '(lambda ()
       (foreach name defs
         (setq result (vl-catch-all-apply
           '(lambda ()
              (if (> (mp:ensure-electrical-display-schema name) 0)
                (vl-cmdf "_.ATTSYNC" "_N" name))) nil))
         (if (vl-catch-all-error-p result) (setq failed (1+ failed))))
       ;; Actualizar solo referencias visibles. XDATA/cantidades ya estan
       ;; validos y no se reescriben: evita una serializacion completa por
       ;; cada tramo del dibujo.
       (foreach rec refs
         (setq vals (mp:electrical-display-values (caddr rec)))
         (setq result
           (vl-catch-all-apply
             '(lambda ()
                ;; Poblar referencias tecnicas nuevas desde alias historicos,
                ;; sin tocar MP_CANT_DATA ni las cantidades.
                (mp:setatt-visible-only (car rec) "DUCTOS"
                  (mp:getval "DUCTOS" vals ""))
                (mp:setatt-visible-only (car rec) "DIAM_DUCTO"
                  (mp:getval "DIAM_DUCTO" vals ""))
                (mp:setatt-visible-only (car rec) "CONDUCTOR"
                  (mp:getval "CONDUCTOR" vals ""))
                (mp:setatt-visible-only (car rec) "ETIQUETA"
                  (mp:getval "ETIQUETA" vals "Conductor: sin dato"))
                (mp:setatt-visible-only (car rec) "LONG_VIS"
                  (mp:getval "LONG_VIS" vals "L=? m | ? tubos de ?\""))) nil))
         (if (vl-catch-all-error-p result)
           (setq failed (1+ failed))
           (progn
             (setq count (1+ count))
             (if (or (= (mp:getval "DIAM_DUCTO" vals "") "")
                     (= (mp:getval "CONDUCTOR" vals "") ""))
               (setq missing (1+ missing))))))) nil))
  (setvar "CMDECHO" old-echo)
  (vla-EndUndoMark doc)
  (if (vl-catch-all-error-p result) (setq failed (1+ failed)))
  (list count failed missing))

;; ---------- 5.6.0 quitar WIPEOUT de los simbolos de redes ----------
;; Reporte del usuario: "los accesorios de acueducto estan quedando como en
;; recuadro que cuando se sobreponen varios elementos ese recuadro hace que
;; lo que este por debajo no se vea nada". Sonda en copia del maestro
;; (2026-09-16): las 13 definiciones MP_PUNTO_ACC_ACU_* (450 inserciones)
;; traian UN AcDbWipeout cada una. Ningun codigo del plugin crea wipeouts
;; (ni el LSP ni los DLL, revisada la historia git): llegaron al dibujo
;; por fuera -- bloques homonimos pegados desde otro plano o editados a
;; mano. Como las inserciones apuntan a la DEFINICION, quitarlo de la
;; definicion arregla todas a la vez. Se limita a bloques del plugin.
(defun mp:strip-network-wipeouts (/ blk victims item n defs)
  (setq n 0 defs 0)
  (vlax-for blk (vla-get-Blocks (urb:doc))
    (if (and (= (vla-get-IsLayout blk) :vlax-false)
             (= (vla-get-IsXRef blk) :vlax-false)
             (wcmatch (strcase (vla-get-Name blk))
               "MP_PUNTO_*,CANT_TRAMO_*,MP_TRAMO_*,CANT_PUNTO_*"))
      (progn
        (setq victims nil)
        (vlax-for item blk
          (if (= (vla-get-ObjectName item) "AcDbWipeout")
            (setq victims (cons item victims))))
        (if victims (setq defs (1+ defs)))
        (foreach item victims
          (if (urb:safe-delete item) (setq n (1+ n)))))))
  (list n defs))

;; una sola definicion (al crear o reusar un simbolo) -- barato
(defun mp:strip-wipeouts-in-block (bname / blk victims item)
  (setq blk (vl-catch-all-apply 'vla-Item
              (list (vla-get-Blocks (urb:doc)) bname)))
  (if (not (vl-catch-all-error-p blk))
    (progn
      (vlax-for item blk
        (if (= (vla-get-ObjectName item) "AcDbWipeout")
          (setq victims (cons item victims))))
      (foreach item victims (urb:safe-delete item))
      (length victims))
    0))

;; ---------- 5.6.1 accesorios: grosor, encima de tuberias, numero pegado ----------
;; Pedido del usuario: "el espesor de los accesorios igual que los tramos,
;; que siempre se vean por encima de los tramos de tuberia y que el numero
;; del accesorio este mas pegado al accesorio".

;; Redibuja las definiciones MP_PUNTO_ACC_ACU_* existentes con el trazo
;; actual (ancho de tramo). Conserva sus atributos: solo cambia geometria,
;; y todas las inserciones toman el cambio a la vez.
(defun mp:rebuild-acc-definitions (/ blk nm victims item lay col n)
  (setq lay (mp:point-layer "ACCESORIO_ACUEDUCTO")
        col (mp:point-color "ACCESORIO_ACUEDUCTO") n 0)
  (vlax-for blk (vla-get-Blocks (urb:doc))
    (setq nm (strcase (vla-get-Name blk)))
    (if (and (= (vla-get-IsLayout blk) :vlax-false)
             (= (vla-get-IsXRef blk) :vlax-false)
             (wcmatch nm "MP_PUNTO_ACC_ACU_*"))
      (progn
        (setq victims nil)
        (vlax-for item blk
          (if (/= (vla-get-ObjectName item) "AcDbAttributeDefinition")
            (setq victims (cons item victims))))
        (foreach item victims (urb:safe-delete item))
        ;; "MP_PUNTO_ACC_ACU_" son 17 caracteres: el resto es el token
        (mp:acc-plan-geom-tk blk (substr nm 18) lay col)
        (setq n (1+ n)))))
  (setq *mp-acc-bbox-cache* nil)
  n)

;; caja de la GEOMETRIA de una definicion (sin atributos), en coordenadas
;; locales: (xmin ymin xmax ymax). Se cachea por nombre.
(defun mp:block-geom-bbox (bname / blk item lo hi r x0 y0 x1 y1 hit)
  (if (setq hit (assoc (strcase bname)
                  (if (boundp '*mp-acc-bbox-cache*) *mp-acc-bbox-cache* nil)))
    (cdr hit)
    (progn
      (setq blk (vl-catch-all-apply 'vla-Item
                  (list (vla-get-Blocks (urb:doc)) bname)))
      (if (not (vl-catch-all-error-p blk))
        (vlax-for item blk
          (if (/= (vla-get-ObjectName item) "AcDbAttributeDefinition")
            (progn
              (setq r (vl-catch-all-apply 'vla-GetBoundingBox (list item 'lo 'hi)))
              (if (not (vl-catch-all-error-p r))
                (progn
                  (setq lo (vlax-safearray->list lo) hi (vlax-safearray->list hi))
                  (if (or (null x0) (< (car lo) x0)) (setq x0 (car lo)))
                  (if (or (null y0) (< (cadr lo) y0)) (setq y0 (cadr lo)))
                  (if (or (null x1) (> (car hi) x1)) (setq x1 (car hi)))
                  (if (or (null y1) (> (cadr hi) y1)) (setq y1 (cadr hi)))))))))
      (setq r (if x0 (list x0 y0 x1 y1) '(-0.5 -0.5 0.5 0.5)))
      (setq *mp-acc-bbox-cache*
        (cons (cons (strcase bname) r)
          (if (boundp '*mp-acc-bbox-cache*) *mp-acc-bbox-cache* nil)))
      r)))

;; Numero del accesorio JUSTO al lado del simbolo, horizontal y legible:
;; se calcula la caja real del simbolo ya girado en el plano; si el simbolo
;; queda tendido en horizontal el numero va ENCIMA, si queda en vertical va
;; a la DERECHA, a 0.15 m del trazo. Antes colgaba a una distancia fija
;; debajo del simbolo en coordenadas locales, y al girar el accesorio
;; quedaba lejos y del lado que no era.
(defun mp:place-acc-label (en / obj ed ip rot sx sy bb xs ys c wx wy
                           x0 x1 y0 y1 a h gap)
  (setq obj (vlax-ename->vla-object en)
        ed (entget en) ip (cdr (assoc 10 ed)) rot (cdr (assoc 50 ed))
        sx (cdr (assoc 41 ed)) sy (cdr (assoc 42 ed)) gap 0.15)
  (setq bb (mp:block-geom-bbox (vla-get-EffectiveName obj)))
  (foreach c (list (list (nth 0 bb) (nth 1 bb)) (list (nth 2 bb) (nth 1 bb))
                   (list (nth 2 bb) (nth 3 bb)) (list (nth 0 bb) (nth 3 bb)))
    (setq wx (+ (car ip) (- (* sx (car c) (cos rot)) (* sy (cadr c) (sin rot))))
          wy (+ (cadr ip) (+ (* sx (car c) (sin rot)) (* sy (cadr c) (cos rot)))))
    (setq xs (cons wx xs) ys (cons wy ys)))
  (setq x0 (apply 'min xs) x1 (apply 'max xs)
        y0 (apply 'min ys) y1 (apply 'max ys))
  (if (= (vla-get-HasAttributes obj) :vlax-true)
    (foreach a (vlax-invoke obj 'GetAttributes)
      (if (= (strcase (vla-get-TagString a)) "ETIQUETA")
        (progn
          (setq h (vla-get-Height a))
          (vl-catch-all-apply 'vla-put-Rotation (list a 0.0))
          (if (>= (- x1 x0) (- y1 y0))
            (progn
              (vl-catch-all-apply 'vla-put-Alignment (list a 10))
              (vl-catch-all-apply 'vla-put-TextAlignmentPoint
                (list a
                  (mp:3d (list (/ (+ x0 x1) 2.0) (+ y1 gap (/ h 2.0)) 0.0)))))
            (progn
              (vl-catch-all-apply 'vla-put-Alignment (list a 9))
              (vl-catch-all-apply 'vla-put-TextAlignmentPoint
                (list a
                  (mp:3d (list (+ x1 gap) (/ (+ y0 y1) 2.0) 0.0))))))
          (vla-Update a)))))
  T)

;; Simbolos de red (pozos, sumideros, cajas, accesorios) SIEMPRE encima de
;; las tuberias: tabla de orden de dibujo del espacio modelo. Con enames
;; mueve solo esos; sin argumento mueve todos los MP_PUNTO_* (despues de
;; crear un tramo, que por ser nuevo quedaria dibujado encima).
(defun mp:points-to-top (enames / ss i objs ms dict st)
  (if (null enames)
    (progn
      (setq ss (ssget "_X" '((0 . "INSERT") (2 . "MP_PUNTO_*"))) i 0)
      (if ss (repeat (sslength ss)
        (setq enames (cons (ssname ss i) enames) i (1+ i))))))
  (setq objs (mapcar 'vlax-ename->vla-object enames))
  (if objs
    (progn
      (setq ms (vla-get-ModelSpace (urb:doc))
            dict (vla-GetExtensionDictionary ms)
            st (vl-catch-all-apply 'vla-GetObject (list dict "ACAD_SORTENTS")))
      (if (vl-catch-all-error-p st)
        (setq st (vla-AddObject dict "ACAD_SORTENTS" "AcDbSortentsTable")))
      (vla-MoveToTop st (urb:object-array-variant objs))
      (length objs))
    0))

;; una vez por DWG y cada vez que cambie el ancho de los tramos
(defun mp:migrate-accessory-look (/ w n ss i)
  (setq w (rtos (mp:acc-line-width) 2 4))
  (if (/= (urb:safe-string (urb:config-read "URB_ACC_LOOK_561B") "") w)
    (progn
      (setq n (mp:rebuild-acc-definitions))
      (setq ss (ssget "_X" '((0 . "INSERT") (2 . "MP_PUNTO_ACC_ACU_*"))) i 0)
      (if ss (repeat (sslength ss)
        (vl-catch-all-apply 'mp:place-acc-label (list (ssname ss i)))
        (setq i (1+ i))))
      (vl-catch-all-apply 'mp:points-to-top (list nil))
      (urb:config-write "URB_ACC_LOOK_561B" w)
      (if (> n 0)
        (prompt (strcat "\nAccesorios de acueducto: " (itoa n)
          " simbolos con el grosor de los tramos, encima de las tuberias y con el numero junto al simbolo.")))
      n)
    0))

(defun mp:migrate-network-wipeouts (/ result)
  (if (/= (urb:safe-string (urb:config-read "URB_SIN_WIPEOUT_560") "") "OK")
    (progn
      (setq result (mp:strip-network-wipeouts))
      (urb:config-write "URB_SIN_WIPEOUT_560" "OK")
      (if (> (car result) 0)
        (progn
          (vla-Regen (urb:doc) 1)
          (prompt (strcat "\nSimbolos de redes: se quitaron " (itoa (car result))
            " mascaras (wipeout) de " (itoa (cadr result))
            " definiciones; ya no tapan lo que queda debajo."))))
      result)
    '(0 0)))

(defun mp:migrate-electrical-display (/ result)
  (if (/= (urb:safe-string (urb:config-read "URB_ELECT_LABELS_5510") "") "OK")
    (progn
      (setq result (mp:refresh-electrical-display))
      (if (= (cadr result) 0)
        (urb:config-write "URB_ELECT_LABELS_5510" "OK"))
      (if (or (> (car result) 0) (> (cadr result) 0))
        (prompt (strcat "\nEtiquetas electricas: " (itoa (car result))
          " actualizadas; " (itoa (cadr result)) " fallidas; "
          (itoa (caddr result)) " con diametro/conductor sin dato (no se inventaron valores).")))
      result)
    '(0 0 0)))

(defun mp:remove-duplicate-points (/ ss i en obj base atts id ip kept rec removed tol candidate)
  ;; Solo elimina coincidencias inequivocas: mismo tipo, ID y coordenada.
  (setq ss (ssget "X" '((0 . "INSERT"))))
  (setq kept nil removed 0 tol 0.50)
  (if ss
    (progn
      (setq i 0)
      (while (< i (sslength ss))
        (setq en (ssname ss i))
        (setq base (mp:point-reference-base en))
        (if (/= base "")
          (progn
            (setq obj (vlax-ename->vla-object en))
            (setq atts (mp:att-alist en))
            (setq id
              (strcase
                (vl-string-trim
                  " "
                  (mp:getval "ID" atts (mp:getval "CODIGO" atts "")))))
            (setq ip (vlax-get obj 'InsertionPoint))
            (setq rec nil)
            (if (/= id "")
              (foreach candidate kept
                (if (and
                      (null rec)
                      (= (car candidate) base)
                      (= (cadr candidate) id)
                      (<= (mp:distance-2d ip (caddr candidate)) tol))
                  (setq rec candidate))))
            (if rec
              (progn
                (entdel en)
                (setq removed (1+ removed)))
              (setq kept (cons (list base id ip en) kept)))))
        (setq i (1+ i)))))
  removed)

(defun mp:referenced-endpoint-handles
  (/ ss index ename obj atts base handle result)
  ;; 2026-09-03 (misma optimizacion del reactor de borrado): solo los
  ;; bloques de TRAMO pueden referenciar extremos -- filtrar por nombre
  ;; evita el barrido COM de todos los inserts del master en cada ERASE.
  (setq ss (ssget "_X" '((0 . "INSERT") (2 . "MP_TRAMO_*,TRAMO_*,CANT_TRAMO_*")))
        index 0
        result nil)
  (if ss
    (while (< index (sslength ss))
      (setq ename (ssname ss index)
            obj (vlax-ename->vla-object ename)
            atts (mp:att-alist ename)
            base
              (mp:infer-base
                (vla-get-EffectiveName obj) atts))
      (if (mp:base-is-tramo base)
        (foreach handle
          (list
            (mp:getval "HANDLE_EXTREMO_INI" atts "")
            (mp:getval "HANDLE_EXTREMO_FIN" atts ""))
          (if (and (/= handle "")
                   (not (member (strcase handle) result)))
            (setq result (cons (strcase handle) result)))))
      (setq index (1+ index))))
  result)

(defun mp:cleanup-orphan-auto-points
  (/ referenced ss index ename base atts origin handle deleted result)
  ;; Solo se eliminan puntos creados como auxiliares de un tramo. Los puntos
  ;; creados desde el menu, los heredados y los compartidos se conservan.
  ;; 2026-09-03 (reporte del usuario: "al borrar un elemento se demora
  ;; mucho cargando"): esta limpieza corre tras CADA ERASE (reactor) y
  ;; escaneaba TODOS los inserts del dibujo con llamadas COM. Ahora el
  ;; ssget filtra por NOMBRE a los unicos candidatos posibles (bloques
  ;; punto MP_PUNTO_*/CANT_PUNTO_*) -- de miles de inserts a decenas.
  (setq referenced (mp:referenced-endpoint-handles)
        ss (ssget "_X" '((0 . "INSERT") (2 . "MP_PUNTO_*,CANT_PUNTO_*")))
        index 0
        deleted 0)
  (if ss
    (while (< index (sslength ss))
      (setq ename (ssname ss index))
      ;; el ssget ya filtro por nombre de bloque punto -- no hace falta
      ;; inferir la base con COM (EffectiveName) por cada insert
      (if (urb:q-modelspace-p ename)
        (progn
          (setq atts (mp:att-alist ename)
                origin
                  (strcase
                    (mp:getval "ORIGEN_CREACION" atts "MANUAL"))
                handle (strcase (cdr (assoc 5 (entget ename)))))
          (if (and
                (= origin "AUTO_TRAMO")
                (not (member handle referenced)))
            (progn
              (setq result
                (vl-catch-all-apply 'entdel (list ename)))
              (if (and
                    (not (vl-catch-all-error-p result))
                    result)
                (setq deleted (1+ deleted)))))))
      (setq index (1+ index))))
  (if (> deleted 0)
    (prompt
      (strcat
        "\nExtremos automaticos huerfanos eliminados: "
        (itoa deleted) ".")))
  deleted)

;; 2026-09-03 (medido en el master real: cada ERASE de CUALQUIER cosa
;; costaba ~7 s por el barrido del reactor). Compuerta barata: el conteo
;; de TRAMOS se toma al INICIAR el comando (ssget por nombre, sin COM,
;; milisegundos) y la limpieza de extremos huerfanos solo corre si el
;; borrado realmente elimino tramos -- el 95% de los borrados (textos,
;; vias, prefabricados, puntos sueltos) queda instantaneo.
(defun mp:count-tramos-fast (/ ss)
  (setq ss (ssget "_X"
    '((0 . "INSERT") (2 . "MP_TRAMO_*,TRAMO_*,CANT_TRAMO_*"))))
  (if ss (sslength ss) 0))

(defun mp:on-network-command-start
  (reactor command-data / command)
  (setq command
    (strcase
      (mp:safe-str
        (if command-data (car command-data) ""))))
  (if (member command '("ERASE" "DELETE" "BORRAR"))
    (setq *mp-pre-erase-tramos* (mp:count-tramos-fast)))
  (princ))

(defun mp:on-network-command-ended
  (reactor command-data / command result)
  (setq command
    (strcase
      (mp:safe-str
        (if command-data (car command-data) ""))))
  (if (and (member command '("ERASE" "DELETE" "BORRAR"))
           (or (not (boundp '*mp-pre-erase-tramos*))
               (null *mp-pre-erase-tramos*)
               (/= (mp:count-tramos-fast) *mp-pre-erase-tramos*)))
    (setq result
      (vl-catch-all-apply 'mp:cleanup-orphan-auto-points nil)))
  (setq *mp-pre-erase-tramos* nil)
  (princ))

(defun mp:install-network-erase-reactor (/ old)
  (if (and
        (boundp '*mp-network-erase-reactor*)
        *mp-network-erase-reactor*)
    (vl-catch-all-apply
      'vlr-remove (list *mp-network-erase-reactor*)))
  (setq *mp-network-erase-reactor*
    (vlr-command-reactor
      nil
      '((:vlr-commandWillStart . mp:on-network-command-start)
        (:vlr-commandEnded . mp:on-network-command-ended))))
  *mp-network-erase-reactor*)

(defun urb:update-network-blocks-command
  (/ ss i en obj bname atts base is-tramo handle refs defs rec added
   total-added sync-errors sync-result doc removed-dups duplicate-choice
   undo-open *error*)
  (vl-load-com)
  (mp:ensure-layers)
  (setq doc (vla-get-ActiveDocument (vlax-get-acad-object)))
  (defun *error* (message)
    (if undo-open
      (progn
        (vl-catch-all-apply 'vla-EndUndoMark (list doc))
        (setq undo-open nil)))
    (if (and message
             (not (member message '("Function cancelled" "quit / exit abort"))))
      (prompt (strcat "\nError al actualizar redes: " message)))
    (princ))
  ;; La eliminacion ya no es automatica: el valor por defecto conserva
  ;; todo. Si el usuario acepta, la migracion completa queda en un UNDO.
  (initget "Si No")
  (setq duplicate-choice
    (getkword
      "\nEliminar pozos/puntos duplicados durante la actualizacion [Si/No] <No>: "))
  (vla-StartUndoMark doc)
  (setq undo-open T)
  (setq removed-dups
    (if (= duplicate-choice "Si") (mp:remove-duplicate-points) 0))
  (setq ss (ssget "X" '((0 . "INSERT"))))
  (setq refs nil defs nil total-added 0 sync-errors 0)
  (if ss
    (progn
      ;; Primera pasada: conserva todos los valores y agrupa definiciones.
      (setq i 0)
      (while (< i (sslength ss))
        (setq en (ssname ss i))
        (setq obj (vlax-ename->vla-object en))
        (setq bname (vla-get-EffectiveName obj))
        (if (mp:is-cant-blockname bname)
          (progn
            (setq atts (mp:att-alist en))
            (setq base (mp:infer-base bname atts))
            (if (/= base "")
              (progn
                (setq is-tramo (mp:base-is-tramo base))
                (setq handle (vla-get-Handle obj))
                (setq refs (cons (list handle bname base is-tramo atts) refs))
                (if (not (mp:definition-record bname defs))
                  (setq defs (cons (list (strcase bname) bname base is-tramo) defs)))))))
        (setq i (1+ i)))

      ;; Segunda pasada: agrega ATTDEF faltantes y sincroniza cada definicion.
      (foreach rec defs
        (setq bname (cadr rec) base (caddr rec) is-tramo (cadddr rec))
        (setq added (mp:ensure-block-schema bname base is-tramo))
        (setq total-added (+ total-added added))
        (setq sync-result (vl-catch-all-apply 'vl-cmdf (list "_.ATTSYNC" "_N" bname)))
        (if (vl-catch-all-error-p sync-result)
          (setq sync-errors (1+ sync-errors))))

      ;; Tercera pasada: restaura valores por handle y repara longitud/etiquetas.
      (foreach rec refs
        (setq en (handent (car rec)))
        (if en
          (progn
            (setq base (caddr rec))
            (setq atts (nth 4 rec))
            (mp:setatts en atts)
            (mp:setatt-one en "BLOQUE_BASE" base)
            (mp:update-block-after-edit en nil))))

      (vla-Regen doc 1)
      (princ
        (strcat
          "\nActualizacion de redes terminada. Bloques: " (itoa (length defs))
          " | Referencias: " (itoa (length refs))
          " | Atributos nuevos: " (itoa total-added)
          " | Pozos duplicados eliminados: " (itoa removed-dups)
          " | Errores de sincronizacion: " (itoa sync-errors))))
    (princ "\nNo se encontraron bloques insertados."))
  (if undo-open
    (progn
      (vla-EndUndoMark doc)
      (setq undo-open nil)))
  (princ))
(defun urb:repair-network-visibility-command (/ doc)
  (mp:ensure-layers)
  (setq doc (vla-get-ActiveDocument (vlax-get-acad-object)))
  (vla-Regen doc 1)
  (princ "\nCapas PPTO encendidas, descongeladas y desbloqueadas. Dibujo regenerado.")
  (princ))

(defun urb:initialize-network-module-command ()
  (mp:ensure-layers)
  (princ "\nRedes Maipore listas. Use URBANISMO para crear, mantener y exportar; use EDITAR para modificar elementos.")
  (princ))

(princ "\nFunciones de redes integradas en el menu URBANISMO.")
(princ)

;;; ============================================================
;;; MODULO URBANISMO 4 - MENU, VIAS Y PERFILES ESTRATIGRAFICOS
;;; ============================================================

(setq *urb-road-profile-types*
  '("Volumen" "Geotextil" "Geomalla" "Tratamiento"))
(setq *urb-road-profile-scopes* '("Total" "Base"))
(setq *urb-road-alignment-modes* '("Existente" "Nuevo"))
(setq *urb-road-cota-modes* '("Pendiente" "Textos por capa"))
(setq *urb-road-overwidth-modes* '("Ambos" "Derecho" "Izquierdo"))
;; Parametros geometricos editables por dibujo. El dialogo de via solo
;; decide el COSTADO; las magnitudes se administran en Ajustes para que no
;; cambien accidentalmente de una via a otra.
(setq *urb-road-overwidth-left* 1.00)
(setq *urb-road-overwidth-right* 1.00)
(setq *urb-road-crossfall* 0.02)
(setq *urb-road-earthwork-interval* 2.50)
(setq *urb-road-max-earthwork-depth* 20.0)
(setq *urb-anden-default-width* 3.50)
;; Perfiles de diseno segun Figura 4.1 (estructuras de pavimento) y
;; estudio de suelos AUS-10786-10 (Alfonso Uribe S.).
;; Capas de arriba hacia abajo, espesores en metros.
;; Geotextil tejido Tipo 2400 (40 kN/m) sobre el rajon en todos los
;; perfiles; traslapo 15% equivale a ~45 cm por rollo (rango 30-60 cm).
;; El rajon de Figura 4.1 incluye el sello de 10 cm.
;;
;; Quinto campo por capa (2026-07-06, opcional): "Base" = se cuantifica
;; solo con el area de la calzada principal, SIN sobreanchos; "Total" o
;; ausente = area completa CON sobreanchos (comportamiento de siempre).
;; Confirmado con el usuario: solo la carpeta asfaltica (Rodadura +
;; Intermedia) va sin sobreancho -- las capas granulares y el
;; mejoramiento si dan soporte estructural hasta el sobreancho.
(setq *urb-road-default-profiles*
  '(("MPD"
      (("Rodadura MDC-19" "Volumen" "0.05" "0" "Base")
       ("Intermedia MDC-25" "Volumen" "0.05" "0" "Base")
       ("Base granular BG" "Volumen" "0.20" "0")
       ("Subbase granular SBG" "Volumen" "0.30" "0")
       ("Geotextil tejido T2400" "Geotextil" "0" "15")
       ("Mejoramiento rajon y sello" "Volumen" "0.40" "0")))
    ("MPI"
      (("Rodadura MDC-19" "Volumen" "0.05" "0" "Base")
       ("Intermedia MDC-25" "Volumen" "0.07" "0" "Base")
       ("Base granular BG" "Volumen" "0.20" "0")
       ("Subbase granular SBG" "Volumen" "0.25" "0")
       ("Geotextil tejido T2400" "Geotextil" "0" "15")
       ("Mejoramiento rajon y sello" "Volumen" "0.40" "0")))
    ("MPK"
      (("Rodadura MDC-19" "Volumen" "0.05" "0" "Base")
       ("Intermedia MDC-25" "Volumen" "0.08" "0" "Base")
       ("Base granular BG" "Volumen" "0.20" "0")
       ("Subbase granular SBG" "Volumen" "0.30" "0")
       ("Geotextil tejido T2400" "Geotextil" "0" "15")
       ("Mejoramiento rajon y sello" "Volumen" "0.40" "0")))
    ("MPG"
      (("Rodadura MDC-19" "Volumen" "0.05" "0" "Base")
       ("Intermedia MDC-25" "Volumen" "0.08" "0" "Base")
       ("Base granular BG" "Volumen" "0.20" "0")
       ("Subbase granular SBG" "Volumen" "0.35" "0")
       ("Geotextil tejido T2400" "Geotextil" "0" "15")
       ("Mejoramiento rajon y sello" "Volumen" "0.40" "0")))
    ("VIA B0"
      (("Rodadura MDC-19" "Volumen" "0.05" "0" "Base")
       ("Intermedia MDC-25" "Volumen" "0.09" "0" "Base")
       ("Base granular BG" "Volumen" "0.20" "0")
       ("Subbase granular SBG" "Volumen" "0.25" "0")
       ("Geotextil tejido T2400" "Geotextil" "0" "15")
       ("Mejoramiento rajon y sello" "Volumen" "0.40" "0")))
    ("MPB2-MPC-MPJ-MPHA-MPHB"
      (("Rodadura MDC-19" "Volumen" "0.05" "0" "Base")
       ("Intermedia MDC-25" "Volumen" "0.09" "0" "Base")
       ("Base granular BG" "Volumen" "0.20" "0")
       ("Subbase granular SBG" "Volumen" "0.30" "0")
       ("Geotextil tejido T2400" "Geotextil" "0" "15")
       ("Mejoramiento rajon y sello" "Volumen" "0.40" "0")))
    ("MPN1-MPN2-MPGL-MPM2"
      (("Rodadura MDC-19" "Volumen" "0.05" "0" "Base")
       ("Intermedia MDC-25" "Volumen" "0.09" "0" "Base")
       ("Base granular BG" "Volumen" "0.20" "0")
       ("Subbase granular SBG" "Volumen" "0.35" "0")
       ("Geotextil tejido T2400" "Geotextil" "0" "15")
       ("Mejoramiento rajon y sello" "Volumen" "0.40" "0")))
    ("MPPAR-MPE-MPF"
      (("Rodadura MDC-19" "Volumen" "0.05" "0" "Base")
       ("Intermedia MDC-25" "Volumen" "0.09" "0" "Base")
       ("Base granular BG" "Volumen" "0.20" "0")
       ("Subbase granular SBG" "Volumen" "0.40" "0")
       ("Geotextil tejido T2400" "Geotextil" "0" "15")
       ("Mejoramiento rajon y sello" "Volumen" "0.40" "0")))
    ("ESTUDIO SUELOS PD10"
      (("Rodadura MDC-19" "Volumen" "0.05" "0" "Base")
       ("Intermedia MDC-25" "Volumen" "0.08" "0" "Base")
       ("Base granular BG" "Volumen" "0.20" "0")
       ("Subbase granular SBG" "Volumen" "0.30" "0")
       ("Geotextil tejido T2400" "Geotextil" "0" "15")
       ("Subrasante mejorada SBG" "Volumen" "0.05" "0")
       ("Subrasante mejorada rajon" "Volumen" "0.25" "0")))))

(defun urb:config-dictionary (/ nod found created)
  (setq nod (namedobjdict))
  (setq found (dictsearch nod "URB_CONFIG"))
  (if found
    (cdr (assoc -1 found))
    (progn
      (setq created
        (entmakex
          '((0 . "DICTIONARY")
            (100 . "AcDbDictionary")
            (280 . 0)
            (281 . 1))))
      (if created (dictadd nod "URB_CONFIG" created))
      created)))

(defun urb:string-chunks (value size / result)
  (setq value (urb:safe-string value ""))
  (while (> (strlen value) size)
    (setq result (cons (substr value 1 size) result))
    (setq value (substr value (1+ size))))
  (reverse (cons value result)))

(defun urb:config-read (key / dict record value item)
  (setq dict (urb:config-dictionary))
  (if (and dict (setq record (dictsearch dict key)))
    (progn
      (foreach item record
        (if (= (car item) 1)
          (setq value (strcat (urb:safe-string value "") (cdr item)))))
      value)))

(defun urb:config-write (key value / dict old xrecord data)
  (setq dict (urb:config-dictionary))
  (if dict
    (progn
      (if (setq old (dictsearch dict key))
        (progn
          (dictremove dict key)
          (entdel (cdr (assoc -1 old)))))
      (setq data
        (append
          '((0 . "XRECORD") (100 . "AcDbXrecord") (280 . 1))
          (mapcar '(lambda (part) (cons 1 part))
            (urb:string-chunks value 2000))))
      (setq xrecord (entmakex data))
      (if xrecord (dictadd dict key xrecord))
      (if xrecord value))))

(defun urb:load-geometric-settings (/ value pair a b c)
  (foreach pair
    '(("URB_ROAD_OVERWIDTH_LEFT" *urb-road-overwidth-left* 0.0 20.0)
      ("URB_ROAD_OVERWIDTH_RIGHT" *urb-road-overwidth-right* 0.0 20.0)
      ("URB_ROAD_CROSSFALL" *urb-road-crossfall* 0.0 0.20)
      ("URB_ROAD_EARTHWORK_INTERVAL" *urb-road-earthwork-interval* 0.25 20.0)
      ("URB_ROAD_MAX_EARTHWORK_DEPTH" *urb-road-max-earthwork-depth* 0.0 100.0)
      ("URB_ANDEN_DEFAULT_WIDTH" *urb-anden-default-width* 0.20 20.0)
      ;; 2026-08-24: editables desde la ventana Movimiento de tierras
      ("URB_ANDEN_DEPTH" *urb-anden-depth* 0.10 3.0)
      ("URB_TRIT_SOBRE_CLAVE" *mp-triturado-sobre-clave* 0.0 2.0)
      ;; 5.6.5 sobreexcavacion y esponjamiento
      ("URB_OVEREXC_DEPTH" *urb-overexc-depth* 0.0 3.0)
      ("URB_CUT_EXPANSION" *urb-cut-expansion* 0.0 1.0)
      ("URB_FILL_SHRINKAGE" *urb-fill-shrinkage* 0.0 1.0))
    (setq value
      (urb:parse-real
        (urb:safe-string (urb:config-read (car pair)) "")))
    (if (and value (>= value (nth 2 pair)) (<= value (nth 3 pair)))
      (set (cadr pair) value)))
  ;; capas del perfil del anden editadas por el usuario (2026-08-24): si
  ;; las tres estan guardadas, reconstruyen la estructura y el espesor
  ;; total -- ganan sobre URB_ANDEN_DEPTH suelto
  (setq a (urb:parse-real (urb:safe-string (urb:config-read "URB_AND_ADOQUIN") ""))
        b (urb:parse-real (urb:safe-string (urb:config-read "URB_AND_ARENA") ""))
        c (urb:parse-real (urb:safe-string (urb:config-read "URB_AND_SBG") "")))
  (if (and a b c (> a 0.0) (> b 0.0) (> c 0.0) (< (+ a b c) 3.0))
    (urb:anden-structure-apply a b c))
  (setq *urb-anden-road-crossfall* *urb-road-crossfall*)
  (list *urb-road-overwidth-left* *urb-road-overwidth-right*
    *urb-road-crossfall* *urb-road-earthwork-interval*
    *urb-anden-default-width*))

(defun urb:write-geometric-settings-dcl (/ filename)
  (setq filename (urb:temp-file "urb_geometria" ".dcl"))
  (if
    (urb:write-lines filename
      '("urb_geometria : dialog { label = \"Tabla de anchos y calculo\";"
        ": boxed_column { label = \"Parametro | valor por dibujo\";"
        ": row { : text { label = \"Sobreancho izquierdo de via (m)\"; width = 38; } : edit_box { key = \"road_left\"; edit_width = 12; } }"
        ": row { : text { label = \"Sobreancho derecho de via (m)\"; width = 38; } : edit_box { key = \"road_right\"; edit_width = 12; } }"
        ": row { : text { label = \"Bombeo de la calzada (%)\"; width = 38; } : edit_box { key = \"road_cross\"; edit_width = 12; } }"
        ": row { : text { label = \"Intervalo secciones movimiento (m)\"; width = 38; } : edit_box { key = \"road_interval\"; edit_width = 12; } }"
        ": row { : text { label = \"Ancho predeterminado de anden (m)\"; width = 38; } : edit_box { key = \"anden_width\"; edit_width = 12; } }"
        ": text { label = \"El desplegable de la via solo define Ambos, Derecho o Izquierdo.\"; }"
        "} ok_cancel; }"))
    filename))

(defun urb:geometric-settings-capture (/ left right cross interval anden)
  (setq left (urb:parse-real (get_tile "road_left"))
        right (urb:parse-real (get_tile "road_right"))
        cross (urb:parse-real (get_tile "road_cross"))
        interval (urb:parse-real (get_tile "road_interval"))
        anden (urb:parse-real (get_tile "anden_width")))
  (cond
    ((or (null left) (< left 0.0) (> left 20.0))
      (alert "El sobreancho izquierdo debe estar entre 0 y 20 m.") nil)
    ((or (null right) (< right 0.0) (> right 20.0))
      (alert "El sobreancho derecho debe estar entre 0 y 20 m.") nil)
    ((or (null cross) (< cross 0.0) (> cross 20.0))
      (alert "El bombeo debe estar entre 0% y 20%.") nil)
    ((or (null interval) (< interval 0.25) (> interval 20.0))
      (alert "El intervalo debe estar entre 0.25 m y 20 m.") nil)
    ((or (null anden) (< anden 0.20) (> anden 20.0))
      (alert "El ancho del anden debe estar entre 0.20 m y 20 m.") nil)
    (T
      (setq *urb-road-overwidth-left* left
            *urb-road-overwidth-right* right
            *urb-road-crossfall* (/ cross 100.0)
            *urb-anden-road-crossfall* (/ cross 100.0)
            *urb-road-earthwork-interval* interval
            *urb-anden-default-width* anden)
      (urb:config-write "URB_ROAD_OVERWIDTH_LEFT" (rtos left 2 6))
      (urb:config-write "URB_ROAD_OVERWIDTH_RIGHT" (rtos right 2 6))
      (urb:config-write "URB_ROAD_CROSSFALL" (rtos (/ cross 100.0) 2 8))
      (urb:config-write "URB_ROAD_EARTHWORK_INTERVAL" (rtos interval 2 6))
      (urb:config-write "URB_ANDEN_DEFAULT_WIDTH" (rtos anden 2 6))
      T)))

(defun urb:geometric-settings-command (/ filename dcl ok)
  (urb:load-geometric-settings)
  (setq filename (urb:write-geometric-settings-dcl)
        dcl (if filename (load_dialog filename) -1))
  (if (and (> dcl 0) (new_dialog "urb_geometria" dcl))
    (progn
      (set_tile "road_left" (rtos *urb-road-overwidth-left* 2 3))
      (set_tile "road_right" (rtos *urb-road-overwidth-right* 2 3))
      (set_tile "road_cross" (rtos (* 100.0 *urb-road-crossfall*) 2 2))
      (set_tile "road_interval" (rtos *urb-road-earthwork-interval* 2 2))
      (set_tile "anden_width" (rtos *urb-anden-default-width* 2 2))
      (action_tile "accept"
        "(if (urb:geometric-settings-capture) (done_dialog 1))")
      (action_tile "cancel" "(done_dialog 0)")
      (setq ok (= 1 (start_dialog)))))
  (if (> dcl 0) (unload_dialog dcl))
  (if filename (vl-catch-all-apply 'vl-file-delete (list filename)))
  (if ok
    (prompt "\nTabla de anchos, bombeo e intervalo guardada para este dibujo."))
  (princ))

;; 2026-08-24 (pedido del usuario): el espesor de estructura de cada tipo
;; de sendero/bioswale y el ancho por defecto de cada tipo de
;; prefabricado perimetral, antes fijos en el catalogo (o pedidos por
;; ventana cada vez), ahora se editan aqui una sola vez -- mismo patron
;; de urb:geometric-settings-command (config por dibujo, get_tile DENTRO
;; del action_tile de accept, regla de oro DCL v4.41).
;; capa editable de la receta de senderos (2026-08-24): valor de config
;; si el usuario lo edito, si no el default de la receta
(defun urb:send-capa-cfg (clave default / v)
  (setq v (urb:parse-real (urb:safe-string (urb:config-read clave) "")))
  (if (and v (> v 0.0)) v default))

(defun urb:write-send-config-dcl (/ filename)
  (setq filename (urb:temp-file "urb_send_config" ".dcl"))
  (if
    (urb:write-lines filename
      '("urb_send_config : dialog { label = \"Estructura de senderos (capas y espesores)\";"
        ": boxed_column { label = \"Capas de la estructura (aplican a todos los tipos)\";"
        ": row { : text { label = \"Concreto 3000 psi (m)\"; width = 30; } : edit_box { key = \"c_concreto\"; edit_width = 10; } }"
        ": row { : text { label = \"Malla electrosoldada (kg/m2)\"; width = 30; } : edit_box { key = \"c_malla\"; edit_width = 10; } }"
        ": row { : text { label = \"Subbase granular SBG (m)\"; width = 30; } : edit_box { key = \"c_sbg\"; edit_width = 10; } }"
        ": row { : text { label = \"Asfalto MD-13 ciclorruta (m)\"; width = 30; } : edit_box { key = \"c_asfalto\"; edit_width = 10; } } }"
        ": boxed_column { label = \"Espesor de EXCAVACION por tipo (m)\";"
        ": row { : text { label = \"Sendero de trote\"; width = 30; } : edit_box { key = \"e_trote\"; edit_width = 10; } }"
        ": row { : text { label = \"Sendero ecologico\"; width = 30; } : edit_box { key = \"e_eco\"; edit_width = 10; } }"
        ": row { : text { label = \"Plazoleta en concreto\"; width = 30; } : edit_box { key = \"e_plaz\"; edit_width = 10; } }"
        ": row { : text { label = \"Ciclorruta\"; width = 30; } : edit_box { key = \"e_ciclo\"; edit_width = 10; } }"
        ": row { : text { label = \"Rampa en concreto\"; width = 30; } : edit_box { key = \"e_rampa\"; edit_width = 10; } }"
        ": row { : text { label = \"Bioswale / biorretenedor\"; width = 30; } : edit_box { key = \"e_bio\"; edit_width = 10; } }"
        ": row { : text { label = \"Tierra negra zona verde\"; width = 30; } : edit_box { key = \"e_tierra\"; edit_width = 10; } } }"
        ": boxed_column { label = \"Tramos de red (aplica a tramos nuevos)\";"
        ": row { : text { label = \"Altura texto de tramo (m)\"; width = 30; } : edit_box { key = \"t_texto\"; edit_width = 10; } }"
        ": row { : text { label = \"Espesor de linea de tramo (m)\"; width = 30; } : edit_box { key = \"t_ancho\"; edit_width = 10; } } }"
        ": boxed_column { label = \"Ancho por defecto del prefabricado (m)\";"
        ": row { : text { label = \"Bordillo\"; width = 30; } : edit_box { key = \"a_bordillo\"; edit_width = 10; } }"
        ": row { : text { label = \"Sardinel\"; width = 30; } : edit_box { key = \"a_sardinel\"; edit_width = 10; } }"
        ": row { : text { label = \"Canuela\"; width = 30; } : edit_box { key = \"a_canuela\"; edit_width = 10; } } }"
        ": boxed_column { label = \"Altura vista del bordillo (m) -- cuanto queda el anden/zona verde por encima de la rasante de la via\";"
        ": row { : text { label = \"Bordillo / sardinel\"; width = 30; } : edit_box { key = \"h_bordillo\"; edit_width = 10; } } }"
        ": boxed_column { label = \"Prefabricado por costados -- valor por defecto (se elige/cambia tambien en la ventana de Sendero y Bioswale)\";"
        ": row { : text { label = \"Derecha\"; width = 30; } : popup_list { key = \"c_lado1\"; width = 16; } }"
        ": row { : text { label = \"Izquierda\"; width = 30; } : popup_list { key = \"c_lado2\"; width = 16; } } }"
        "ok_cancel; }"))
    filename))

;; (clave-config tile-dcl minimo maximo)
(setq *urb-send-config-fields*
  '(("URB_SEND_CONCRETO" "c_concreto" 0.01 1.0)
    ("URB_SEND_MALLA" "c_malla" 0.1 20.0)
    ("URB_SEND_SBG" "c_sbg" 0.05 2.0)
    ("URB_SEND_ASFALTO" "c_asfalto" 0.01 1.0)
    ("URB_SEND_ESP_SEND-TROTE" "e_trote" 0.05 3.0)
    ("URB_SEND_ESP_SEND-ECO" "e_eco" 0.05 3.0)
    ("URB_SEND_ESP_PLAZOLETA" "e_plaz" 0.05 3.0)
    ("URB_SEND_ESP_CICLORRUTA" "e_ciclo" 0.05 3.0)
    ("URB_SEND_ESP_RAMPA-CONC" "e_rampa" 0.05 3.0)
    ("URB_SEND_ESP_BIOSWALE" "e_bio" 0.05 3.0)
    ("URB_GREEN_ESP_TIERRA" "e_tierra" 0.05 1.0)
    ("MP_TRAMO_TEXT_HEIGHT" "t_texto" 0.1 3.0)
    ("MP_TRAMO_LINE_WIDTH" "t_ancho" 0.01 2.0)
    ("URB_PREFAB_ANCHO_BORDILLO" "a_bordillo" 0.05 2.0)
    ("URB_PREFAB_ANCHO_SARDINEL" "a_sardinel" 0.05 2.0)
    ("URB_PREFAB_ANCHO_CANUELA" "a_canuela" 0.05 2.0)
    ("URB_PREFAB_ALTO_BORDILLO" "h_bordillo" 0.05 1.0)))

(defun urb:send-config-capture (/ field valores clave tile lo hi v ok)
  (setq valores nil ok T)
  (foreach field *urb-send-config-fields*
    (setq clave (nth 0 field) tile (nth 1 field)
          lo (nth 2 field) hi (nth 3 field))
    (setq v (urb:parse-real (get_tile tile)))
    (if (or (null v) (< v lo) (> v hi))
      (progn
        (if ok
          (alert (strcat "Valor invalido en \"" tile "\": debe estar entre "
            (rtos lo 2 2) " y " (rtos hi 2 2) " m.")))
        (setq ok nil))
      (setq valores (cons (cons clave (rtos v 2 4)) valores))))
  (setq valores
    (cons (cons "URB_SEND_COSTADO1"
            (nth (atoi (urb:safe-string (get_tile "c_lado1") "0"))
              *urb-anillo-prefab-list*))
      (cons (cons "URB_SEND_COSTADO2"
              (nth (atoi (urb:safe-string (get_tile "c_lado2") "0"))
                *urb-anillo-prefab-list*))
        valores)))
  (if ok
    (progn
      (foreach par valores (urb:config-write (car par) (cdr par)))
      T)
    nil))

(defun urb:send-config-command (/ filename dcl ok field tile default)
  (setq filename (urb:write-send-config-dcl)
        dcl (if filename (load_dialog filename) -1))
  (if (and (> dcl 0) (new_dialog "urb_send_config" dcl))
    (progn
      (foreach field *urb-send-config-fields*
        (setq tile (nth 1 field))
        (setq default
          (cond
            ((= tile "c_concreto") (urb:send-capa-cfg "URB_SEND_CONCRETO" 0.10))
            ((= tile "c_malla") (urb:send-capa-cfg "URB_SEND_MALLA" 2.36))
            ((= tile "c_sbg") (urb:send-capa-cfg "URB_SEND_SBG" 0.30))
            ((= tile "c_asfalto") (urb:send-capa-cfg "URB_SEND_ASFALTO" 0.08))
            ((= tile "e_trote") (urb:send-espesor-de (assoc "SEND-TROTE" *urb-send-tipos*)))
            ((= tile "e_eco") (urb:send-espesor-de (assoc "SEND-ECO" *urb-send-tipos*)))
            ((= tile "e_plaz") (urb:send-espesor-de (assoc "PLAZOLETA" *urb-send-tipos*)))
            ((= tile "e_ciclo") (urb:send-espesor-de (assoc "CICLORRUTA" *urb-send-tipos*)))
            ((= tile "e_rampa") (urb:send-espesor-de (assoc "RAMPA-CONC" *urb-send-tipos*)))
            ((= tile "e_bio") (urb:send-espesor-de *urb-bioswale-tipo*))
            ((= tile "e_tierra") (urb:green-default-espesor))
            ((= tile "t_texto") (mp:cfg-tramo-text 0.60))
            ((= tile "t_ancho") (mp:cfg-tramo-width 0.20))
            ((= tile "a_bordillo") (urb:prefab-default-ancho "Bordillo"))
            ((= tile "a_sardinel") (urb:prefab-default-ancho "Sardinel"))
            ((= tile "a_canuela") (urb:prefab-default-ancho "Canuela"))
            ((= tile "h_bordillo") (urb:prefab-default-alto "Bordillo"))
            (T 0.20)))
        (set_tile tile (rtos default 2 3)))
      (urb:fill-popup "c_lado1" *urb-anillo-prefab-list*
        (urb:list-index-ci (urb:send-costado-de 1) *urb-anillo-prefab-list*))
      (urb:fill-popup "c_lado2" *urb-anillo-prefab-list*
        (urb:list-index-ci (urb:send-costado-de 2) *urb-anillo-prefab-list*))
      (action_tile "accept"
        "(if (urb:send-config-capture) (done_dialog 1))")
      (action_tile "cancel" "(done_dialog 0)")
      (setq ok (= 1 (start_dialog)))))
  (if (> dcl 0) (unload_dialog dcl))
  (if filename (vl-catch-all-apply 'vl-file-delete (list filename)))
  (if ok
    (progn
      (mp:load-tramo-appearance-settings)
      (mp:store-tramo-appearance-settings
        *mp-vis-width* *mp-vis-tramo-text-height*)
      (mp:apply-tramo-appearance-to-drawing)
      (prompt "\nEspesores y anchos guardados y aplicados al dibujo.")))
  (princ))

;; 2026-08-24 (pedido del usuario): hub "Movimiento de tierras" -- una
;; sola ventana en Ajustes que reune lo que antes eran 3 botones sueltos:
;; los sobreanchos/bombeo/intervalo/ancho de anden editables DIRECTO en
;; la ventana, mas dos botones que abren los administradores complejos
;; (perfiles estratigraficos y referencia de relleno de redes) y VUELVEN
;; a esta ventana al cerrar. Reutiliza urb:geometric-settings-capture y
;; los mismos tiles del dialogo urb_geometria viejo (que sigue existiendo
;; por codigo pero salio del menu).
;; captura de la ventana Movimiento de tierras (2026-08-24 v2, pedido
;; del usuario): fuera el intervalo de secciones (2.5 m quedo fijo -- la
;; sonda de la auditoria demostro que a 2.5 m el resultado es exacto; se
;; puede seguir cambiando por codigo/config si algun dia hace falta) y
;; fuera el ancho predeterminado de anden (el ancho real sale del
;; poligono que se dibuja; el campo solo alimentaba el fondo de la rampa,
;; que ya se pregunta en su propia ventana). Entran: espesor de
;; estructura del anden (la excavacion del anden = area x este espesor,
;; antes fijo en 0.60), triturado sobre la clave (cimentacion modelo 2
;; de redes) y la referencia de relleno Terreno/Subrasante como popup.
;; 5.6.5: los tres campos de sobreexcavacion viven en DOS ventanas (la de
;; Movimiento de tierras y la de Perfiles de pavimento, como se pidio), con
;; la misma lectura, validacion y guardado.
(defun urb:overexc-set-tiles ()
  (set_tile "over_depth" (rtos *urb-overexc-depth* 2 2))
  (set_tile "cut_exp" (rtos (* 100.0 *urb-cut-expansion*) 2 1))
  (set_tile "fill_shrink" (rtos (* 100.0 *urb-fill-shrinkage*) 2 1)))

(defun urb:overexc-capture (/ h e s)
  (setq h (urb:parse-real (get_tile "over_depth"))
        e (urb:parse-real (get_tile "cut_exp"))
        s (urb:parse-real (get_tile "fill_shrink")))
  (cond
    ((or (null h) (< h 0.0) (> h 3.0))
      (alert "El material no portante debe estar entre 0 y 3 m.") nil)
    ((or (null e) (< e 0.0) (> e 100.0))
      (alert "La expansion del corte debe estar entre 0 y 100 %.") nil)
    ((or (null s) (< s 0.0) (> s 100.0))
      (alert "El sobreconsumo del relleno debe estar entre 0 y 100 %.") nil)
    (T
      (setq *urb-overexc-depth* h
            *urb-cut-expansion* (/ e 100.0)
            *urb-fill-shrinkage* (/ s 100.0))
      (urb:config-write "URB_OVEREXC_DEPTH" (rtos h 2 4))
      (urb:config-write "URB_CUT_EXPANSION" (rtos (/ e 100.0) 2 6))
      (urb:config-write "URB_FILL_SHRINKAGE" (rtos (/ s 100.0) 2 6))
      T)))

(defun urb:earthworks-capture (/ left right cross max-depth adoquin arena sbg trit
                               relleno)
  (setq left (urb:parse-real (get_tile "road_left"))
        right (urb:parse-real (get_tile "road_right"))
        cross (urb:parse-real (get_tile "road_cross"))
        max-depth (urb:parse-real (get_tile "road_max_depth"))
        adoquin (urb:parse-real (get_tile "ad_adoquin"))
        arena (urb:parse-real (get_tile "ad_arena"))
        sbg (urb:parse-real (get_tile "ad_sbg"))
        trit (urb:parse-real (get_tile "trit_clave"))
        relleno (atoi (urb:safe-string (get_tile "relleno_ref") "0")))
  (cond
    ((or (null left) (< left 0.0) (> left 20.0))
      (alert "El sobreancho izquierdo debe estar entre 0 y 20 m.") nil)
    ((or (null right) (< right 0.0) (> right 20.0))
      (alert "El sobreancho derecho debe estar entre 0 y 20 m.") nil)
    ((or (null cross) (< cross 0.0) (> cross 20.0))
      (alert "El bombeo debe estar entre 0 y 20 %.") nil)
    ((or (null max-depth) (< max-depth 0.0) (> max-depth 100.0))
      (alert "La profundidad maxima de control debe estar entre 0 y 100 m; use 0 para desactivarla.") nil)
    ((or (null adoquin) (<= adoquin 0.0) (> adoquin 0.50))
      (alert "El adoquin/loseta debe estar entre 0.01 y 0.50 m.") nil)
    ((or (null arena) (<= arena 0.0) (> arena 0.50))
      (alert "La arena de nivelacion debe estar entre 0.01 y 0.50 m.") nil)
    ((or (null sbg) (<= sbg 0.0) (> sbg 2.0))
      (alert "La subbase SBG-C debe estar entre 0.01 y 2.0 m.") nil)
    ((or (null trit) (< trit 0.0) (> trit 2.0))
      (alert "El triturado sobre la clave debe estar entre 0 y 2.0 m.") nil)
    ((null (urb:overexc-capture)) nil)
    (T
      (setq *urb-road-overwidth-left* left
            *urb-road-overwidth-right* right
            *urb-road-crossfall* (/ cross 100.0)
            *urb-road-max-earthwork-depth* max-depth
            *urb-anden-road-crossfall* (/ cross 100.0)
            *mp-triturado-sobre-clave* trit)
      (urb:anden-structure-apply adoquin arena sbg)
      (urb:config-write "URB_ROAD_OVERWIDTH_LEFT" (rtos left 2 6))
      (urb:config-write "URB_ROAD_OVERWIDTH_RIGHT" (rtos right 2 6))
      (urb:config-write "URB_ROAD_CROSSFALL" (rtos (/ cross 100.0) 2 8))
      (urb:config-write "URB_ROAD_MAX_EARTHWORK_DEPTH" (rtos max-depth 2 4))
      (urb:config-write "URB_AND_ADOQUIN" (rtos adoquin 2 4))
      (urb:config-write "URB_AND_ARENA" (rtos arena 2 4))
      (urb:config-write "URB_AND_SBG" (rtos sbg 2 4))
      (urb:config-write "URB_ANDEN_DEPTH" (rtos *urb-anden-depth* 2 4))
      (urb:config-write "URB_TRIT_SOBRE_CLAVE" (rtos trit 2 4))
      (urb:config-write "MP_TRAMO_RELLENO_MODO"
        (if (= relleno 1) "Subrasante" "Terreno"))
      T)))

;; tabla de normas de zanja, solo lectura (2026-08-24, pedido del
;; usuario: la norma CODENSA "plasmada, organizada y clara" + la tabla
;; de anchos hidraulicos que ya vivia en el codigo como
;; *mp-pvc-trench-width-table* pero nunca se podia VER)
(defun urb:normas-zanja-lineas (/ out entry linea a)
  (setq out
    (list
      "=== REDES SECAS -- zanja normativa CODENSA (Likinormas CS203/CS207) ==="
      ""
      "  Recubrimiento sobre el banco de ductos:"
      "     bajo anden o zona verde ........ 0.60 m"
      "     bajo calzada ................... 0.80 m"
      "  Banco de ductos:"
      "     columnas = raiz cuadrada del numero de ductos, redondeada hacia arriba"
      "     altura = 0.05 (base) + filas x diametro del ducto + 0.05 entre filas"
      "  Ancho de zanja = 0.30 m + columnas x diametro + 0.05 entre columnas"
      "     (minimo 0.80 m en MT / 0.60 m en BT-alumbrado)"
      "  Profundidad de zanja = recubrimiento + altura del banco"
      ""
      "  CORTE (excavacion) = ancho x profundidad x longitud (no requiere cotas)"
      "  RELLENO = arena (envolvente del banco - ductos)"
      "          + base granular B (excavacion - envolvente)"
      "  Ambos salen automaticamente al presupuesto por cada tramo MT / BT-AP."
      ""
      "=== REDES HIDRAULICAS -- anchos de zanja PVC (hoja del presupuesto) ==="
      ""
      "  Diam \" |  anchos (m) segun profundidad de zanja:"
      "         |  <=1.5  <=2.5  <=3.5  <=4.5  <=5.5  <=6.5  <=7.5  <=8.5  <=9.5  >9.5"
      "  -------+-----------------------------------------------------------------------"))
  (foreach entry *mp-pvc-trench-width-table*
    (setq linea
      (strcat "    " (if (< (car entry) 10) " " "") (itoa (car entry))
        "   |"))
    (foreach a (cdr entry)
      (setq linea (strcat linea "  " (rtos a 2 2))))
    (setq out (append out (list linea))))
  out)

(defun urb:normas-zanja-command (/ filename dcl linea)
  (setq filename (urb:write-main-menu-dcl)
        dcl (if filename (load_dialog filename) -1))
  (if (and (> dcl 0) (new_dialog "urb_normas" dcl))
    (progn
      (start_list "tabla")
      (foreach linea (urb:normas-zanja-lineas) (add_list linea))
      (end_list)
      (action_tile "accept" "(done_dialog 1)")
      (start_dialog)))
  (if (> dcl 0) (unload_dialog dcl))
  (princ))

(defun urb:earthworks-config-command (/ filename dcl done again modo)
  (setq again T)
  (while again
    (setq again nil done nil)
    (urb:load-geometric-settings)
    (setq filename (urb:write-main-menu-dcl)
          dcl (if filename (load_dialog filename) -1))
    (if (and (> dcl 0) (new_dialog "urb_earthworks" dcl))
      (progn
        (set_tile "road_left" (rtos *urb-road-overwidth-left* 2 3))
        (set_tile "road_right" (rtos *urb-road-overwidth-right* 2 3))
        (set_tile "road_cross" (rtos (* 100.0 *urb-road-crossfall*) 2 2))
        (set_tile "road_max_depth" (rtos *urb-road-max-earthwork-depth* 2 2))
        ;; capas actuales del perfil del anden (posiciones fijas de
        ;; *urb-anden-structure*: 0 adoquin, 1 arena, 2 SBG-C)
        (set_tile "ad_adoquin"
          (rtos (atof (nth 2 (nth 0 *urb-anden-structure*))) 2 3))
        (set_tile "ad_arena"
          (rtos (atof (nth 2 (nth 1 *urb-anden-structure*))) 2 3))
        (set_tile "ad_sbg"
          (rtos (atof (nth 2 (nth 2 *urb-anden-structure*))) 2 3))
        (set_tile "trit_clave" (rtos *mp-triturado-sobre-clave* 2 2))
        (urb:overexc-set-tiles)
        (setq modo
          (urb:safe-string (urb:config-read "MP_TRAMO_RELLENO_MODO")
            "Terreno"))
        (urb:fill-popup "relleno_ref"
          '("Terreno natural" "Subrasante de via")
          (if (= modo "Subrasante") 1 0))
        (action_tile "accept"
          "(if (urb:earthworks-capture) (done_dialog 1))")
        (action_tile "cancel" "(done_dialog 0)")
        (action_tile "perfiles" "(done_dialog 2)")
        (action_tile "senderos" "(done_dialog 4)")
        (action_tile "normas" "(done_dialog 5)")
        (setq done (start_dialog))))
    (if (> dcl 0) (unload_dialog dcl))
    (cond
      ((= done 1)
        (prompt "\nParametros de movimiento de tierras guardados para este dibujo."))
      ((= done 2) (urb:manage-road-profiles) (setq again T))
      ((= done 4) (urb:send-config-command) (setq again T))
      ((= done 5) (urb:normas-zanja-command) (setq again T))))
  (princ))

;; 2026-08-24 (pedido del usuario: "el modelo ya tiene muchas cosas
;; basura y se esta poniendo lento"): depuracion con el -PURGE nativo.
;; Varias pasadas de "All" (los bloques anidados solo se liberan cuando
;; su contenedor ya se purgo) + una de Regapps (las appid huerfanas de
;; xdata NO caen con All y pesan en dibujos viejos). No toca nada en
;; uso: -PURGE solo elimina definiciones sin referencias.
;; 5.7.2 (pedido del usuario: "esta muy pesado y se demora mucho en
;; moverse... sin perder precision"). Medido en el maestro (39,5 MB): la
;; purga clasica solo retiro 4 de 1169 definiciones -- no es ahi donde esta
;; el peso. El 60% de lo dibujado son las piezas tactiles DENTRO de los
;; andenes: 32.929 circulos (domos de toperol) en URB-ANDEN-LOSETA-TOPEROL-20X20
;; y 23.922 lineas/polilineas en URB-ANDEN-LOSETA-GUIA-20X20. Sus CANTIDADES
;; viven en la XDATA/atributos del anden, no en el dibujo, asi que congelar
;; esas capas (incluidas sus variantes 40x40) acelera el zoom/pan/regen sin
;; cambiar ni un numero, y se deshace con la misma opcion explicita.
(setq *urb-light-layers*
  '("URB-ANDEN-LOSETA-TOPEROL-20X20" "URB-ANDEN-LOSETA-GUIA-20X20"
    "URB-ANDEN-LOSETA-TOPEROL-40X40" "URB-ANDEN-LOSETA-GUIA-40X40"))

(defun urb:light-mode-state (/ lay frozen total)
  (setq frozen 0 total 0)
  (foreach lay *urb-light-layers*
    (if (tblsearch "LAYER" lay)
      (progn
        (setq total (1+ total))
        (if (= 1 (logand 1 (cdr (assoc 70 (tblsearch "LAYER" lay)))))
          (setq frozen (1+ frozen))))))
  (cond ((= total 0) "SIN CAPAS") ((= frozen total) "ACTIVO") (T "APAGADO")))

(defun urb:light-mode-set (on / lay obj n)
  (setq n 0)
  (foreach lay *urb-light-layers*
    (if (tblsearch "LAYER" lay)
      (progn
        (setq obj (vla-Item (vla-get-Layers (urb:doc)) lay))
        (if (not (vl-catch-all-error-p
                   (vl-catch-all-apply 'vla-put-Freeze (list obj (if on :vlax-true :vlax-false)))))
          (setq n (1+ n))))))
  (vl-catch-all-apply '(lambda () (vla-Regen (urb:doc) acAllViewports)))
  n)

(defun urb:count-table (name / a n)
  (setq n 0 a (tblnext name T))
  (while a (setq n (1+ n) a (tblnext name)))
  n)

(defun urb:count-blocks (/ n)
  (setq n 0)
  (vlax-for b (vla-get-Blocks (urb:doc)) (setq n (1+ n)))
  n)

(defun urb:light-mode-command (/ state answer)
  ;; Accion separada de PURGE: ocultar detalle tactil es util para navegar
  ;; dibujos grandes, pero nunca debe parecer una eliminacion causada por la
  ;; depuracion. Aqui siempre requiere una eleccion explicita del usuario.
  (setq state (urb:light-mode-state))
  (if (= state "SIN CAPAS")
    (prompt "\nEste dibujo aun no contiene capas tactiles para ocultar.")
    (progn
      (initget "Activar Restaurar Cancelar")
      (setq answer
        (getkword
          (strcat
            "\nModo fluido -- hoy " state
            " [Activar/Restaurar/Cancelar] <Cancelar>: ")))
      (cond
        ((= answer "Activar")
          (urb:light-mode-set T)
          (prompt
            "\nModo fluido ACTIVO: guia y toperol solo estan congelados; no se borraron y sus cantidades se conservan."))
        ((= answer "Restaurar")
          (urb:light-mode-set nil)
          (prompt "\nDetalle de guia y toperol visible de nuevo."))
        (T (prompt "\nNo se cambio la visibilidad del dibujo.")))))
  (princ))

(defun urb:purge-command (/ b0 r0 b1 r1)
  (setq b0 (urb:count-blocks) r0 (urb:count-table "APPID"))
  (prompt "\nDepurando definiciones sin uso (3 pasadas)...")
  (repeat 3
    (vl-catch-all-apply
      '(lambda () (command "_.-PURGE" "_A" "*" "_N"))))
  (vl-catch-all-apply
    '(lambda () (command "_.-PURGE" "_R" "*" "_N")))
  (setq b1 (urb:count-blocks) r1 (urb:count-table "APPID"))
  (prompt (strcat "\nDepuracion: definiciones de bloque " (itoa b0) " -> " (itoa b1)
                  " | regapps " (itoa r0) " -> " (itoa r1) "."))
  (prompt
    "\nGuarde el dibujo para que el archivo baje de peso. PURGE no oculto ni borro guia o toperol.")
  (princ))

(defun mp:configured-tramo-value (canonical legacy default lo hi / value)
  (setq value
    (urb:parse-real
      (urb:safe-string (urb:config-read canonical) "")))
  (if (not (and value (>= value lo) (<= value hi)))
    (setq value
      (urb:parse-real
        (urb:safe-string (urb:config-read legacy) ""))))
  (if (and value (>= value lo) (<= value hi)) value default))

(defun mp:store-tramo-appearance-settings (line-width text-height)
  ;; Escribe ambas claves durante la transicion para que una instalacion
  ;; anterior no vuelva a mostrar un valor distinto en el mismo DWG.
  (urb:config-write "MP_TRAMO_LINE_WIDTH" (rtos line-width 2 6))
  (urb:config-write "MP_TRAMO_TEXT_HEIGHT" (rtos text-height 2 6))
  (urb:config-write "URB_MP_ANCHO_TRAMO" (rtos line-width 2 6))
  (urb:config-write "URB_MP_TEXTO_TRAMO" (rtos text-height 2 6))
  (urb:config-write "MP_POINT_TEXT_HEIGHT" (rtos text-height 2 6))
  (list line-width text-height))

(defun mp:load-tramo-appearance-settings (/ value)
  ;; Ajustes por DWG: al abrir otro proyecto se respetan sus escalas y el
  ;; valor predeterminado sigue disponible en dibujos nuevos.
  (setq *mp-vis-width*
    (mp:configured-tramo-value
      "MP_TRAMO_LINE_WIDTH" "URB_MP_ANCHO_TRAMO" *mp-vis-width* 0.01 20.0))
  (setq *mp-vis-tramo-text-height*
    (mp:configured-tramo-value
      "MP_TRAMO_TEXT_HEIGHT" "URB_MP_TEXTO_TRAMO"
      *mp-vis-tramo-text-height* 0.10 50.0))
  (setq *mp-vis-text-height*
    (mp:configured-tramo-value
      "MP_POINT_TEXT_HEIGHT" "MP_TRAMO_TEXT_HEIGHT"
      *mp-vis-text-height* 0.10 50.0))
  (setq *mp-vis-tramo-text-gap*
    (mp:cfg-tramo-text-gap *mp-vis-tramo-text-gap*))
  (list *mp-vis-width* *mp-vis-tramo-text-height*)
)

(defun mp:apply-tramo-appearance-to-drawing
  (/ blocks blk bname base definitions ss index ename obj atts att tag refs visible)
  ;; Apariencia global: referencias y definiciones de tramos, pozos, cajas y
  ;; accesorios. Las polilineas viven en definiciones compartidas; los textos
  ;; visibles se actualizan en cada INSERT sin tocar XDATA ni geometria.
  (setq blocks (vla-get-Blocks (urb:doc)) definitions 0 refs 0)
  ;; 5.6.0: Apariencia tambien limpia mascaras (wipeout) de los simbolos
  (vl-catch-all-apply 'mp:strip-network-wipeouts nil)
  (vlax-for blk blocks
    (if (and (= (vla-get-IsLayout blk) :vlax-false)
             (= (vla-get-IsXRef blk) :vlax-false))
      (progn
        (setq bname (vla-get-Name blk)
              base (mp:infer-base bname nil))
        (if (or (mp:base-is-tramo base) (/= base ""))
          (progn
            (if (mp:base-is-tramo base)
              (progn
                (mp:normalize-tramo-graphics blk base)
                (mp:normalize-visible-attdefs blk T base))
              (mp:normalize-visible-attdefs blk nil base))
            (setq definitions (1+ definitions)))))))
  (setq ss (ssget "_X" '((0 . "INSERT"))) index 0)
  (if ss
    (while (< index (sslength ss))
      (setq ename (ssname ss index)
            obj (vlax-ename->vla-object ename)
            base (mp:infer-base (vla-get-EffectiveName obj) (mp:att-alist ename)))
      (if (and (/= base "")
               (= (vla-get-HasAttributes obj) :vlax-true))
        (progn
          (setq atts (vlax-invoke obj 'GetAttributes))
          (foreach att atts
            (setq tag (strcase (vla-get-TagString att)))
            (if (member tag '("ETIQUETA" "PENDIENTE_VIS" "LONG_VIS" "NUM_VIS"))
              (progn
                (vl-catch-all-apply 'vla-put-Height
                  (list att (float (if (mp:base-is-tramo base)
                                     *mp-vis-tramo-text-height*
                                     *mp-vis-text-height*))))
                (vla-Update att))))
          ;; Reaplicar la posicion local de las cotas a cada referencia;
          ;; esto corrige tambien bloques ya existentes al cambiar la
          ;; apariencia global, sin depender de que el usuario ejecute
          ;; ETIQUETAS manualmente.
          (if (mp:base-is-tramo base)
            (mp:recenter-tramo-attribs ename))
          (setq refs (1+ refs))))
      (setq index (1+ index))))
  ;; 5.6.1: si cambio el ancho de los tramos, los accesorios lo siguen
  (vl-catch-all-apply 'mp:migrate-accessory-look nil)
  (vla-Regen (urb:doc) 1)
  (list definitions refs)
)

(defun mp:write-tramo-appearance-dcl (/ filename)
  (setq filename (urb:temp-file "urb_tramo_apariencia" ".dcl"))
  (if
    (urb:write-lines filename
      '("urb_tramo_apariencia : dialog { label = \"Apariencia de tramos\";"
        ": boxed_column { label = \"Geometria y datos visibles\";"
        ": edit_box { label = \"Espesor de linea del tramo (m)\"; key = \"line_width\"; edit_width = 12; }"
        ": edit_box { label = \"Altura global de textos (m)\"; key = \"text_height\"; edit_width = 12; }"
        ": edit_box { label = \"Separacion texto - linea del tramo (m)\"; key = \"text_gap\"; edit_width = 12; }"
        ": text { label = \"Espacio libre entre el borde de la linea y el texto (0 = pegado).\"; }"
        ": text { label = \"Se aplica a tramos, pozos, cajas y accesorios existentes y nuevos.\"; } }"
        "ok_cancel; }"))
    filename)
)

(defun mp:tramo-appearance-capture (/ line-width text-height text-gap updated)
  (setq line-width (urb:parse-real (get_tile "line_width"))
        text-height (urb:parse-real (get_tile "text_height"))
        text-gap (urb:parse-real (get_tile "text_gap")))
  (cond
    ((or (null line-width) (< line-width 0.01) (> line-width 20.0))
      (alert "El espesor debe estar entre 0.01 m y 20.00 m.") nil)
    ((or (null text-height) (< text-height 0.10) (> text-height 50.0))
      (alert "La altura global de textos debe estar entre 0.10 m y 50.00 m.") nil)
    ((or (null text-gap) (< text-gap 0.0) (> text-gap 50.0))
      (alert "La separacion texto - linea debe estar entre 0.00 m y 50.00 m.") nil)
    (T
      (setq *mp-vis-width* line-width
            *mp-vis-tramo-text-height* text-height
            *mp-vis-tramo-text-gap* text-gap)
      (mp:store-tramo-appearance-settings line-width text-height)
      ;; se guarda antes de aplicar: mp:tramo-label-offset lee la config
      (urb:config-write "MP_TRAMO_TEXT_GAP" (rtos text-gap 2 6))
      ;; las definiciones se normalizan de nuevo con la separacion nueva:
      ;; la cache de attdefs del recentrado quedaria con la posicion vieja
      (setq *mp-recenter-defcache* nil)
      (setq *mp-tramo-appearance-result*
        (mp:apply-tramo-appearance-to-drawing))
      T))
)

(defun mp:tramo-appearance-command (/ filename dcl ok result)
  (mp:load-tramo-appearance-settings)
  (setq *mp-tramo-appearance-result* nil
        filename (mp:write-tramo-appearance-dcl)
        dcl (if filename (load_dialog filename) -1))
  (if (and (> dcl 0) (new_dialog "urb_tramo_apariencia" dcl))
    (progn
      (set_tile "line_width" (rtos *mp-vis-width* 2 3))
      (set_tile "text_height" (rtos *mp-vis-tramo-text-height* 2 3))
      (set_tile "text_gap" (rtos *mp-vis-tramo-text-gap* 2 3))
      (action_tile "accept"
        "(if (mp:tramo-appearance-capture) (done_dialog 1))")
      (action_tile "cancel" "(done_dialog 0)")
      (setq ok (= 1 (start_dialog)))))
  (if (> dcl 0) (unload_dialog dcl))
  (if filename (vl-catch-all-apply 'vl-file-delete (list filename)))
  (if ok
    (progn
      (setq result *mp-tramo-appearance-result*)
      (prompt
        (strcat
          "\nApariencia actualizada: espesor " (rtos *mp-vis-width* 2 3)
          " m | datos " (rtos *mp-vis-tramo-text-height* 2 3)
          " m | separacion " (rtos *mp-vis-tramo-text-gap* 2 3)
          " m | definiciones " (itoa (if result (car result) 0))
          " | tramos insertados " (itoa (if result (cadr result) 0)) "."))))
  (princ)
)

;; vl-princ-to-string (lo que se usaba aqui antes) NO conserva las
;; comillas de los strings dentro de una lista -- un perfil como "MPD"
;; se guardaba como texto sin comillas y al leerlo de vuelta con
;; (read ...) se convertia en el SIMBOLO MPD en vez de la cadena "MPD".
;; Eso rompia add_list mas adelante ("bad argument type: stringp MPD").
;; prin1 si conserva las comillas (por eso es "leible" de vuelta), pero
;; solo escribe a un stream, no devuelve un string directamente; por
;; eso se usa un archivo temporal como intermediario.
(defun urb:serialize-lisp (value / filename stream text)
  (setq filename (urb:temp-file "urb_config" ".txt"))
  (setq stream (open filename "w"))
  (if stream
    (progn
      (prin1 value stream)
      (close stream)
      (setq stream (open filename "r"))
      (setq text (read-line stream))
      (close stream)
      (vl-catch-all-apply 'vl-file-delete (list filename))))
  (if text text (vl-princ-to-string value))
)

;; Auto-reparacion: si el dibujo ya tiene una biblioteca guardada con el
;; bug anterior (strings convertidos en simbolos), esta validacion lo
;; detecta y urb:road-profiles la reemplaza por los valores por defecto,
;; guardados correctamente esta vez con urb:serialize-lisp.
(defun urb:valid-road-profiles-p (profiles / ok profile layer)
  (setq ok (and (listp profiles) (> (length profiles) 0)))
  (foreach profile profiles
    (if (not (and (listp profile)
                  (stringp (car profile))
                  (listp (cadr profile))))
      (setq ok nil)
      (foreach layer (cadr profile)
        (if (not (and (listp layer)
                      (stringp (nth 0 layer)) (stringp (nth 1 layer))
                      (stringp (nth 2 layer)) (stringp (nth 3 layer))))
          (setq ok nil)))))
  ok
)

;; Normaliza las capas conocidas al nombre corto del MATERIAL. Las
;; descripciones de actividad ("Suministro, extendida...") hacian ilegible
;; la paleta Properties y no aportaban informacion adicional al metrado.
;; Las capas personalizadas del usuario permanecen intactas.
(defun urb:budget-road-layer-name (name)
  (cond
    ((or (urb:string-equal-p name "Rodadura MDC-19")
         (urb:string-equal-p name
           "Suministro, extendida y compactacion de Rodadura Asfaltica MD-12"))
      "Rodadura Asfaltica MD-12")
    ((or (urb:string-equal-p name "Intermedia MDC-25")
         (urb:string-equal-p name
           "Suministro, extendida y compactacion de Base Asfaltica MD-20"))
      "Base Asfaltica MD-20")
    ((or (urb:string-equal-p name "Base granular BG")
         (urb:string-equal-p name
           "Suministro e instalacion de base granular BG-A"))
      "Base granular BG-A")
    ((or (urb:string-equal-p name "Subbase granular SBG")
         (urb:string-equal-p name
           "Suministro e instalacion de subbase granular SBG-A"))
      "Subbase granular SBG-A")
    ((or (urb:string-equal-p name "Geotextil tejido T2400")
         (urb:string-equal-p name
           "Suministro y colocacion de geotextil Tejido 2400"))
      "Geotextil tejido 2400")
    ((or (urb:string-equal-p name "Subrasante mejorada SBG")
         (urb:string-equal-p name
           "Suministro e instalacion de sello en subbase granular SBG-C"))
      "Sello subbase granular SBG-C")
    ((or (urb:string-equal-p name "Subrasante mejorada rajon")
         (urb:string-equal-p name
           "Suministro y colocacion de piedra rajon y/o media zonga"))
      "Piedra rajon y/o media zonga")
    (T name))
)

(defun urb:migrate-budget-road-layer
  (layer / name thickness seal-thickness rajon-thickness scope)
  (setq name (urb:safe-string (nth 0 layer) "")
        scope (urb:safe-string (nth 4 layer) "Total"))
  (if (urb:string-equal-p name "Mejoramiento rajon y sello")
    (progn
      ;; Los perfiles base documentan un sello de 10 cm incluido dentro
      ;; del mejoramiento. Se separa sin cambiar el espesor total.
      (setq thickness (max 0.0 (atof (urb:safe-string (nth 2 layer) "0")))
            seal-thickness (min 0.10 thickness)
            rajon-thickness (max 0.0 (- thickness seal-thickness)))
      (append
        (if (> seal-thickness 1e-9)
          (list
            (list
              "Sello subbase granular SBG-C"
              "Volumen" (rtos seal-thickness 2 4) "0" scope))
          nil)
        (if (> rajon-thickness 1e-9)
          (list
            (list
              "Piedra rajon y/o media zonga"
              "Volumen" (rtos rajon-thickness 2 4) "0" scope))
          nil)))
    (list
      (cons (urb:budget-road-layer-name name) (cdr layer))))
)

(defun urb:migrate-budget-road-profiles
  (profiles / result profile layers layer)
  (foreach profile profiles
    (setq layers nil)
    (foreach layer (cadr profile)
      (setq layers
        (append layers (urb:migrate-budget-road-layer layer))))
    (setq result
      (append result (list (list (car profile) layers)))))
  result
)

(defun urb:road-profiles (/ raw parsed valid migrated)
  (setq raw (urb:config-read "ROAD_PROFILES"))
  (if (and raw (/= raw ""))
    (setq parsed (vl-catch-all-apply 'read (list raw))))
  (if (vl-catch-all-error-p parsed) (setq parsed nil))
  ;; La validacion tambien se blinda: si los datos guardados vienen de
  ;; una version anterior con datos corruptos, revisarlos no deberia
  ;; poder tronar el comando completo -- cualquier error aqui se trata
  ;; igual que "no es valido" y cae a los valores por defecto.
  (if parsed
    (setq valid (vl-catch-all-apply 'urb:valid-road-profiles-p (list parsed))))
  (if (or (null parsed) (vl-catch-all-error-p valid) (not valid))
    (progn
      (setq parsed *urb-road-default-profiles*)
      (urb:config-write "ROAD_PROFILES" (urb:serialize-lisp parsed))))
  (setq migrated (urb:migrate-budget-road-profiles parsed))
  (if (not (equal migrated parsed))
    (progn
      (setq parsed migrated)
      (urb:config-write "ROAD_PROFILES" (urb:serialize-lisp parsed))))
  parsed)

(defun urb:save-road-profiles (profiles)
  (urb:config-write "ROAD_PROFILES" (urb:serialize-lisp profiles))
  profiles)

(defun urb:road-profile-names (/ result profile)
  (foreach profile (urb:road-profiles)
    (setq result (cons (car profile) result)))
  (reverse result))

(defun urb:road-profile-by-name (name / found profile)
  (foreach profile (urb:road-profiles)
    (if (urb:string-equal-p (car profile) name)
      (setq found profile)))
  found)

(defun urb:replace-road-profile (profiles old-name new-profile / result profile)
  (foreach profile profiles
    (if (and old-name (urb:string-equal-p (car profile) old-name))
      (setq result (cons new-profile result))
      (setq result (cons profile result))))
  (if (null old-name) (setq result (cons new-profile result)))
  (reverse result))

(defun urb:remove-road-profile (profiles name / result profile)
  (foreach profile profiles
    (if (not (urb:string-equal-p (car profile) name))
      (setq result (cons profile result))))
  (reverse result))

;; 4.1.0: incorpora al DWG actual los perfiles de diseno que falten,
;; sin tocar los que el usuario ya creo o modifico. Los dibujos nuevos
;; los reciben solos; los dibujos con biblioteca ya guardada usan esto.
(defun urb:merge-default-road-profiles (/ profiles candidate added)
  (setq profiles (urb:road-profiles))
  (setq added 0)
  (foreach candidate *urb-road-default-profiles*
    (if (not
          (vl-some
            '(lambda (profile)
              (urb:string-equal-p (car profile) (car candidate)))
            profiles))
      (progn
        (setq profiles (append profiles (list candidate)))
        (setq added (1+ added)))))
  (if (> added 0)
    (urb:save-road-profiles profiles))
  added)

(defun urb:load-base-profiles-command (/ added)
  (setq added (urb:merge-default-road-profiles))
  (if (> added 0)
    (prompt
      (strcat
        "\nPerfiles de diseno agregados a este dibujo: "
        (itoa added) "."))
    (prompt
      "\nEste dibujo ya tiene todos los perfiles de diseno."))
  (princ)
)

(defun urb:road-profile-in-use-p (name / ss index data found)
  (setq ss (ssget "_X" '((-3 ("URB_VIA")))))
  (if ss
    (progn
      (setq index 0)
      (while (and (< index (sslength ss)) (not found))
        (setq data
          (urb:get-xdata-strings (ssname ss index) "URB_VIA"))
        (if (and data (> (length data) 4)
                 (urb:string-equal-p (nth 4 data) name))
          (setq found T))
        (setq index (1+ index)))))
  found)

(defun urb:write-road-profile-dcl (/ filename)
  (setq filename (urb:temp-file "urbanismo_via_perfiles" ".dcl"))
  (if
    (urb:write-lines filename
      '("urb_profile_manager : dialog { label = \"Perfiles estratigraficos de vias\";"
        ": list_box { label = \"Perfiles disponibles\"; key = \"profiles\"; height = 9; width = 48; }"
        ": row { : button { label = \"Nuevo\"; key = \"new\"; } : button { label = \"Editar\"; key = \"edit\"; } : button { label = \"Eliminar\"; key = \"delete\"; } }"
        ": boxed_column { label = \"Sobreexcavacion y esponjamiento (todo el movimiento de tierras)\";"
        ": row { : text { label = \"Material no portante bajo el terreno (m)\"; width = 38; } : edit_box { key = \"over_depth\"; edit_width = 12; } }"
        ": row { : text { label = \"Expansion del material de corte (%)\"; width = 38; } : edit_box { key = \"cut_exp\"; edit_width = 12; } }"
        ": row { : text { label = \"Sobreconsumo del relleno compactado (%)\"; width = 38; } : edit_box { key = \"fill_shrink\"; edit_width = 12; } }"
        ": button { label = \"Guardar sobreexcavacion\"; key = \"save_over\"; width = 30; } }"
        "cancel_button; }"
        "urb_profile_editor : dialog { label = \"Perfil estratigrafico vial\";"
        ": edit_box { label = \"Nombre del perfil\"; key = \"name\"; edit_width = 30; }"
        ": list_box { label = \"Capas de arriba hacia abajo\"; key = \"layers\"; height = 9; width = 62; }"
        ": boxed_column { label = \"Capa\";"
        ": edit_box { label = \"Material\"; key = \"material\"; edit_width = 30; }"
        ": popup_list { label = \"Tipo\"; key = \"type\"; }"
        ": edit_box { label = \"Espesor (cm, solo volumen)\"; key = \"thickness\"; edit_width = 12; }"
        ": edit_box { label = \"Traslapo (%, geosinteticos)\"; key = \"overlap\"; edit_width = 12; }"
        ": popup_list { label = \"Area de aplicacion\"; key = \"scope\"; }"
        ": row { : button { label = \"Agregar\"; key = \"add_layer\"; } : button { label = \"Actualizar\"; key = \"update_layer\"; } : button { label = \"Quitar\"; key = \"remove_layer\"; } } }"
        "ok_cancel; }"))
    filename))

;; BUG (mismo patron de distance/length): "type" es una funcion nativa
;; de AutoLISP; usarla como variable local tapa la funcion mientras esta
;; activa, y urb:string-equal-p (via urb:safe-string) SI llama (type
;; value) internamente -- rompe con "no function definition: TYPE".
(defun urb:profile-layer-label (layer / layer-type layer-scope)
  (setq layer-type (nth 1 layer))
  (setq layer-scope (urb:safe-string (nth 4 layer) "Total"))
  (strcat (nth 0 layer) " | " layer-type
    (if (urb:string-equal-p layer-type "Volumen")
      (strcat " | " (rtos (* 100.0 (atof (nth 2 layer))) 2 2) " cm")
      (strcat " | traslapo " (rtos (atof (nth 3 layer)) 2 1) "%"))
    " | " layer-scope))

(defun urb:profile-editor-refresh (/ layer)
  (start_list "layers")
  (foreach layer *urb-profile-edit-layers*
    (add_list (urb:profile-layer-label layer)))
  (end_list)
  (set_tile "layers" "0")
  (if *urb-profile-edit-layers* (urb:profile-editor-select "0")))

(defun urb:profile-editor-select (value / layer)
  (setq *urb-profile-layer-index* (atoi value))
  (setq layer (nth *urb-profile-layer-index* *urb-profile-edit-layers*))
  (if layer
    (progn
      (set_tile "material" (nth 0 layer))
      (set_tile "type" (itoa (urb:index-of (nth 1 layer) *urb-road-profile-types*)))
      (set_tile "thickness" (rtos (* 100.0 (atof (nth 2 layer))) 2 2))
      (set_tile "overlap" (rtos (atof (nth 3 layer)) 2 2))
      (set_tile "scope"
        (itoa
          (urb:index-of
            (urb:safe-string (nth 4 layer) "Total")
            *urb-road-profile-scopes*))))))

;; "type" tapa la funcion nativa mientras esta activa (ver nota en
;; urb:profile-layer-label); renombrado a layer-type.
(defun urb:profile-editor-layer-from-tiles
  (/ material layer-type thickness overlap layer-scope)
  (setq material (vl-string-trim " " (get_tile "material")))
  (setq layer-type (nth (atoi (get_tile "type")) *urb-road-profile-types*))
  (setq thickness (urb:parse-real (get_tile "thickness")))
  (setq overlap (urb:parse-real (get_tile "overlap")))
  (setq layer-scope
    (nth (atoi (get_tile "scope")) *urb-road-profile-scopes*))
  (cond
    ((= material "") (alert "Escriba el material de la capa.") nil)
    ((null thickness) (alert "El espesor no es un numero valido.") nil)
    ((null overlap) (alert "El traslapo no es un numero valido.") nil)
    ((and (urb:string-equal-p layer-type "Volumen") (<= thickness 0.0))
      (alert "Las capas volumetricas requieren un espesor mayor que cero.") nil)
    (T
      (setq thickness (/ thickness 100.0))
      (setq overlap (max 0.0 overlap))
      (list material layer-type (rtos thickness 2 6)
            (rtos overlap 2 4) layer-scope))))

(defun urb:profile-editor-add-layer (/ layer)
  (if (setq layer (urb:profile-editor-layer-from-tiles))
    (progn
      (setq *urb-profile-edit-layers*
        (append *urb-profile-edit-layers* (list layer)))
      (urb:profile-editor-refresh))))

(defun urb:profile-editor-update-layer (/ layer index result item position)
  (if (and *urb-profile-edit-layers*
           (setq layer (urb:profile-editor-layer-from-tiles)))
    (progn
      (setq index 0)
      (foreach item *urb-profile-edit-layers*
        (setq result
          (append result
            (list (if (= index *urb-profile-layer-index*) layer item))))
        (setq index (1+ index)))
      (setq *urb-profile-edit-layers* result)
      (urb:profile-editor-refresh))))

(defun urb:profile-editor-remove-layer (/ index result item)
  (if *urb-profile-edit-layers*
    (progn
      (setq index 0)
      (foreach item *urb-profile-edit-layers*
        (if (/= index *urb-profile-layer-index*)
          (setq result (append result (list item))))
        (setq index (1+ index)))
      (setq *urb-profile-edit-layers* result)
      (urb:profile-editor-refresh))))

(defun urb:profile-editor-accept ()
  (setq *urb-profile-edit-name* (vl-string-trim " " (get_tile "name")))
  (cond
    ((= *urb-profile-edit-name* "")
      (alert "Escriba un nombre para el perfil.") nil)
    ((null *urb-profile-edit-layers*)
      (alert "Agregue al menos una capa.") nil)
    (T T)))

(defun urb:edit-road-profile (profile / dcl result)
  (setq *urb-profile-edit-name* (if profile (car profile) ""))
  (setq *urb-profile-edit-layers* (if profile (cadr profile) nil))
  (setq *urb-profile-layer-index* 0)
  (setq dcl (load_dialog (urb:write-road-profile-dcl)))
  (if (and (> dcl 0) (new_dialog "urb_profile_editor" dcl))
    (progn
      (set_tile "name" *urb-profile-edit-name*)
      (urb:fill-popup "type" *urb-road-profile-types* 0)
      (urb:fill-popup "scope" *urb-road-profile-scopes* 0)
      (set_tile "thickness" "0.00")
      (set_tile "overlap" "0.00")
      (urb:profile-editor-refresh)
      (action_tile "layers" "(urb:profile-editor-select $value)")
      (action_tile "add_layer" "(urb:profile-editor-add-layer)")
      (action_tile "update_layer" "(urb:profile-editor-update-layer)")
      (action_tile "remove_layer" "(urb:profile-editor-remove-layer)")
      (action_tile "accept" "(if (urb:profile-editor-accept) (done_dialog 1))")
      (action_tile "cancel" "(done_dialog 0)")
      (if (= 1 (start_dialog))
        (setq result (list *urb-profile-edit-name* *urb-profile-edit-layers*)))))
  (if (> dcl 0) (unload_dialog dcl))
  result)

(defun urb:profile-manager-dialog (profiles / dcl action index profile)
  (setq dcl (load_dialog (urb:write-road-profile-dcl)))
  (if (and (> dcl 0) (new_dialog "urb_profile_manager" dcl))
    (progn
      (start_list "profiles")
      (foreach profile profiles (add_list (car profile)))
      (end_list)
      (set_tile "profiles" "0")
      (urb:overexc-set-tiles)
      (action_tile "save_over" "(if (urb:overexc-capture) (alert \"Sobreexcavacion guardada en este dibujo.\"))")
      (action_tile "new" "(setq action \"new\" index (atoi (get_tile \"profiles\")))(done_dialog 1)")
      (action_tile "edit" "(setq action \"edit\" index (atoi (get_tile \"profiles\")))(done_dialog 1)")
      (action_tile "delete" "(setq action \"delete\" index (atoi (get_tile \"profiles\")))(done_dialog 1)")
      (action_tile "cancel" "(done_dialog 0)")
      (start_dialog)))
  (if (> dcl 0) (unload_dialog dcl))
  (if action (list action index)))

(defun urb:manage-road-profiles (/ profiles choice action index old edited continue)
  (setq continue T)
  (while continue
    (setq profiles (urb:road-profiles))
    (setq choice (urb:profile-manager-dialog profiles))
    (if (null choice)
      (setq continue nil)
      (progn
        (setq action (car choice) index (cadr choice))
        (setq old (nth index profiles))
        (cond
          ((= action "new")
            (if (setq edited (urb:edit-road-profile nil))
              (urb:save-road-profiles
                (urb:replace-road-profile profiles nil edited))))
          ((= action "edit")
            (if (and old (setq edited (urb:edit-road-profile old)))
              (if (and
                    (not (urb:string-equal-p (car old) (car edited)))
                    (urb:road-profile-in-use-p (car old)))
                (alert
                  (strcat
                    "El perfil esta asignado a una via."
                    " Puede editar sus capas, pero no cambiarle el nombre."))
                (urb:save-road-profiles
                  (urb:replace-road-profile profiles (car old) edited)))))
          ((= action "delete")
            (cond
              ((null old) nil)
              ((= (length profiles) 1)
                (alert "Debe conservar al menos un perfil."))
              ((urb:road-profile-in-use-p (car old))
                (alert "El perfil esta asignado a una via y no puede eliminarse."))
              (T
                (urb:save-road-profiles
                  (urb:remove-road-profile profiles (car old)))))))))
  (princ)))

(defun urb:add-unique-string (value values)
  (if (or (null value) (= value "")
          (vl-some '(lambda (item) (urb:string-equal-p item value)) values))
    values
    (append values (list value))))

(defun urb:civil-surface-names (/ ss index ename obj name result)
  (setq ss
    (ssget "_X"
      '((0 . "AECC_TIN_SURFACE,AECC_GRID_SURFACE,AECC_TIN_VOLUME_SURFACE"))))
  (if ss
    (progn
      (setq index 0)
      (repeat (sslength ss)
        (setq ename (ssname ss index))
        (setq obj (vlax-ename->vla-object ename))
        (setq name (vl-catch-all-apply 'vla-get-Name (list obj)))
        (if (and name (not (vl-catch-all-error-p name)))
          (setq result (urb:add-unique-string name result)))
        (setq index (1+ index)))))
  (if result result '("Seleccionar en dibujo")))

(defun urb:write-road-dcl (/ filename)
  (setq filename (urb:temp-file "urbanismo_via" ".dcl"))
  (if
    (urb:write-lines filename
      (list
        "urb_road : dialog { label = \"Crear / editar via\";"
        ": boxed_column { label = \"Clasificacion\";"
        ": edit_box { label = \"Nombre de la via\"; key = \"name\"; edit_width = 24; }"
        ;; etapa/subetapa ocultas cuando las etapas estan deshabilitadas
        (if (urb:etapas-enabled-p)
          ": popup_list { label = \"Etapa\"; key = \"etapa\"; }" "")
        (if (urb:etapas-enabled-p)
          ": popup_list { label = \"Subetapa\"; key = \"subetapa\"; }" "")
        ": popup_list { label = \"Perfil estratigrafico\"; key = \"profile\"; } }"
        ": boxed_column { label = \"Referencia\";"
        ": popup_list { label = \"Eje / alineamiento (admite XREF)\"; key = \"alignment\"; }"
        ": popup_list { label = \"Superficie topografica\"; key = \"surface\"; }"
        ": popup_list { label = \"Cotas de rasante (admite otro XREF)\"; key = \"cota\"; }"
        ": edit_box { label = \"Abscisado cada (m)\"; key = \"station_interval\"; edit_width = 14; } }"
        ": boxed_column { label = \"Geometria\";"
        ": text { label = \"El contorno cerrado define el area y el ancho real de la via.\"; }"
        ": popup_list { label = \"Sobreancho\"; key = \"overwidth\"; }"
        ": text { label = \"Las magnitudes se modifican en Ajustes > Tabla de anchos.\"; } }"
        "ok_cancel; }"))
    filename))

(defun urb:road-default (defaults key fallback / pair)
  (setq pair (assoc key defaults))
  (if pair (cdr pair) fallback))

(defun urb:road-dialog-update-subetapa ()
  (setq *urb-road-dialog-etapa*
    (nth (atoi (get_tile "etapa")) *urb-etapa-list*))
  (urb:fill-popup "subetapa"
    (urb:subetapas-for *urb-road-dialog-etapa*) 0))

(defun urb:road-dialog-update-overwidth () nil)

(defun urb:road-dialog-capture
  (/ name interval stage subetapas mode left right)
  (setq name (vl-string-trim " " (get_tile "name")))
  (setq interval (urb:parse-real (get_tile "station_interval")))
  (setq mode
    (nth (atoi (get_tile "overwidth")) *urb-road-overwidth-modes*))
  (cond
    ((= name "") (alert "Escriba el nombre de la via.") nil)
    ((null interval) (alert "El intervalo no es un numero valido.") nil)
    ((<= interval 0.0) (alert "El intervalo debe ser mayor que cero.") nil)
    (T
      (setq stage
        (if (urb:etapas-enabled-p)
          (nth (atoi (get_tile "etapa")) *urb-etapa-list*)
          (car *urb-etapa-list*)))
      (setq subetapas (urb:subetapas-for stage))
      (setq left
        (if (member mode '("Izquierdo" "Ambos"))
          *urb-road-overwidth-left* 0.0))
      (setq right
        (if (member mode '("Derecho" "Ambos"))
          *urb-road-overwidth-right* 0.0))
      (setq *urb-road-dialog-result*
        (list
          name
          stage
          (if (urb:etapas-enabled-p)
            (nth (atoi (get_tile "subetapa")) subetapas)
            (car subetapas))
          (nth (atoi (get_tile "profile")) *urb-road-dialog-profiles*)
          (nth (atoi (get_tile "alignment")) *urb-road-alignment-modes*)
          (nth (atoi (get_tile "surface")) *urb-road-dialog-surfaces*)
          (nth (atoi (get_tile "cota")) *urb-road-cota-modes*)
          ;; La abscisa inicial ya no se pide aqui: se sugiere sola
          ;; despues de dibujar el contorno (ver urb:create-road).
          ""
          (rtos interval 2 4)
          mode
          (rtos left 2 4)
          (rtos right 2 4)
          "0.0000"))
      T)))

;; 2026-08-14 v4.24.0: nombres de via unicos. Con 5 vias llamadas "VIA-01"
;; en el maestro real, las memorias y el enlace al presupuesto se vuelven
;; ambiguos; el dialogo ahora sugiere el siguiente "VIA-NN" libre y la
;; creacion avisa si el nombre ya existe (aviso, no bloqueo: el usuario
;; puede repetir nombre a proposito entre etapas).
(defun urb:road-names (/ filters ss i d names)
  (setq names nil)
  (foreach filters
    '(((0 . "INSERT") (-3 ("URB_VIA"))) ((0 . "LWPOLYLINE") (-3 ("URB_VIA"))))
    (setq ss (ssget "_X" filters) i 0)
    (if ss
      (repeat (sslength ss)
        (setq d (urb:get-xdata-strings (ssname ss i) "URB_VIA"))
        (if (and d (> (length d) 1))
          (setq names
            (cons (strcase (urb:safe-string (nth 1 d) "")) names)))
        (setq i (1+ i)))))
  names)

(defun urb:road-name-exists-p (name)
  (if (member (strcase (urb:safe-string name "")) (urb:road-names)) T nil))

(defun urb:next-road-name (/ names item best num)
  (setq names (urb:road-names) best 0)
  (foreach item names
    (if (wcmatch item "VIA-*")
      (progn
        (setq num (atoi (substr item 5)))
        (if (> num best) (setq best num)))))
  (setq num (1+ best))
  (strcat "VIA-" (if (< num 10) (strcat "0" (itoa num)) (itoa num))))

(defun urb:dialog-road (defaults / dcl ok stage sub profile surface cota over)
  (setq *urb-road-dialog-profiles* (urb:road-profile-names))
  (setq *urb-road-dialog-surfaces* (urb:civil-surface-names))
  (setq surface (urb:road-default defaults "surface" (car *urb-road-dialog-surfaces*)))
  (setq *urb-road-dialog-surfaces*
    (urb:add-unique-string surface *urb-road-dialog-surfaces*))
  (setq stage (urb:road-default defaults "stage" "1"))
  (setq sub (urb:road-default defaults "substage" stage))
  (setq profile (urb:road-default defaults "profile" (car *urb-road-dialog-profiles*)))
  (setq cota (urb:road-default defaults "cota" "Textos por capa"))
  ;; Vias antiguas pueden guardar modos ya retirados del dialogo. Al
  ;; editarlas se llevan a la opcion vigente sin dejar un indice nulo.
  (if (not (member cota *urb-road-cota-modes*))
    (setq cota "Textos por capa"))
  ;; Estudio AUS-10786-10: sobreancho minimo 1.0 m a cada lado en las
  ;; capas granulares, por eso el predeterminado es Ambos con 1.00 m.
  (setq over (urb:road-default defaults "overwidth" "Ambos"))
  (if (not (member over *urb-road-overwidth-modes*)) (setq over "Ambos"))
  (setq *urb-road-dialog-result* nil)
  (setq dcl (load_dialog (urb:write-road-dcl)))
  (if (and (> dcl 0) (new_dialog "urb_road" dcl))
    (progn
      (set_tile "name" (urb:road-default defaults "name" (urb:next-road-name)))
      (if (urb:etapas-enabled-p)
        (progn
          (urb:fill-popup "etapa" *urb-etapa-list*
            (urb:index-of stage *urb-etapa-list*))
          (urb:fill-popup "subetapa" (urb:subetapas-for stage)
            (urb:index-of sub (urb:subetapas-for stage)))
          (action_tile "etapa" "(urb:road-dialog-update-subetapa)")))
      (urb:fill-popup "profile" *urb-road-dialog-profiles*
        (urb:index-of profile *urb-road-dialog-profiles*))
      (urb:fill-popup "alignment" *urb-road-alignment-modes*
        (urb:index-of (urb:road-default defaults "alignment" "Existente")
          *urb-road-alignment-modes*))
      (urb:fill-popup "surface" *urb-road-dialog-surfaces*
        (urb:index-of surface *urb-road-dialog-surfaces*))
      (urb:fill-popup "cota" *urb-road-cota-modes*
        (urb:index-of cota *urb-road-cota-modes*))
      (urb:fill-popup "overwidth" *urb-road-overwidth-modes*
        (urb:index-of over *urb-road-overwidth-modes*))
      (set_tile "station_interval" (urb:road-default defaults "station_interval" "5.00"))
      (urb:road-dialog-update-overwidth)
      (action_tile "overwidth" "(urb:road-dialog-update-overwidth)")
      (action_tile "accept" "(if (urb:road-dialog-capture) (done_dialog 1))")
      (action_tile "cancel" "(done_dialog 0)")
      (setq ok (= 1 (start_dialog)))))
  (if (> dcl 0) (unload_dialog dcl))
  (if ok *urb-road-dialog-result*))

(defun urb:curve-entity-p (ename / result)
  (setq result
    (vl-catch-all-apply 'vlax-curve-getEndParam (list ename)))
  (and ename (not (vl-catch-all-error-p result))))

;; BUG (existia desde antes de esta sesion): vl-cmdf solo ENVIA el
;; comando PLINE, no espera a que el usuario termine de dibujar. Sin el
;; bucle "CMDACTIVE" de abajo, entlast se revisaba de inmediato (con el
;; PLINE recien iniciado, 0 puntos), asi que urb:draw-road-boundary
;; siempre recibia un contorno vacio ("no genera un area valida") y el
;; comando de via terminaba ahi -- todo lo dibujado despues quedaba
;; como un PLINE suelto, sin relacion con la via.
(defun urb:draw-polyline
  (message layer / before ename obj old-plinewid *error*)
  (setq old-plinewid (getvar "PLINEWID"))
  (defun *error* (msg)
    (if old-plinewid (setvar "PLINEWID" old-plinewid))
    (if (and msg
             (not (member msg '("Function cancelled" "quit / exit abort"))))
      (prompt (strcat "\nError al dibujar: " msg)))
    (princ))
  (setvar "PLINEWID" 0.0)
  (prompt message)
  (setq before (entlast))
  (urb:draw-polyline-interactive old-plinewid)
  (setq ename (entlast))
  (if (and ename (/= ename before))
    (progn
      (setq obj (vlax-ename->vla-object ename))
      (if layer (vla-put-Layer obj layer))
      ename)))

;; Cache en memoria de sesion (boundary-handle -> ename del eje ya
;; resuelto). handent no puede volver a encontrar un eje que vive
;; dentro de un xref (su handle pertenece a la base de datos del xref,
;; no a la del dibujo actual), asi que sin esta cache el usuario tenia
;; que volver a seleccionar el eje con nentsel en CADA edicion, aunque
;; fuera la misma via recien creada en la misma sesion de AutoCAD. La
;; cache se pierde si se cierra/reabre el dibujo o se recarga el xref
;; (el ename deja de ser valido); en ese caso se vuelve a pedir una
;; sola vez y se recachea con el nuevo ename.
(setq *urb-road-axis-cache* nil)

(defun urb:cache-road-axis (boundary-handle axis / entry)
  (if (and (/= (urb:safe-string boundary-handle "") "")
           axis
           (urb:curve-entity-p axis))
    (progn
      (setq entry (assoc boundary-handle *urb-road-axis-cache*))
      (if entry
        (setq *urb-road-axis-cache*
          (subst (cons boundary-handle axis) entry *urb-road-axis-cache*))
        (setq *urb-road-axis-cache*
          (cons (cons boundary-handle axis) *urb-road-axis-cache*)))
      axis)
    nil))

(defun urb:cached-road-axis (boundary-handle / entry axis check)
  (setq entry (assoc boundary-handle *urb-road-axis-cache*))
  (if entry
    (progn
      (setq axis (cdr entry))
      (setq check (vl-catch-all-apply 'entget (list axis)))
      (if (or (vl-catch-all-error-p check)
              (null check)
              (not (urb:curve-entity-p axis)))
        (progn
          (setq *urb-road-axis-cache*
            (vl-remove entry *urb-road-axis-cache*))
          nil)
        axis))
    nil))

(defun urb:select-or-draw-road-axis (mode / selected ename)
  (urb:ensure-layer "URB-VIA" 8 T)
  (if (urb:string-equal-p mode "Nuevo")
    (setq ename
      (urb:draw-polyline
        "\nDibuje el eje de la via. Enter termina: " "URB-VIA"))
    (progn
      ;; nentsel (no entsel) perfora bloques y xrefs: permite tomar como
      ;; eje una polilinea que vive dentro de una referencia externa.
      (setq selected
        (nentsel
          (strcat
            "\nSeleccione una polilinea del eje dentro o fuera del XREF."
            " Aunque se resalte el XREF completo, se usara la entidad anidada: ")))
      (if selected (setq ename (car selected)))))
  (if (and ename (urb:curve-entity-p ename))
    ename
    (progn (prompt "\nEl eje seleccionado no es una curva valida.") nil)))

(defun urb:road-axis-direction (/ choice)
  (initget "Inicio Final")
  (setq choice
    (getkword "\nSentido del abscisado [Inicio/Final] <Inicio>: "))
  (if choice choice "Inicio"))

(defun urb:station-number (value / text position kilometer remainder)
  (setq text (vl-string-translate "," "." (urb:safe-string value "0")))
  (setq position (vl-string-search "+" text))
  (if position
    (progn
      (setq kilometer (atof (substr text 1 position)))
      (setq remainder (atof (substr text (+ position 2))))
      (+ (* kilometer 1000.0) remainder))
    (atof text)))

(defun urb:pad-station-remainder (value / text dot whole decimal)
  (setq text (rtos value 2 (if (< (abs (- value (fix value))) 0.001) 0 2)))
  (setq dot (vl-string-search "." text))
  (if dot
    (setq whole (substr text 1 dot) decimal (substr text (+ dot 2)))
    (setq whole text decimal ""))
  (while (and (> (strlen decimal) 0)
              (= (substr decimal (strlen decimal) 1) "0"))
    (setq decimal (substr decimal 1 (1- (strlen decimal)))))
  (while (< (strlen whole) 3) (setq whole (strcat "0" whole)))
  (strcat whole (if (= decimal "") "" (strcat "." decimal))))

(defun urb:format-station (value / kilometer remainder)
  (setq value (max 0.0 value))
  (setq kilometer (fix (/ value 1000.0)))
  (setq remainder (- value (* kilometer 1000.0)))
  (strcat (itoa kilometer) "+" (urb:pad-station-remainder remainder)))

;; La abscisa inicial ya no se digita antes de dibujar: se sugiere
;; despues, a partir de axis-start (donde el contorno cayo sobre el
;; eje compartido). Enter acepta la sugerencia; si el usuario tiene
;; una referencia de abscisado distinta, la escribe y se usa esa.
(defun urb:prompt-station-start (suggested / label)
  (setq label
    (getstring
      (strcat "\nAbscisa inicial de este tramo <" suggested ">: ")))
  (if (= (vl-string-trim " " (urb:safe-string label "")) "")
    suggested
    label)
)

(defun urb:tag-road-generated (obj parent-handle / ename)
  (if obj
    (progn
      (setq ename (vlax-vla-object->ename obj))
      (urb:set-xdata-strings ename "URB_VIA_GEN" (list parent-handle))))
  obj)

(defun urb:delete-road-generated (parent-handle / ss index ename data obj count)
  (setq ss (ssget "_X" '((-3 ("URB_VIA_GEN")))))
  (if ss
    (progn
      (setq index 0 count 0)
      (repeat (sslength ss)
        (setq ename (ssname ss index))
        (setq data (urb:get-xdata-strings ename "URB_VIA_GEN"))
        (if (and data (= (car data) parent-handle))
          (progn
            (setq obj (vlax-ename->vla-object ename))
            (if (urb:safe-delete obj)
              (setq count (1+ count)))))
        (setq index (1+ index)))))
  (if count count 0))

;; Agrupa el contorno de la via con todo su abscisado (URB_VIA_GEN) en
;; un GROUP nativo de AutoCAD: con PICKSTYLE en modo grupo (el valor por
;; defecto), un clic en cualquier miembro selecciona todos, y se puede
;; borrar todo de una sola vez. No se uso un bloque (como en andenes)
;; (2026-07-06) Se reemplazo el empaquetado por GROUP con un BLOQUE de
;; atributos invisibles (ver urb:package-road mas abajo), igual que
;; anden -- asi los datos calculados se ven en el panel Properties de
;; AutoCAD con solo seleccionar la via. urb:create-group/urb:refresh-
;; road-group quedaron sin uso y se retiraron.
(defun urb:road-generated-objects (parent-handle / ss index ename data objects)
  (setq ss (ssget "_X" '((-3 ("URB_VIA_GEN")))))
  (if ss
    (progn
      (setq index 0)
      (repeat (sslength ss)
        (setq ename (ssname ss index))
        (setq data (urb:get-xdata-strings ename "URB_VIA_GEN"))
        (if (and data (= (car data) parent-handle))
          (setq objects (cons (vlax-ename->vla-object ename) objects)))
        (setq index (1+ index)))))
  (reverse objects)
)

(defun urb:create-road-axis-display
  (boundary axis / data start span finish d step point coords poly handle via-id)
  ;; Copia grafica del tramo de eje dentro del bloque. El eje fuente se
  ;; conserva como referencia de calculo (puede pertenecer a un XREF),
  ;; mientras esta polilinea queda seleccionable junto con la via.
  (setq data (urb:get-xdata-strings boundary "URB_VIA")
        start (atof (urb:safe-string (nth 21 data) "0"))
        span (atof (urb:safe-string (nth 18 data) "0"))
        finish (+ start span)
        step (max 0.25 (min 2.0 (/ (max span 0.25) 40.0)))
        d start)
  (while (< d (- finish 1e-7))
    (setq point
      (vl-catch-all-apply 'vlax-curve-getPointAtDist (list axis d)))
    (if (and point (not (vl-catch-all-error-p point)))
      (setq coords (append coords (list (car point) (cadr point)))))
    (setq d (+ d step)))
  (setq point
    (vl-catch-all-apply 'vlax-curve-getPointAtDist (list axis finish)))
  (if (and point (not (vl-catch-all-error-p point)))
    (setq coords (append coords (list (car point) (cadr point)))))
  (if (>= (length coords) 4)
    (progn
      (setq poly
        (vla-AddLightWeightPolyline
          (urb:space) (urb:double-array-variant coords)))
      (vla-put-Layer poly "URB-VIA")
      (vla-put-Color poly 256)
      (if (vlax-property-available-p poly 'ConstantWidth T)
        (vla-put-ConstantWidth poly 0.04))
      (setq handle
        (vla-get-Handle (vlax-ename->vla-object boundary)))
      (urb:tag-road-generated poly handle)
      (setq via-id (urb:safe-string (nth 22 data) ""))
      (urb:set-xdata-strings
        (vlax-vla-object->ename poly) "URB_VIA_EJE"
        (list handle via-id "EJE_DENTRO_BLOQUE"))
      poly)))

(defun urb:create-road-display-hatch (boundary / obj hatch handle)
  (setq obj (vlax-ename->vla-object boundary))
  (setq hatch
    (vl-catch-all-apply
      'vla-AddHatch (list (urb:space) 1 "SOLID" :vlax-true)))
  (if (not (vl-catch-all-error-p hatch))
    (progn
      (if (vl-catch-all-error-p
            (vl-catch-all-apply 'vla-AppendOuterLoop
              (list hatch (urb:make-loop-array obj))))
        (progn (urb:safe-delete hatch) (setq hatch nil))
        (progn
          (vla-put-Layer hatch "URB-VIA")
          (vla-put-Color hatch 256)
          ;; COM acepta 0..90 como texto en versiones recientes; si una
          ;; version no expone la propiedad, el hatch sigue siendo valido.
          (if (vlax-property-available-p hatch 'EntityTransparency T)
            (vl-catch-all-apply 'vlax-put-property
              (list hatch 'EntityTransparency "75")))
          (urb:evaluate-render-hatch hatch)
          (setq handle
            (vla-get-Handle (vlax-ename->vla-object boundary)))
          (urb:tag-road-generated hatch handle)))))
  hatch)

;; ename es un bloque de via ya empacado (mismo criterio que
;; urb:anden-block-p): referencia de bloque de primer nivel con xdata
;; URB_VIA valida.
(defun urb:road-block-p (ename / obj data)
  (setq obj (vl-catch-all-apply 'vlax-ename->vla-object (list ename)))
  (and
    (not (vl-catch-all-error-p obj))
    (= (vla-get-ObjectName obj) "AcDbBlockReference")
    (setq data (urb:get-xdata-strings ename "URB_VIA"))
    (urb:string-equal-p (car data) "VIA"))
)

;; Agrega una propiedad independiente por cada capa del perfil de pavimento.
;; Los atributos son invisibles en el dibujo, pero aparecen en la categoria
;; Atributos de la paleta Propiedades al seleccionar el bloque de la via.
(defun urb:attribute-tag-token (value / text index char code result previous-separator)
  (setq text (strcase (urb:safe-string value "MATERIAL")))
  (setq index 1 result "" previous-separator nil)
  (while (<= index (strlen text))
    (setq char (substr text index 1))
    (setq code (ascii char))
    (if (or (and (>= code 48) (<= code 57))
            (and (>= code 65) (<= code 90)))
      (progn
        (setq result (strcat result char))
        (setq previous-separator nil))
      (if (not previous-separator)
        (progn
          (setq result (strcat result "_"))
          (setq previous-separator T))))
    (setq index (1+ index)))
  (setq result (vl-string-trim "_" result))
  (if (= result "") "MATERIAL" result)
)

(defun urb:add-road-pavement-attributes
  (block point data / area road-length left right left-area right-area
   base-area profile layers layer layer-name layer-type layer-scope
   layer-area quantity unit index tag prompt-text)
  (setq area (atof (urb:safe-string (nth 17 data) "0")))
  (setq road-length (atof (urb:safe-string (nth 18 data) "0")))
  (setq left (atof (urb:safe-string (nth 14 data) "0")))
  (setq right (atof (urb:safe-string (nth 15 data) "0")))
  (setq left-area (min area (* road-length left)))
  (setq right-area (min (- area left-area) (* road-length right)))
  (setq base-area (max 0.0 (- area left-area right-area)))
  (setq profile (urb:road-profile-by-name (nth 4 data)))
  (setq layers (if profile (cadr profile) nil))
  (setq index 1)
  (foreach layer layers
    (setq layer-name
      (urb:budget-road-layer-name
        (urb:safe-string (nth 0 layer) "Capa")))
    (setq layer-type (urb:safe-string (nth 1 layer) "Volumen"))
    (setq layer-scope (urb:safe-string (nth 4 layer) "Total"))
    (setq layer-area
      (if (urb:string-equal-p layer-scope "Base") base-area area))
    (if (urb:string-equal-p layer-type "Volumen")
      (progn
        (setq quantity (* layer-area (atof (nth 2 layer))))
        (setq unit "m3"))
      (progn
        (setq quantity
          (* layer-area (+ 1.0 (/ (atof (nth 3 layer)) 100.0))))
        (setq unit "m2")))
    ;; La paleta Properties muestra el TAG, no el texto del prompt. Por eso
    ;; el tag debe contener el nombre real del material y no PAV_CAPA_1, 2...
    (setq tag (urb:attribute-tag-token layer-name))
    (setq prompt-text
      (strcat "Pavimento - " layer-name " (" unit ")"))
    (urb:add-invisible-attribute
      block point tag prompt-text (rtos quantity 2 2))
    (setq index (1+ index)))
  index
)

(defun urb:road-property-hidden-tag-p (tag)
  (member (strcase (urb:safe-string tag ""))
    '("VIA_PERFIL" "VIA_SUPERFICIE" "VIA_ESTADO"
      "VIA_ABSC_INICIAL" "VIA_MEMORIA" "PAV_ESPESOR_M"
      "VIA_METODO_RASANTE"))
)

(defun urb:road-material-property-tags (data / profile layer result)
  (setq profile (urb:road-profile-by-name (nth 4 data)))
  (foreach layer (if profile (cadr profile) nil)
    (setq result
      (append result
        (list
          (urb:attribute-tag-token
            (urb:budget-road-layer-name (nth 0 layer)))))))
  result
)

(defun urb:clean-road-property-object-list
  (objects material-tags / item tag victims material-index changed new-tag)
  (setq material-index 0 changed 0)
  (foreach item objects
    (setq tag
      (if (vlax-property-available-p item 'TagString)
        (strcase (vla-get-TagString item)) ""))
    (cond
      ((urb:road-property-hidden-tag-p tag)
        (setq victims (cons item victims)))
      ((and (urb:starts-with tag "PAV_")
            (< material-index (length material-tags)))
        (setq new-tag (nth material-index material-tags)
              material-index (1+ material-index))
        (if (and (/= new-tag tag)
                 (vlax-property-available-p item 'TagString T))
          (progn
            (vl-catch-all-apply 'vla-put-TagString (list item new-tag))
            (setq changed (1+ changed)))))))
  (foreach item victims
    (if (urb:safe-delete item) (setq changed (1+ changed))))
  changed
)

(defun urb:clean-existing-road-properties
  (/ ss index ename data obj blocks block-definition items item
   attributes material-tags changed block-result)
  ;; Migra inmediatamente las vias ya empacadas: retira los campos
  ;; administrativos marcados por el usuario y deja los tags de pavimento
  ;; con solo el material. Cada via tiene una definicion de bloque propia.
  (setq ss (ssget "_X" '((0 . "INSERT") (-3 ("URB_VIA"))))
        blocks (vla-get-Blocks (urb:doc)) index 0 changed 0)
  (if ss
    (while (< index (sslength ss))
      (setq ename (ssname ss index)
            data (urb:get-xdata-strings ename "URB_VIA"))
      (if (and data (urb:string-equal-p (car data) "VIA"))
        (progn
          (setq obj (vlax-ename->vla-object ename)
                material-tags (urb:road-material-property-tags data)
                attributes
                  (if (= (vla-get-HasAttributes obj) :vlax-true)
                    (vlax-invoke obj 'GetAttributes) nil))
          (setq changed
            (+ changed
              (urb:clean-road-property-object-list
                attributes material-tags)))
          (setq block-result
            (vl-catch-all-apply 'vla-Item
              (list blocks (vla-get-EffectiveName obj))))
          (if (not (vl-catch-all-error-p block-result))
            (progn
              (setq block-definition block-result items nil)
              (vlax-for item block-definition
                (if (= (vla-get-ObjectName item) "AcDbAttributeDefinition")
                  (setq items (append items (list item)))))
              (setq changed
                (+ changed
                  (urb:clean-road-property-object-list
                    items material-tags)))))))
      (setq index (1+ index))))
  (if (> changed 0) (vla-Regen (urb:doc) 1))
  changed
)

(defun urb:upgrade-existing-road-properties
  (/ ss i road data mov obj blocks bdef bname tags item victims length-value
   left right area overarea footprint-info footprint-area added sync-result spec added-before vals)
  (setq ss (ssget "_X" '((0 . "INSERT") (-3 ("URB_VIA"))))
        i 0 blocks (vla-get-Blocks (urb:doc)) added 0)
  (if ss
    (repeat (sslength ss)
      (setq road (ssname ss i) data (urb:get-xdata-strings road "URB_VIA")
            mov (urb:road-movement-data road)
            obj (vlax-ename->vla-object road)
            bname (vla-get-EffectiveName obj)
            bdef (vl-catch-all-apply 'vla-Item (list blocks bname))
            tags nil victims nil)
      (if (and data (not (vl-catch-all-error-p bdef)))
        (progn
          (vlax-for item bdef
            (cond
              ((= (vla-get-ObjectName item) "AcDbAttributeDefinition")
                (setq tags (cons (strcase (vla-get-TagString item)) tags)))
              ;; El antiguo cuadro MTEXT sobre la calzada ya no se usa.
              ((= (vla-get-ObjectName item) "AcDbMText")
                (setq victims (cons item victims)))))
          (foreach item victims (if (urb:safe-delete item) (setq added (1+ added))))
          (setq added-before added)
          (setq area (atof (urb:safe-string (nth 17 data) "0"))
                length-value (atof (urb:safe-string (nth 18 data) "0"))
                left (atof (urb:safe-string (nth 14 data) "0"))
                right (atof (urb:safe-string (nth 15 data) "0"))
                overarea (* length-value (+ left right))
                footprint-info (vlax-ldata-get road "URB_VIA_HUELLA")
                footprint-area
                  (if (and (listp footprint-info)
                           (numberp (car footprint-info))
                           (>= (car footprint-info) area))
                    (car footprint-info) nil))
          ;; Desde 5.7.5 el calculo de tierras deja el area exacta de la
          ;; huella desplazada. En vias curvas o de ancho variable no es
          ;; igual a longitud * sobreancho; mantener atributos y memoria
          ;; sobre la misma geometria que produjo los volumenes.
          (if footprint-area (setq overarea (- footprint-area area)))
          (foreach spec
            (list
              (list "VIA_AREA_SOBREANCHO_M2" "Area con sobreancho m2"
                (rtos (if footprint-area footprint-area (+ area overarea)) 2 2))
              (list "VIA_SOBREANCHO_M2" "Area exclusiva de sobreancho m2" (rtos overarea 2 2))
              (list "MEMORIAS" "Memorias - use QMEMORIAVIA" "OCULTAR")
              (list "PERFIL" "Perfil longitudinal - MOSTRAR u OCULTAR" "OCULTAR"))
            (if (not (member (car spec) tags))
              (progn
                (urb:add-invisible-attribute bdef '(0.0 0.0 0.0)
                  (car spec) (cadr spec) (caddr spec))
                (setq added (1+ added)))))
          ;; 5.7.2: ATTSYNC solo si a ESTA definicion le falto algo (antes
          ;; corria en cada via en cada apertura: 1,6 s en el maestro) y
          ;; los valores solo se reescriben si cambiaron
          (if (> added added-before)
            (setq sync-result
              (vl-catch-all-apply 'vl-cmdf (list "_.ATTSYNC" "_N" bname))))
          (setq vals (urb:block-attribute-values obj))
          (if (/= (cdr (assoc "VIA_AREA_SOBREANCHO_M2" vals))
                  (rtos (if footprint-area footprint-area (+ area overarea)) 2 2))
            (urb:set-block-attribute obj "VIA_AREA_SOBREANCHO_M2"
              (rtos (if footprint-area footprint-area (+ area overarea)) 2 2)))
          (if (/= (cdr (assoc "VIA_SOBREANCHO_M2" vals)) (rtos overarea 2 2))
            (urb:set-block-attribute obj "VIA_SOBREANCHO_M2" (rtos overarea 2 2)))
          (if (= (urb:safe-string
                    (cdr (assoc "MEMORIAS" (urb:block-attribute-values obj))) "") "")
            (urb:set-block-attribute obj "MEMORIAS" "OCULTAR"))
          (if (= (urb:safe-string
                    (cdr (assoc "PERFIL" (urb:block-attribute-values obj))) "") "")
            (urb:set-block-attribute obj "PERFIL" "OCULTAR"))))
      (setq i (1+ i))))
  added)

;; Empaqueta el contorno + abscisado de una via en un BLOQUE con
;; atributos invisibles (mismo patron que urb:package-anden, linea
;; ~1403): la xdata URB_VIA nunca aparece en el panel
;; Properties de AutoCAD, pero los atributos de bloque si -- asi el
;; usuario ve los datos calculados con solo seleccionar la via, sin
;; correr ningun comando. El eje NO se copia dentro del bloque (puede
;; vivir en un xref); solo su handle sigue viviendo en la xdata, igual
;; que antes.
(defun urb:package-road
  (ename / boundary data mov handle objects point block-name blocks
   block-definition copy-result block-ref obj insert-result block-ename
   xdata-result road-length left right overwidth-area footprint-info
   footprint-area base-area grade-full grade-src grade-check)
  (setq *urb-package-road-stage* "lectura del contorno")
  (setq boundary (vlax-ename->vla-object ename))
  (urb:ensure-layer "URB-VIA" 8 T)
  (setq data (urb:get-xdata-strings ename "URB_VIA"))
  (setq mov (urb:road-movement-data ename))
  (setq footprint-info (vlax-ldata-get ename "URB_VIA_HUELLA"))
  (setq grade-full (urb:road-ldata-stored ename "URB_VIA_RASANTE_FULL")
        grade-src (urb:road-ldata-stored ename "URB_VIA_RASANTE_SRC"))
  (setq handle (vla-get-Handle boundary))
  (setq objects (cons boundary (urb:road-generated-objects handle)))
  (setq point
    (if (urb:lwpoly-points ename)
      (car (urb:lwpoly-points ename))
      '(0.0 0.0 0.0)))
  (setq block-name
    (strcat "URB_VIA_" handle "_" (itoa (getvar "MILLISECS"))))
  (setq blocks (vla-get-Blocks (urb:doc)))
  (setq *urb-package-road-stage* "crear definicion")
  (setq block-definition
    (vla-Add blocks (vlax-3d-point '(0.0 0.0 0.0)) block-name))
  (setq copy-result
    (progn
      (setq *urb-package-road-stage* "copiar geometria")
    (vl-catch-all-apply
      'vla-CopyObjects
      (list (urb:doc) (urb:object-array-variant objects) block-definition))))
  (if (vl-catch-all-error-p copy-result)
    (progn
      (urb:safe-delete block-definition)
      (prompt
        (strcat "\nERROR al crear el bloque de la via: "
          (vl-catch-all-error-message copy-result)))
      nil)
    (progn
      (setq *urb-package-road-stage* "atributos")
      (urb:add-invisible-attribute block-definition point
        "VIA_NOMBRE" "Nombre" (urb:safe-string (nth 1 data) ""))
      (urb:add-invisible-attribute block-definition point
        "VIA_ETAPA" "Etapa" (urb:safe-string (nth 2 data) ""))
      (urb:add-invisible-attribute block-definition point
        "VIA_SUBETAPA" "Subetapa" (urb:safe-string (nth 3 data) ""))
      (urb:add-road-pavement-attributes block-definition point data)
      (urb:add-invisible-attribute block-definition point
        "VIA_AREA_M2" "Area m2"
        (rtos (atof (urb:safe-string (nth 17 data) "0")) 2 2))
      (setq road-length (atof (urb:safe-string (nth 18 data) "0"))
            left (atof (urb:safe-string (nth 14 data) "0"))
            right (atof (urb:safe-string (nth 15 data) "0"))
            base-area (atof (urb:safe-string (nth 17 data) "0"))
            overwidth-area (* road-length (+ left right))
            footprint-area
              (if (and (listp footprint-info)
                       (numberp (car footprint-info))
                       (>= (car footprint-info) base-area))
                (car footprint-info) nil))
      (if footprint-area (setq overwidth-area (- footprint-area base-area)))
      (urb:add-invisible-attribute block-definition point
        "VIA_AREA_SOBREANCHO_M2" "Area con sobreancho m2"
        ;; 2026-08-30: el contorno (nth 17) es la CALZADA; este
        ;; atributo suma el sobreancho adicional para ser fiel a su
        ;; nombre
        (rtos (if footprint-area footprint-area (+ base-area overwidth-area)) 2 2))
      (urb:add-invisible-attribute block-definition point
        "VIA_SOBREANCHO_M2" "Area exclusiva de sobreancho m2"
        (rtos overwidth-area 2 2))
      (urb:add-invisible-attribute block-definition point
        "VIA_LONGITUD_M" "Longitud tramo m"
        (rtos (atof (urb:safe-string (nth 18 data) "0")) 2 2))
      (urb:add-invisible-attribute block-definition point
        "VIA_CORTE_M3" "Corte m3"
        (if mov (urb:safe-string (nth 0 mov) "0") "0"))
      (urb:add-invisible-attribute block-definition point
        "VIA_RELLENO_M3" "Relleno m3"
        (if mov (urb:safe-string (nth 1 mov) "0") "0"))
      (urb:add-invisible-attribute block-definition point
        "MEMORIAS" "Memorias - use QMEMORIAVIA" "OCULTAR")
      (urb:add-invisible-attribute block-definition point
        "PERFIL" "Perfil longitudinal - MOSTRAR u OCULTAR" "OCULTAR")
      (setq insert-result
        (progn
          (setq *urb-package-road-stage* "insertar bloque")
        (vl-catch-all-apply
          'vla-InsertBlock
          (list (urb:space) (vlax-3d-point '(0.0 0.0 0.0))
            block-name 1.0 1.0 1.0 0.0))))
      (if (vl-catch-all-error-p insert-result)
        (progn
          (urb:safe-delete block-definition)
          (prompt
            (strcat "\nERROR al insertar el bloque de la via: "
              (vl-catch-all-error-message insert-result)))
          nil)
        (progn
          (setq block-ref insert-result block-ename (urb:as-ename block-ref))
          (if (not block-ename)
            (progn
              (urb:safe-delete block-ref)
              (urb:safe-delete block-definition)
              (prompt
                "\nERROR: AutoCAD no devolvio una referencia de bloque valida para la via.")
              nil)
            (progn
              (vla-put-Layer block-ref "URB-VIA")
              (setq *urb-package-road-stage* "transferir perfil")
              ;; CopyObjects no conserva de forma fiable el diccionario
              ;; LDATA del contorno. Transferir explicitamente la huella
              ;; que respalda atributos, memorias y movimiento de tierras.
              (if footprint-info
                (vlax-ldata-put block-ename "URB_VIA_HUELLA" footprint-info))
              ;; CopyObjects no garantiza el diccionario LDATA. La rasante
              ;; completa gobierna andenes, senderos y zonas verdes; el
              ;; XDATA compacto queda como respaldo, no como unico origen.
              (if grade-full
                (vl-catch-all-apply 'vlax-ldata-put
                  (list block-ename "URB_VIA_RASANTE_FULL" grade-full)))
              (if grade-src
                (vl-catch-all-apply 'vlax-ldata-put
                  (list block-ename "URB_VIA_RASANTE_SRC" grade-src)))
              (setq grade-check
                (and (or (null grade-full)
                         (equal grade-full
                           (urb:road-ldata-stored block-ename "URB_VIA_RASANTE_FULL")))
                     (or (null grade-src)
                         (equal grade-src
                           (urb:road-ldata-stored block-ename "URB_VIA_RASANTE_SRC")))))
              (setq xdata-result
                (urb:set-xdata-strings block-ename "URB_VIA" data))
              (setq *urb-package-road-stage* "validar y cerrar")
              (if (and xdata-result grade-check)
                (progn
                  (foreach obj objects (urb:safe-delete obj))
                  (vl-catch-all-apply
                    'urb:attach-memory-reactor-to-block (list block-ename))
                  block-ref)
                (progn
                  (urb:safe-delete block-ref)
                  (urb:safe-delete block-definition)
                  (prompt
                    "\nERROR: no fue posible conservar los datos y la rasante del bloque de via.")
                  nil))))))))
)

;; De una lista de objetos ya explotados, la polilinea que de verdad es un
;; contorno: la CERRADA de mayor area. Si ninguna cierra o ninguna tiene
;; area, devuelve la ultima polilinea (comportamiento anterior a v4.86),
;; para no dejar sin contorno a un bloque viejo con geometria rara.
;; Funcion aparte para poder autoprobar la regla de eleccion.
(defun urb:largest-closed-polyline (objects / item area cerrada best best-area ultima)
  (setq best nil best-area nil ultima nil)
  (foreach item objects
    (if (= (vla-get-ObjectName item) "AcDbPolyline")
      (progn
        (setq ultima item)
        (setq cerrada
          (vl-catch-all-apply 'vla-get-Closed (list item)))
        (setq area (vl-catch-all-apply 'vla-get-Area (list item)))
        (if (and (not (vl-catch-all-error-p cerrada))
                 (= cerrada :vlax-true)
                 (numberp area)
                 (> area 1e-6)
                 (or (null best-area) (> area best-area)))
          (setq best item best-area area)))))
  (if best best ultima)
)

;; Desempaca un bloque de via ya empacado: recupera el contorno crudo
;; (capa URB-VIA-CONTORNO) y le reaplica la xdata que tenia el bloque,
;; para que el resto del flujo de edicion siga funcionando igual que
;; con una via nunca empacada. El abscisado generado se descarta (se
;; reconstruye fresco despues); mismo patron que
;; urb:explode-anden-block-boundary.
(defun urb:explode-road-block-boundary
  (ename / obj data mov exploded objects item boundary grade-full grade-src)
  (setq data (urb:get-xdata-strings ename "URB_VIA"))
  (setq mov (urb:road-movement-data ename))
  (setq grade-full (urb:road-ldata-stored ename "URB_VIA_RASANTE_FULL")
        grade-src (urb:road-ldata-stored ename "URB_VIA_RASANTE_SRC"))
  (setq obj (vlax-ename->vla-object ename))
  (setq exploded (vl-catch-all-apply 'vla-Explode (list obj)))
  (if (vl-catch-all-error-p exploded)
    nil
    (progn
      (setq objects (urb:variant-object-list exploded))
      ;; 4.18.0: todas las capas de via se consolidaron en URB-VIA, asi que
      ;; la capa ya no distingue el contorno de las abscisas/datos/tabla
      ;; dentro del bloque explotado.
      ;;
      ;; 2026-09-10 (reporte del usuario: "si edito una via, cuando termino
      ;; de editar me la borra del todo"). Hasta v4.85 esto se resolvia con
      ;; "el contorno es la UNICA LWPOLYLINE del bloque" y se guardaba la
      ;; ULTIMA que apareciera. Ese supuesto ya no se cumple: medido en
      ;; Civil real, el bloque de via trae DOS polilineas (contorno de
      ;; 600,00 m2 y una de apoyo de area 0,00). Si la ultima resultaba ser
      ;; la de apoyo, el contorno REAL se borraba tres lineas mas abajo y
      ;; la via desaparecia. Ahora se escoge por area: el contorno es la
      ;; polilinea CERRADA de mayor area, y solo si ninguna sirve se cae al
      ;; comportamiento anterior.
      (setq boundary (urb:largest-closed-polyline objects))
      (foreach item objects
        (if (not (eq item boundary)) (urb:safe-delete item)))
      (if boundary
        (progn
          (setq boundary (vlax-vla-object->ename boundary))
          (if data (urb:set-xdata-strings boundary "URB_VIA" data))
          (if grade-full
            (vl-catch-all-apply 'vlax-ldata-put
              (list boundary "URB_VIA_RASANTE_FULL" grade-full)))
          (if grade-src
            (vl-catch-all-apply 'vlax-ldata-put
              (list boundary "URB_VIA_RASANTE_SRC" grade-src)))
          ;; Migra una via antigua que aun conserve URB_VIA_MOV al registro
          ;; principal. Las nuevas vias ya llevan el movimiento embebido.
          (if (and mov (< (length data) 32))
            (urb:set-road-movement-data boundary mov))
          boundary)
        nil)))
)

;; BUG (existia desde antes de esta sesion, nunca ejercitado hasta la
;; primera prueba real de una via completa): los parametros/locales se
;; llamaban "distance" y "length", ambos nombres de funciones nativas de
;; AutoLISP. Al llegar a (distance '(0.0 0.0 0.0) derivative), AutoLISP
;; encontraba el PARAMETRO "distance" (un numero, p.ej. 6.80273) en vez
;; de la funcion nativa, e intentaba "llamar" ese numero como funcion:
;; "bad function: 6.80273". Renombrados para no tapar los nativos.
(defun urb:add-road-station
  (axis dist-value station direction parent-handle
   / param point derivative seg-length tangent normal p1 p2 line text text-angle)
  (setq point (vlax-curve-getPointAtDist axis dist-value))
  (setq param (vlax-curve-getParamAtDist axis dist-value))
  (setq derivative (vlax-curve-getFirstDeriv axis param))
  (if (urb:string-equal-p direction "Final")
    (setq derivative (mapcar '- derivative)))
  (setq seg-length (distance '(0.0 0.0 0.0) derivative))
  (if (> seg-length 1e-9)
    (progn
      (setq tangent (mapcar '(lambda (item) (/ item seg-length)) derivative))
      (setq normal (list (- (cadr tangent)) (car tangent) 0.0))
      (setq p1 (mapcar '+ point (mapcar '(lambda (item) (* item 0.50)) normal)))
      (setq p2 (mapcar '- point (mapcar '(lambda (item) (* item 0.50)) normal)))
      (setq line (vla-AddLine (urb:space) (vlax-3d-point p1) (vlax-3d-point p2)))
      (vla-put-Layer line "URB-VIA")
      (urb:tag-road-generated line parent-handle)
      (setq text-angle (atan (cadr tangent) (car tangent)))
      (setq text
        (vla-AddText (urb:space) (urb:format-station station)
          (vlax-3d-point
            (mapcar '+ point (mapcar '(lambda (item) (* item 0.75)) normal)))
          0.45))
      (vla-put-Layer text "URB-VIA")
      (vla-put-Rotation text text-angle)
      (urb:tag-road-generated text parent-handle))))

;; axis-start = punto sobre el eje donde comienza el tramo de esta via
;; (0 si el eje seleccionado coincide con la via); span = longitud propia
;; del tramo (ya no la longitud total del eje, que puede ser mas largo
;; si el eje se comparte entre varias vias).
;;
;; Marcado alineado a una grilla de proyecto (2026-07-06): antes las
;; marcas salian equiespaciadas desde el inicio detectado (p.ej. 0+013,
;; 0+018, 0+023...), sin relacion con la grilla real de cotas del
;; usuario (cada 10 m: 0+010, 0+020, 0+030...). Ahora "interval" se
;; trata como el tamano de esa grilla: siempre se marca el INICIO real
;; y el FINAL real del tramo (aunque no caigan en un multiplo redondo),
;; y en el medio solo los multiplos redondos de interval que quedan
;; estrictamente entre los dos (0+013, 0+020, 0+030, 0+036.89, etc.).
(defun urb:generate-road-stations
  (axis parent-handle start interval direction axis-start span
   / end-label labels next-round label traveled distance-value)
  (urb:ensure-layer "URB-VIA" 8 T)
  (if (or (not (numberp interval)) (<= interval 1e-6))
    (setq interval 10.0))
  (setq end-label (+ start span))
  (setq labels (list start))
  (setq next-round (* interval (fix (1+ (/ start interval)))))
  (if (<= next-round (+ start 1e-6)) (setq next-round (+ next-round interval)))
  (while (< next-round (- end-label 1e-6))
    (setq labels (append labels (list next-round)))
    (setq next-round (+ next-round interval)))
  (setq labels (append labels (list end-label)))
  (foreach label labels
    (setq traveled (- label start))
    (setq distance-value
      (+ axis-start
        (if (urb:string-equal-p direction "Final")
          (- span traveled)
          traveled)))
    (urb:add-road-station axis distance-value label direction parent-handle))
  span)

(defun urb:pick-cota-value (msg / selected ename edata txt value)
  ;; Selecciona un texto/etiqueta de cota y devuelve su valor numerico REAL
  ;; (mp:last-decimal-number devuelve STRING -- se convierte con atof aqui
  ;; mismo; los consumidores hacen aritmetica/rtos directo y truenan con
  ;; un string). Enter u objeto ilegible -> pide digitarla.
  (setq selected (nentsel msg))
  (if selected
    (progn
      (setq ename (car selected) edata (entget ename))
      (setq txt (cdr (assoc 1 edata)))
      (if txt (setq value (mp:last-decimal-number txt)))
      (if value (setq value (atof value)))
      (if value
        (prompt (strcat "\nCota leida de la etiqueta: " (rtos value 2 3))))))
  (if (null value)
    (setq value (getreal "\nNo se pudo leer la cota; digitela (Enter omite): ")))
  value
)

;;; 2026-09-11 (reporte del usuario: "elegi 2565.25 pero me reconoce
;;; siempre la cota de abajo, la de 2562.25"). Las etiquetas de pozo traen
;;; las DOS cotas en un mismo objeto (tapa arriba, batea abajo, en dos
;;; renglones). urb:selected-cota-number usaba mp:last-decimal-number, que
;;; recorre TODO el texto y se queda con el ULTIMO numero -- siempre el de
;;; abajo, se clickeara donde se clickeara. Ahora el texto se parte por
;;; renglones y se toma el renglon que queda bajo el clic.

;; Un numero por renglon, de arriba a abajo. MTEXT separa renglones con \P;
;; en cada renglon se toma el ULTIMO decimal, porque los codigos de formato
;; (\H0.7x; \f...;) van ANTES del contenido y tambien traen decimales.
(defun urb:text-line-numbers (txt / out v)
  (setq txt (vl-string-translate "\n" "\r" (urb:safe-string txt "")))
  (foreach ln (urb:split-string txt "\\P")
    (foreach sub (urb:split-string ln "\r")
      (setq v (mp:last-decimal-number sub))
      (if v (setq out (cons (atof v) out)))))
  (reverse out))

;; Punto de un nentsel llevado a WCS con su matriz (entidades anidadas en
;; un bloque o XREF). Sin matriz, la entidad ya esta en WCS.
(defun urb:nentsel-to-wcs (pt mat)
  (if (and mat (= (length mat) 4))
    (mapcar '+
      (mapcar '(lambda (c) (* (car pt) c)) (nth 0 mat))
      (mapcar '(lambda (c) (* (cadr pt) c)) (nth 1 mat))
      (mapcar '(lambda (c) (* (if (caddr pt) (caddr pt) 0.0) c)) (nth 2 mat))
      (nth 3 mat))
    pt))

(defun urb:nentsel-dir-to-wcs (v mat)
  (if (and mat (= (length mat) 4))
    (mapcar '+
      (mapcar '(lambda (c) (* (car v) c)) (nth 0 mat))
      (mapcar '(lambda (c) (* (cadr v) c)) (nth 1 mat))
      (mapcar '(lambda (c) (* (if (caddr v) (caddr v) 0.0) c)) (nth 2 mat)))
    v))

;; Indice 0..n-1 del renglon clickeado (0 = el de arriba). Se mide sobre
;; el eje "hacia abajo" DEL PROPIO TEXTO (sirve rotado) desde el centro del
;; bloque de texto; el centro de la caja de un rectangulo rotado es el
;; centro del rectangulo, asi que no depende del punto de insercion ni de
;; la justificacion. Solo para TEXT/MTEXT; para otras etiquetas devuelve
;; nil y el llamador pregunta en vez de adivinar.
(defun urb:picked-line-index (selected obj n / name mat pick lo hi res ctr rot
                              up upw ctrw len d h pitch idx sp)
  (setq name (vl-catch-all-apply 'vla-get-ObjectName (list obj)))
  (if (not (member name '("AcDbText" "AcDbMText")))
    nil
    (progn
      (setq mat (caddr selected)
            pick (trans (cadr selected) 1 0))
      (setq res
        (vl-catch-all-apply
          '(lambda () (vla-GetBoundingBox obj 'lo 'hi)
             (list (vlax-safearray->list lo) (vlax-safearray->list hi)))))
      (setq rot (vl-catch-all-apply 'vla-get-Rotation (list obj)))
      (if (or (vl-catch-all-error-p res) (not (numberp rot)))
        nil
        (progn
          (setq ctr (mapcar '(lambda (a b) (* 0.5 (+ a b))) (car res) (cadr res)))
          (setq up (list (- (sin rot)) (cos rot) 0.0))
          (setq ctrw (urb:nentsel-to-wcs ctr mat)
                upw (urb:nentsel-dir-to-wcs up mat))
          (setq len (distance '(0.0 0.0 0.0) upw))
          (if (< len 1e-9)
            nil
            (progn
              ;; d > 0 = el clic cae POR DEBAJO del centro del texto
              (setq d (- (+ (* (- (car pick) (car ctrw)) (/ (car upw) len))
                            (* (- (cadr pick) (cadr ctrw)) (/ (cadr upw) len)))))
              (if (= n 2)
                (if (< d 0.0) 0 1)
                (progn
                  (setq h (vl-catch-all-apply 'vla-get-Height (list obj)))
                  (setq sp (if (= name "AcDbMText")
                             (vl-catch-all-apply 'vla-get-LineSpacingFactor (list obj))
                             1.0))
                  (if (or (not (numberp h)) (not (numberp sp)))
                    nil
                    (progn
                      (setq pitch (* h len 1.6667 sp))
                      (setq idx (fix (/ (+ d (* 0.5 n pitch)) pitch)))
                      (max 0 (min (1- n) idx)))))))))))))

;; Si no se pudo saber por geometria, se pregunta: nunca se elige en
;; silencio una cota que el usuario no clickeo.
(defun urb:ask-which-cota (nums / i s keys kw)
  (setq s "" keys "" i 1)
  (foreach v nums
    (setq s (strcat s "  " (itoa i) "=" (rtos v 2 3))
          keys (strcat keys (if (> i 1) " " "") (itoa i)))
    (setq i (1+ i)))
  (initget keys)
  (setq kw (getkword
    (strcat "\nLa etiqueta trae " (itoa (length nums)) " cotas:" s
            ". Cual es la que quiere? [" (vl-string-translate " " "/" keys)
            "] <1>: ")))
  (nth (1- (if kw (atoi kw) 1)) nums))

(defun urb:selected-cota-number (selected / ename edata obj txt nums idx)
  ;; Lee TEXT/MTEXT, etiquetas Civil y proxies seleccionados con NENTSEL,
  ;; incluidos los que viven dentro de un XREF. Se prueban tanto ActiveX
  ;; como DXF porque cada tipo de etiqueta expone el contenido distinto.
  ;; Una etiqueta numerica anidada en una VIA sin rasante no es una cota
  ;; alternativa: leerla inventaria la rasante de esa via.
  (setq ename (if (and selected (null (urb:pick-road-name selected)))
                (car selected) nil)
        edata (if ename (entget ename) nil)
        obj
          (if ename
            (vl-catch-all-apply 'vlax-ename->vla-object (list ename))))
  (if (vl-catch-all-error-p obj) (setq obj nil))
  (if obj
    (progn
      (setq txt (vl-catch-all-apply 'vla-get-TextString (list obj)))
      (if (vl-catch-all-error-p txt) (setq txt nil))))
  (if (or (null txt) (= (urb:safe-string txt "") ""))
    (setq txt (cdr (assoc 1 edata))))
  (setq nums (if txt (urb:text-line-numbers txt)))
  (cond
    ((null nums) nil)
    ((= (length nums) 1) (car nums))
    (T
      (setq idx (if obj (vl-catch-all-apply 'urb:picked-line-index
                          (list selected obj (length nums)))))
      (if (or (null idx) (vl-catch-all-error-p idx))
        (urb:ask-which-cota nums)
        (progn
          (prompt (strcat "\nLa etiqueta trae " (itoa (length nums))
            " cotas; se toma la del renglon clickeado."))
          (nth idx nums)))))
)

(defun urb:road-design-grade-records (road data / mov records span c0 c1)
  ;; La rasante de diseno se puede consultar aunque no exista superficie
  ;; TN y, por tanto, aun no se haya calculado movimiento de tierras.
  (setq mov (urb:road-movement-data road))
  (setq records (urb:road-ldata-stored road "URB_VIA_RASANTE_FULL"))
  (if (not (urb:grade-records-valid-p records)) (setq records nil))
  (if (and (null records) mov (> (length mov) 9))
    (setq records (urb:read-lisp-safe (nth 9 mov))))
  (if (not (urb:grade-records-valid-p records)) (setq records nil))
  (if (and (null records) (> (length data) 32))
    (setq records (urb:read-lisp-safe (nth 32 data))))
  (if (not (urb:grade-records-valid-p records)) (setq records nil))
  (setq span
    (atof (urb:safe-string (if (> (length data) 18) (nth 18 data) nil) "0")))
  (if (null records)
    (progn
      ;; or de AutoLISP devuelve T, no el valor -- cadena if explicita
      (setq c0
        (urb:parse-real
          (if (and mov (> (length mov) 7)) (nth 7 mov) "")))
      (if (null c0)
        (setq c0
          (urb:parse-real
            (if (> (length data) 30) (nth 30 data) ""))))
      (setq c1
        (urb:parse-real
          (if (and mov (> (length mov) 8)) (nth 8 mov) "")))
      (if (null c1)
        (setq c1
          (urb:parse-real
            (if (> (length data) 31) (nth 31 data) ""))))
      (if (and c0 c1 (> span 1e-6))
        (setq records (list (list 0.0 c0) (list span c1))))))
  records
)

(defun urb:cota-start-from-via (ename / road data records)
  ;; Para la PRIMERA cota del metodo Pendiente importa el inicio del tramo
  ;; de via, no el lugar accidental donde se hizo clic sobre su bloque.
  (setq road (urb:road-parent-from-entity ename))
  (if (and road (setq data (urb:get-xdata-strings road "URB_VIA")))
    (progn
      (setq records (urb:road-design-grade-records road data))
      (if records (urb:cota-at-axis-distance 0.0 records) nil))
    nil)
)

(defun urb:cota-start-from-pick (selected / cands item value attempt)
  (setq cands (list (car selected)))
  (if (> (length selected) 3)
    (setq cands (append cands (nth 3 selected))))
  (foreach item cands
    (if (null value)
      (progn
        (setq attempt
          (vl-catch-all-apply 'urb:cota-start-from-via (list item)))
        (if (not (vl-catch-all-error-p attempt))
          (setq value attempt)))))
  value
)

;; Si lo seleccionado pertenece a una VIA ya creada por el plugin,
;; devuelve la cota de RASANTE de esa via en el punto del click
;; (proyectado a su eje, con los records de rasante guardados); nil si no
;; es una via o no tiene rasante calculada. (2026-08-12: para que el
;; picker de cotas reconozca automaticamente texto O via, sin preguntar.)
(defun urb:cota-from-via (ename point / road data mov records via-id
   axis-handle axis span axis-start direction c0 c1 closest d station)
  (setq road (urb:road-parent-from-entity ename))
  (if (and road (setq data (urb:get-xdata-strings road "URB_VIA")))
    (progn
      (setq mov (urb:road-movement-data road))
      (setq records (urb:road-design-grade-records road data))
      (setq via-id (if (> (length data) 22) (nth 22 data) ""))
      ;; Si el handle del eje ya no existe, se busca por via-id/cache.
      ;; Nunca se fabrica un alineamiento nuevo al consultar una cota.
      (setq axis (urb:road-axis-recover road data via-id))
      (setq span
        (atof (urb:safe-string (if (> (length data) 18) (nth 18 data) nil) "0")))
      (setq axis-start
        (atof (urb:safe-string (if (> (length data) 21) (nth 21 data) nil) "0")))
      (setq direction
        (urb:safe-string (if (> (length data) 12) (nth 12 data) nil) "Inicio"))
      (if (and axis records)
        (progn
          (setq closest
            (vl-catch-all-apply 'vlax-curve-getClosestPointTo (list axis point)))
          (if (vl-catch-all-error-p closest)
            nil
            (progn
              (setq d
                (vl-catch-all-apply 'vlax-curve-getDistAtPoint (list axis closest)))
              (if (vl-catch-all-error-p d)
                nil
                (progn
                  ;; records de rasante en coordenada LOCAL (0..span)
                  (setq station
                    (if (urb:string-equal-p direction "Final")
                      (- (+ axis-start span) d)
                      (- d axis-start)))
                  (urb:cota-at-axis-distance station records))))))
        (progn
          ;; se reconocio una via del programa pero no se puede dar cota:
          ;; explicar POR QUE en vez de fallar en silencio (reporte del
          ;; usuario: "no puede leer la cota cuando selecciono la via")
          (if (null records)
            (prompt
              (strcat "\nLa via "
                (urb:safe-string (nth 1 data) "seleccionada")
                " no tiene rasante guardada; no se puede tomar su cota."
                " Use EDITAR y asignele cotas con pendiente, o seleccione"
                " otra via/texto de cota.")))
          (if (and records (null axis))
            (prompt
              (strcat "\nLa via "
                (urb:safe-string (nth 1 data) "seleccionada")
                " tiene rasante, pero no se recupero su eje."
                " Use EDITAR para volver a vincularlo.")))
          nil)))
    nil))

;; Modo "Pendiente" generalizado a N cotas (2026-08-11, pedido del
;; usuario: pozos sobre la via). Devuelve una lista de (valor punto) --
;; con 2 cotas la rasante es lineal inicial/final (como antes); con 3 o
;; mas, cada cota se proyecta sobre el eje en el punto donde se clickeo
;; su etiqueta y la rasante queda por tramos. Enter tras 2 o mas cotas
;; termina; Enter antes de 2 cancela.
;; Localiza un eje YA existente por el identificador estable de la via.
;; Desde 4.21.2 URB_VIA_EJE guarda (handle-contorno via-id); el segundo
;; valor permite recuperar el mismo eje aunque el bloque de via cambie de
;; handle al editarse o el DWG se vuelva a abrir.
(defun urb:find-linked-road-axis (via-id / selection index candidate link axis)
  (setq via-id (urb:safe-string via-id ""))
  (if (/= via-id "")
    (setq selection (ssget "_X" '((-3 ("URB_VIA_EJE"))))))
  (setq index 0)
  (if selection
    (repeat (sslength selection)
      (setq candidate (ssname selection index)
            link (urb:get-xdata-strings candidate "URB_VIA_EJE"))
      (if (and (null axis)
               (> (length link) 1)
               (urb:string-equal-p (nth 1 link) via-id)
               (urb:curve-entity-p candidate))
        (setq axis candidate))
      (setq index (1+ index))))
  axis
)

(defun urb:remember-road-axis
  (road data via-id axis / axis-handle road-handle updated)
  ;; Registra una seleccion manual para que las siguientes operaciones de
  ;; ese anden/via no vuelvan a preguntar. En ejes de xref la escritura de
  ;; xdata puede no estar permitida; la cache de sesion sigue funcionando.
  (setq via-id (urb:safe-string via-id ""))
  (if (and axis (/= via-id ""))
    (urb:cache-road-axis via-id axis))
  (setq axis-handle
    (if axis
      (vl-catch-all-apply
        '(lambda () (vla-get-Handle (vlax-ename->vla-object axis))))
      nil))
  (if (vl-catch-all-error-p axis-handle) (setq axis-handle nil))
  (setq road-handle
    (if road
      (vl-catch-all-apply
        '(lambda () (vla-get-Handle (vlax-ename->vla-object road))))
      nil))
  (if (vl-catch-all-error-p road-handle) (setq road-handle ""))
  (if (and axis axis-handle (/= via-id ""))
    (vl-catch-all-apply
      'urb:set-xdata-strings
      (list axis "URB_VIA_EJE"
        (list (urb:safe-string road-handle "") via-id))))
  (if (and road data axis-handle)
    (progn
      (setq updated (urb:list-set-extended data 5 axis-handle))
      (vl-catch-all-apply
        'urb:set-xdata-strings (list road "URB_VIA" updated))))
  axis
)

(defun urb:find-axis-in-road-block
  (road via-id / obj blocks bdef result fallback item candidate link)
  (setq obj (vl-catch-all-apply 'vlax-ename->vla-object (list road)))
  (if (and (not (vl-catch-all-error-p obj))
           (= (vla-get-ObjectName obj) "AcDbBlockReference"))
    (progn
      (setq blocks (vla-get-Blocks (urb:doc))
            bdef
              (vl-catch-all-apply 'vla-Item
                (list blocks (vla-get-EffectiveName obj))))
      (if (not (vl-catch-all-error-p bdef))
        (vlax-for item bdef
          (setq candidate
            (vl-catch-all-apply 'vlax-vla-object->ename (list item)))
          (if (and (not (vl-catch-all-error-p candidate))
                   (urb:curve-entity-p candidate))
            (progn
              (setq link
                (urb:get-xdata-strings candidate "URB_VIA_EJE"))
              ;; La copia grafica del eje dentro del bloque lleva el rol
              ;; EJE_DENTRO_BLOQUE. Se acepta como respaldo aunque una via
              ;; antigua haya perdido o cambiado su via-id.
              (if (and link
                       (or (member "EJE_DENTRO_BLOQUE" link)
                           (> (length link) 1)))
                (if (null fallback) (setq fallback candidate)))
              (if (and link (> (length link) 1)
                       (urb:string-equal-p (nth 1 link) via-id))
                (setq result candidate))))))))
  (if result result fallback))

;; Resuelve el EJE de una via YA CREADA sin fabricar geometria nueva:
;; 1) handle guardado, 2) cache de sesion, 3) xdata URB_VIA_EJE/via-id.
;; Si los tres fallan, el flujo superior pide seleccionar el eje existente
;; y lo recuerda. Se retiro deliberadamente la reconstruccion desde el
;; contorno, que era la responsable de crear un alineamiento duplicado.
(defun urb:road-axis-recover (road data via-id / axis axis-handle cache-key)
  (setq axis-handle
    (if (> (length data) 5) (urb:safe-string (nth 5 data) "") ""))
  (setq via-id (urb:safe-string via-id ""))
  (setq cache-key
    (if (/= via-id "")
      via-id
      (vl-catch-all-apply
        '(lambda () (vla-get-Handle (vlax-ename->vla-object road))))))
  (if (vl-catch-all-error-p cache-key) (setq cache-key nil))
  ;; 2026-08-13: cada candidato se valida POR SEPARADO y en CADENA DE
  ;; IF, no con or -- el or de AutoLISP devuelve T, NO el valor (probado
  ;; empiricamente: (or nil "abc") -> T), asi que un or "selector de
  ;; valores" entregaba el simbolo T como eje. Ademas handent de un
  ;; handle BORRADO devuelve el ename muerto (no nil), por eso cada
  ;; candidato pasa por urb:usable-axis-or-nil. Cazado por la autoprueba
  ;; de verify_lib con el eje borrado a proposito.
  (setq axis
    (urb:usable-axis-or-nil
      (if (/= axis-handle "") (handent axis-handle) nil)))
  (if (null axis)
    (setq axis
      (urb:usable-axis-or-nil
        (if cache-key (urb:cached-road-axis cache-key) nil))))
  (if (null axis)
    (setq axis (urb:usable-axis-or-nil (urb:find-linked-road-axis via-id))))
  (if (null axis)
    (setq axis
      (urb:usable-axis-or-nil (urb:find-axis-in-road-block road via-id))))
  (if (and axis cache-key) (urb:cache-road-axis cache-key axis))
  axis)

(defun urb:usable-axis-or-nil (e)
  (if (and e (urb:curve-entity-p e)) e nil))

;; Prueba la entidad clickeada Y sus bloques contenedores: cuando el clic
;; cae dentro de un bloque o xref, nentsel devuelve la geometria ANIDADA
;; como (car sel) y los INSERT contenedores en el 4to elemento. Las vias
;; empacadas llevan la xdata URB_VIA en el INSERT -- por eso el picker no
;; reconocia una via ya creada al clickearla (reporte 2026-08-12).
(defun urb:cota-from-pick (sel / value cands item)
  (setq cands (list (car sel)))
  (if (> (length sel) 3)
    (setq cands (append cands (nth 3 sel))))
  (foreach item cands
    (if (and (null value) item)
      (progn
        (setq value
          (vl-catch-all-apply 'urb:cota-from-via (list item (cadr sel))))
        (if (vl-catch-all-error-p value) (setq value nil)))))
  value)

;; 2026-09-02 (pedido del usuario: "que pasa si inicialmente tengo un
;; pozo... o dos pozos a la mitad de la via"): el MISMO clic tambien
;; reconoce un POZO/CAJA/ELEMENTO del MODELO (bloques MP_PUNTO_*) y toma
;; su cota de rasante: COTA_TAPA si existe (cajas electricas), si no la
;; COTA_TN_INI (pozos hidro, terreno rasante en la tapa). Con esto el
;; orden es libre (via->pozo, pozo->via, pozo->pozo, solo pozos
;; intermedios) y la rasante extrapola con la pendiente de borde.
(defun urb:cota-from-model-punto (sel / cands item ed obj bname atts v out)
  (setq cands (list (car sel)))
  (if (> (length sel) 3) (setq cands (append cands (nth 3 sel))))
  (foreach item cands
    (if (and (null out) item (setq ed (entget item))
             (= (cdr (assoc 0 ed)) "INSERT"))
      (progn
        (setq obj (vl-catch-all-apply 'vlax-ename->vla-object (list item)))
        (setq bname
          (if (vl-catch-all-error-p obj) ""
            (vl-catch-all-apply 'vla-get-EffectiveName (list obj))))
        (if (vl-catch-all-error-p bname) (setq bname ""))
        (if (wcmatch (strcase (mp:safe-str bname)) "MP_PUNTO_*,MP_TRAMO_*")
          (progn
            (setq atts (mp:att-alist item))
            (setq v (mp:numeric-real (mp:getval "COTA_TAPA" atts "")))
            (if (null v)
              (setq v (mp:numeric-real (mp:getval "COTA_TN_INI" atts ""))))
            (if (null v)
              (setq v (mp:numeric-real (mp:getval "COTA_RASANTE" atts ""))))
            (if v (setq out v)))))))
  out)

(defun urb:pick-road-cotas (/)
  (urb:pick-road-cotas-loop nil))

;; Bucle interno reutilizable (2026-08-12): seed-picks permite arrancar
;; con la primera cota ya capturada -- lo usa "Textos por capa" cuando el
;; primer clic resulta ser una VIA creada o una etiqueta con numero
;; (auto-detect) y el flujo continua pidiendo la cota final y las
;; intermedias, igual que el modo Pendiente.
;; 2026-09-10 (reporte del usuario: "me esta limitando mucho a seleccionar
;; via al principio y via al final... puede que tenga via al principio pero
;; que pasa si no tengo via al final, o si no tengo ni al principio ni al
;; final"). El picker SIEMPRE acepto cualquier fuente -- via creada, pozo
;; del modelo, etiqueta con numero o valor digitado --, pero lo decia mal:
;; hablaba de "la COTA del extremo INICIAL/FINAL de la via" y exigia DOS
;; referencias, asi que sin una segunda no se podia seguir. Ahora los
;; mensajes nombran las cuatro fuentes y, con UNA sola cota, se pide la
;; PENDIENTE y con eso se arma la rasante (el mismo camino de "cota inicial
;; + pendiente" que el motor ya sabia usar).
;; 5.7.2 FUENTE de cada cota (pedido del usuario: "mi pozo esta en el
;; circulo naranja pero mi cota esta en la parte verde... la localizacion
;; de esa cota queda donde esta la elevacion que senalo?"). Antes SI: la
;; cota se ubicaba en el punto del CLIC sobre el texto, que puede estar a
;; varios metros del pozo. Ahora:
;;  - clic sobre un POZO del modelo: la cota va en el CENTRO del pozo;
;;  - clic sobre una ETIQUETA: se busca un pozo del modelo a <= 25 m con
;;    una cota igual (+-0,006); si aparece, la cota va en ese pozo; si no,
;;    se pide el punto al que pertenece (Enter = donde esta el texto).
;; Cada pick queda (valor punto tipo nombre) y la lista cruda se guarda en
;; *urb-road-picks-raw* para que el PERFIL dibuje pozos y cotas de via.
(defun urb:pick-model-punto-info (sel / cands item ed obj bname atts v out id)
  (setq cands (list (car sel)))
  (if (> (length sel) 3) (setq cands (append cands (nth 3 sel))))
  (foreach item cands
    (if (and (null out) item (setq ed (entget item))
             (= (cdr (assoc 0 ed)) "INSERT"))
      (progn
        (setq obj (vl-catch-all-apply 'vlax-ename->vla-object (list item)))
        (setq bname (if (vl-catch-all-error-p obj) ""
                      (vl-catch-all-apply 'vla-get-EffectiveName (list obj))))
        (if (vl-catch-all-error-p bname) (setq bname ""))
        (if (wcmatch (strcase (mp:safe-str bname)) "MP_PUNTO_*")
          (progn
            (setq atts (mp:att-alist item)
                  id (mp:getval "ID" atts (mp:getval "CODIGO" atts "")))
            (setq v (mp:numeric-real (mp:getval "COTA_TAPA" atts "")))
            (if (null v) (setq v (mp:numeric-real (mp:getval "COTA_TN_INI" atts ""))))
            (if (null v) (setq v (mp:numeric-real (mp:getval "COTA_RASANTE" atts ""))))
            (if v (setq out (list v (cdr (assoc 10 ed)) id))))))))
  out)

;; pozo del modelo cerca de una etiqueta cuyo valor coincide con alguna de
;; sus cotas: devuelve (punto id) o nil
(defun urb:pozo-for-cota-label (value point / r ss i e obj bname atts best bestd d id)
  (setq r 25.0
        ss (ssget "_X"
             (list '(0 . "INSERT")
                   '(-4 . ">,>,*") (list 10 (- (car point) r) (- (cadr point) r) 0.0)
                   '(-4 . "<,<,*") (list 10 (+ (car point) r) (+ (cadr point) r) 0.0)))
        i 0)
  (if ss
    (repeat (sslength ss)
      (setq e (ssname ss i) i (1+ i)
            obj (vlax-ename->vla-object e)
            bname (vl-catch-all-apply 'vla-get-EffectiveName (list obj)))
      (if (and (not (vl-catch-all-error-p bname))
               (wcmatch (strcase bname) "MP_PUNTO_*"))
        (progn
          (setq atts (mp:att-alist e))
          (if (vl-some
                '(lambda (a)
                   (and (wcmatch (strcase (car a)) "COTA*")
                        (mp:numeric-real (cdr a))
                        (equal (mp:numeric-real (cdr a)) value 0.006)))
                atts)
            (progn
              (setq d (distance (list (car point) (cadr point))
                                (list (car (cdr (assoc 10 (entget e))))
                                      (cadr (cdr (assoc 10 (entget e)))))))
              (if (or (null bestd) (< d bestd))
                (setq bestd d
                      best (list (cdr (assoc 10 (entget e)))
                                 (mp:getval "ID" atts (mp:getval "CODIGO" atts "")))))))))))
  best)

(defun urb:pick-road-name (sel / cands item road data out)
  (setq cands (list (car sel)))
  (if (> (length sel) 3) (setq cands (append cands (nth 3 sel))))
  (foreach item cands
    (if (and (null out) item)
      (progn
        (setq road (vl-catch-all-apply 'urb:road-parent-from-entity (list item)))
        (if (and road (not (vl-catch-all-error-p road))
                 (setq data (urb:get-xdata-strings road "URB_VIA")))
          (setq out (urb:safe-string (nth 1 data) "VIA"))))))
  out)

(defun urb:pick-road-cotas-loop (picks / sel obj txt value point msg n done slope
                                 kind label info pz)
  (setq done nil)
  (setq *urb-road-picked-slope* nil
        *urb-road-picks-raw* nil
        *urb-road-picked-sources* nil)
  (while (not done)
    (setq n (length picks))
    (setq msg
      (cond
        ((= n 0)
          (strcat "\nPrimera cota de referencia -- clic sobre una VIA creada,"
                  " un POZO, una etiqueta de cota, o Enter para digitarla: "))
        ((= n 1)
          (strcat "\nSegunda cota (el otro extremo, misma libertad de fuente)"
                  " o Enter para seguir con una PENDIENTE: "))
        (T "\nOtra cota sobre la via (pozos, quiebres) o Enter para terminar: ")))
    (setq sel (nentsel msg))
    (cond
      ((null sel)
        (cond
          ((>= n 2) (setq done T))
          ;; una sola referencia: se completa con la pendiente
          ((= n 1)
            (setq slope
              (getreal "\nPendiente de la via en % (Enter cancela): "))
            (if slope
              (progn
                (setq *urb-road-picked-slope* slope)
                (prompt
                  (strcat "\nRasante desde la cota seleccionada con pendiente "
                    (rtos slope 2 3) " %."))
                (setq done T))
              (progn
                (prompt "\nSin segunda cota ni pendiente; seleccion cancelada.")
                (setq done T picks nil))))
          ;; ninguna referencia: se digita la cota y la pendiente
          (T
            (setq value (getreal "\nCota inicial (msnm), Enter cancela: "))
            (if value
              (progn
                (setq slope
                  (getreal "\nPendiente de la via en % <0>: "))
                (setq *urb-road-picked-slope* (if slope slope 0.0))
                (setq picks (list (list value nil "DIGITADA" "")))
                (prompt
                  (strcat "\nRasante digitada: " (rtos value 2 3)
                    " msnm con pendiente "
                    (rtos *urb-road-picked-slope* 2 3) " %."))
                (setq done T))
              (progn
                (prompt "\nSeleccion cancelada.")
                (setq done T picks nil))))))
      (T
        ;; AUTO-DETECCION: el mismo click reconoce una VIA creada o un
        ;; TEXTO/etiqueta de cota de cualquier XREF. Se prueba primero la
        ;; via para que un atributo numerico anidado en su bloque no se
        ;; confunda con la cota de rasante.
        ;; La primera cota tambien se toma EN EL PUNTO DEL CLIC. Antes se
        ;; forzaba la abscisa local 0+000 de la via fuente; por eso una
        ;; conexion cerca de 0+210 heredaba 2560.96 en vez de interpolar
        ;; aproximadamente 2556.89 entre las cotas vecinas.
        (setq point (cadr sel) kind nil label "")
        (setq value (urb:cota-from-pick sel))
        (if value
          (progn
            (setq kind "VIA" label (urb:safe-string (urb:pick-road-name sel) "VIA"))
            (prompt
              (strcat
                "\nCota interpolada de la RASANTE en el punto seleccionado: "
                (rtos value 2 3))))
          (progn
            ;; pozo/caja del modelo: cota de tapa/rasante del bloque, y la
            ;; cota se ubica en el CENTRO del pozo, no donde cayo el clic
            (setq info (urb:pick-model-punto-info sel))
            (if info
              (progn
                (setq value (car info) point (cadr info)
                      kind "POZO" label (urb:safe-string (caddr info) ""))
                (prompt
                  (strcat "\nCota tomada del POZO " label " del modelo: "
                    (rtos value 2 3) " (ubicada en el centro del pozo)")))
              (progn
                (setq value (urb:selected-cota-number sel))
                (if value
                  (progn
                    (prompt
                      (strcat "\nCota leida de la etiqueta: " (rtos value 2 3)))
                    (setq pz (urb:pozo-for-cota-label value point))
                    (if pz
                      (progn
                        (setq point (car pz) kind "POZO"
                              label (urb:safe-string (cadr pz) ""))
                        (prompt (strcat " -> pertenece al POZO " label
                                        "; se ubica en el centro del pozo.")))
                      (progn
                        (setq kind "TEXTO")
                        (setq pz (getpoint
                                   (strcat "\nClic en el POZO o punto al que pertenece esa cota"
                                           " <Enter = donde esta el texto>: ")))
                        (if pz (setq point pz))))))))))
        (if (null value)
          (progn
            (setq value
              (getreal "\nNo se pudo leer la cota; digitela (Enter omite): "))
            (setq kind "DIGITADA" label "")))
        (if value
          (setq picks (append picks (list (list value point kind label))))))))
  (setq *urb-road-picks-raw* picks)
  picks)

;; 2026-09-01 (pedido del usuario: "que pasa si no tengo una via cerca o
;; no he dibujado ninguna... que sea muy intuitivo"): picker de cotas de
;; DISENO para el corte/relleno de poligonos (zona verde, sendero,
;; rampa). Cada cota puede venir de: clic sobre una VIA creada, un POZO
;; del modelo, una ETIQUETA de cota (texto de cualquier xref) o
;; DIGITADA (opcion Digitar: numero + punto donde aplica). Sin vias ni
;; pozos, se digita y ya. Con UNA sola cota el plano de diseno queda
;; horizontal; con 2 es una rasante lineal; con 3+ un plano ajustado.
(defun urb:pick-design-cotas (/ picks sel value point done n alto ref)
  (setq done nil picks nil *urb-anden-pts-cache* nil)
  (while (not done)
    (setq n (length picks) ref nil)
    (initget "Digitar Terminar")
    (setq sel
      (nentsel
        (strcat "\nCota de diseno " (itoa (1+ n))
          ": clic sobre VIA/ANDEN/POZO/etiqueta, [Digitar] la cota, o Enter para terminar"
          (if (> n 0) (strcat " (" (itoa n) " tomadas)") "") ": ")))
    (cond
      ((null sel)
        (if (>= n 1)
          (setq done T)
          (progn
            (prompt "\nSe necesita al menos 1 cota (o cancele con Esc).")
            (setq done T picks nil))))
      ((and (= (type sel) 'STR) (= sel "Terminar")) (setq done T))
      ((and (= (type sel) 'STR) (= sel "Digitar"))
        (setq value (getreal "\nCota de diseno (msnm): "))
        (if value
          (progn
            (setq point
              (getpoint (strcat "\nPunto donde aplica esa cota"
                (if (= n 0) " (Enter = toda la zona plana)" "") ": ")))
            (cond
              (point
                (setq picks (append picks (list (list value point)))))
              ((= n 0)
                ;; sin punto y es la unica: plano horizontal, el punto da igual
                (setq picks (list (list value (list 0.0 0.0)))))
              (T
                (prompt "\nSin punto la cota no se puede ubicar; se omite."))))))
      (T
        ;; misma cascada del modo Pendiente: via -> pozo del modelo ->
        ;; etiqueta con numero -> digitar de respaldo
        ;; 5.6.2: clic sobre un ANDEN creado -> su superficie de DISENO
        ;; (la cota de cada punto sale del borde del anden mas cercano)
        (setq ref (vl-catch-all-apply 'urb:anden-reference-from-pick (list sel)))
        (if (vl-catch-all-error-p ref) (setq ref nil))
        (if ref
          (progn
            (setq value (urb:anden-reference-design-z ref (car (cadr sel)) (cadr (cadr sel))))
            (urb:anden-ref-curves-clear)
            (if value
              (prompt (strcat "\nAnden creado: se usan sus cotas de DISENO en el borde mas cercano"
                " (en el clic: " (rtos value 2 3) "). Enter para terminar."))
              (setq ref nil)))
          (progn
        (setq value (urb:cota-from-pick sel))
        (if value
          ;; 2026-09-10 (pedido del usuario): estas son cotas de DISENO de
          ;; anden / zona verde. Si la referencia es una VIA, la cota NO es
          ;; su rasante: el anden va POR ENCIMA de la calzada, la altura
          ;; del bordillo/sardinel. Esa altura sale de Ajustes
          ;; (urb:prefab-default-alto), no se pregunta.
          (progn
            (setq alto (urb:prefab-default-alto "Bordillo"))
            (setq value (+ value alto))
            ;; 5.6.1 (reporte del usuario: "me esta reconociendo solo una
            ;; cota"): el clic sobre una VIA ya no aporta un punto suelto --
            ;; aporta su RASANTE COMPLETA. La cota de diseno de cada punto
            ;; sale de la estacion de la via frente a el (+ bordillo).
            (setq ref (vl-catch-all-apply 'urb:road-reference-from-pick (list sel)))
            (if (vl-catch-all-error-p ref) (setq ref nil))
            (if ref
              (prompt (strcat "\nVia creada: se usa su rasante en TODO el alineamiento"
                " + " (rtos alto 2 2) " m de bordillo (en el clic: "
                (rtos value 2 3) "). Enter para terminar."))
              (prompt (strcat "\nRasante de la via en el clic + " (rtos alto 2 2)
                " m de bordillo -> cota de diseno " (rtos value 2 3)))))
          (progn
            (setq value (urb:cota-from-model-punto sel))
            (if value
              (prompt (strcat "\nCota tomada del POZO/ELEMENTO del modelo: "
                (rtos value 2 3)))
              (progn
                (setq value (urb:selected-cota-number sel))
                (if value
                  (prompt (strcat "\nCota leida de la etiqueta: "
                    (rtos value 2 3))))))))))
        (if (null value)
          (setq value
            (getreal "\nNo se pudo leer la cota; digitela (Enter omite): ")))
        (if value
          (setq picks (append picks
                        (list (if ref (list value (cadr sel) ref)
                                      (list value (cadr sel))))))))))
  picks)

;; ---------- 5.6.2 cotas de DISENO de un ANDEN como referencia ----------
;; Pedido del usuario: "que pasa si para el movimiento de tierras de los
;; senderos tengo una via lejos o un pozo, no podria sacarla con respecto a
;; los puntos de elevacion de los andenes? por eso es importante que los
;; andenes queden bien las cotas". El anden ya tiene su superficie de
;; diseno completa (rasante de SU via + bombeo al borde + bordillo +
;; pendiente transversal, urb:anden-grade-at-point). Un sendero o una zona
;; que llega al anden se amarra a la cota de diseno del BORDE del anden en
;; el punto mas cercano. Referencia: (ANDEN ref-via borde contorno).
(defun urb:anden-design-reference (ab / pts road ref edge)
  (setq pts (urb:anden-points-cached ab))
  (if pts
    (progn
      (setq road (urb:anden-road-autodetect pts))
      (if road (setq ref (urb:anden-road-grade-for road)))
      (if ref
        (progn
          (setq edge (urb:anden-axis-edge-offset pts (car ref)))
          (if (numberp edge) (list 'ANDEN ref edge pts)))))))

;; punto mas cercano sobre un contorno CERRADO dado por sus vertices.
;; Recorre la lista UNA vez (nth dentro del ciclo la volvia cuadratica y se
;; llama por cada muestra de la malla: 17+ min en un anden de 251 vertices)
(defun urb:closest-point-on-closed-pts (p pts / px py rest ax ay bx by dx dy len2 tt qx qy d best bd)
  (setq px (car p) py (cadr p) rest (append pts (list (car pts))))
  (while (cdr rest)
    (setq ax (car (car rest)) ay (cadr (car rest))
          bx (car (cadr rest)) by (cadr (cadr rest))
          dx (- bx ax) dy (- by ay) len2 (+ (* dx dx) (* dy dy)))
    (if (> len2 1e-18)
      (progn
        (setq tt (/ (+ (* (- px ax) dx) (* (- py ay) dy)) len2)
              tt (max 0.0 (min 1.0 tt))
              qx (+ ax (* tt dx)) qy (+ ay (* tt dy))
              d (+ (* (- px qx) (- px qx)) (* (- py qy) (- py qy))))
        (if (or (null bd) (< d bd)) (setq bd d best (list qx qy)))))
    (setq rest (cdr rest)))
  best)

;; contorno del anden como polilinea TEMPORAL (una por calculo): la busqueda
;; nativa vlax-curve es cientos de veces mas rapida que recorrer los
;; vertices en LISP por cada muestra. Se borran en urb:anden-ref-curves-clear.
(setq *urb-anden-ref-curves* nil)
;; la lista de puntos es la llave por IDENTIDAD (eq): comparar con equal
;; 1272 vertices por cada muestra seria otra vez lento
(defun urb:pts-temp-curve (pts / hit obj)
  (setq hit (vl-some '(lambda (h) (if (eq (car h) pts) h)) *urb-anden-ref-curves*))
  (if (and hit (not (vlax-erased-p (cdr hit))))
    (cdr hit)
    (progn
      (setq obj (vl-catch-all-apply 'vla-AddLightWeightPolyline
                  (list (vla-get-ModelSpace (urb:doc))
                        (mp:var-dbls (apply 'append (mapcar '(lambda (p) (list (car p) (cadr p))) pts))))))
      (if (vl-catch-all-error-p obj)
        nil
        (progn
          (vla-put-Closed obj :vlax-true)
          (vla-put-Visible obj :vlax-false)
          (setq *urb-anden-ref-curves* (cons (cons pts obj) *urb-anden-ref-curves*))
          obj)))))

(defun urb:anden-ref-curve (aref) (urb:pts-temp-curve (nth 3 aref)))

(defun urb:anden-ref-curves-clear (/ item)
  (foreach item *urb-anden-ref-curves*
    (if (not (vlax-erased-p (cdr item))) (vl-catch-all-apply 'vla-Delete (list (cdr item)))))
  (setq *urb-anden-ref-curves* nil))

;; contorno de tierras de cada anden leido UNA vez por comando: recorrer la
;; definicion del bloque (miles de losetas) costaba 10-50 s por lectura
(setq *urb-anden-pts-cache* nil)
(defun urb:anden-points-cached (ab / key hit pts)
  (setq key (cdr (assoc 5 (entget ab)))
        hit (assoc key *urb-anden-pts-cache*))
  (if hit
    (cdr hit)
    (progn
      (setq pts (vl-catch-all-apply 'urb:anden-earthwork-points (list ab)))
      (if (vl-catch-all-error-p pts) (setq pts nil))
      (setq *urb-anden-pts-cache* (cons (cons key pts) *urb-anden-pts-cache*))
      pts)))

;; cota de diseno en (x y) amarrada al borde del anden mas cercano
(defun urb:anden-reference-design-z (aref x y / q curve)
  (setq curve (urb:anden-ref-curve aref))
  (if curve
    (setq q (vl-catch-all-apply 'vlax-curve-getClosestPointTo (list curve (list x y 0.0))))
    (setq q (urb:closest-point-on-closed-pts (list x y) (nth 3 aref))))
  (if (vl-catch-all-error-p q) (setq q (urb:closest-point-on-closed-pts (list x y) (nth 3 aref))))
  (if q (urb:anden-grade-at-point (list (car q) (cadr q) 0.0) (nth 1 aref) (nth 2 aref))))

;; anden tocado por un clic (nentsel: la entidad o uno de sus contenedores)
(defun urb:anden-reference-from-pick (sel / cands item out)
  (setq cands (list (car sel)))
  (if (> (length sel) 3) (setq cands (append cands (nth 3 sel))))
  (foreach item cands
    (if (and (null out) item
             (not (vl-catch-all-error-p (vl-catch-all-apply 'urb:anden-block-p (list item))))
             (urb:anden-block-p item))
      (setq out (urb:anden-design-reference item))))
  out)

;; anden mas cercano a un contorno (<= 10 m), para senderos sin via al lado
(defun urb:anden-near-points (pts / step k sample best bestd en apts curve q d p
                               xs ys x0 x1 y0 y1 r lo hi)
  (if (> (length pts) 60)
    (setq step (/ (length pts) 60) k 0
          sample (vl-remove-if '(lambda (p) (/= 0 (rem (setq k (1+ k)) step))) pts))
    (setq sample pts))
  (setq bestd 10.0 xs (mapcar 'car pts) ys (mapcar 'cadr pts)
        x0 (- (apply 'min xs) 10.0) x1 (+ (apply 'max xs) 10.0)
        y0 (- (apply 'min ys) 10.0) y1 (+ (apply 'max ys) 10.0))
  (foreach en (urb:all-anden-blocks)
    ;; filtro barato: UNA caja envolvente por anden contra la caja del
    ;; sendero + 10 m (pedirla por cada muestra costaba ~50 s)
    (setq r (vl-catch-all-apply 'vla-GetBoundingBox (list (vlax-ename->vla-object en) 'lo 'hi)))
    (if (and (not (vl-catch-all-error-p r))
             (setq lo (vlax-safearray->list lo) hi (vlax-safearray->list hi))
             (<= (car lo) x1) (>= (car hi) x0) (<= (cadr lo) y1) (>= (cadr hi) y0))
      (progn
        (setq apts (urb:anden-points-cached en)
              curve (if apts (urb:pts-temp-curve apts)))
        (if curve
          (foreach p sample
            (setq q (vl-catch-all-apply 'vlax-curve-getClosestPointTo
                      (list curve (list (car p) (cadr p) 0.0))))
            (if (not (vl-catch-all-error-p q))
              (progn
                (setq d (distance (list (car p) (cadr p)) (list (car q) (cadr q))))
                (if (< d bestd) (setq bestd d best en)))))))))
  best)

;; referencia de rasante de la via creada tocada por un clic (nentsel)
(defun urb:road-reference-from-pick (sel / cands item road out)
  (setq cands (list (car sel)))
  (if (> (length sel) 3) (setq cands (append cands (nth 3 sel))))
  (foreach item cands
    (if (and (null out) item)
      (progn
        (setq road (vl-catch-all-apply 'urb:road-parent-from-entity (list item)))
        (if (and road (not (vl-catch-all-error-p road)))
          (setq out (urb:anden-road-grade-for-safe road))))))
  out)

;; cota de DISENO en (x y) sobre la rasante de una via: estacion del punto
;; proyectado en el eje (misma regla que urb:anden-grade-at-point) + altura
;; de bordillo, igual que el clic suelto sobre la via.
(defun urb:road-reference-design-z (reference x y / axis records axis-start
                                    span direction mode closest raw station z)
  (setq axis (nth 0 reference) records (nth 1 reference)
        axis-start (nth 2 reference) span (nth 3 reference)
        direction (nth 4 reference) mode (nth 5 reference))
  (setq closest (vlax-curve-getClosestPointTo axis (list x y 0.0)))
  (setq raw (vlax-curve-getDistAtPoint axis closest))
  (setq station
    (if (urb:string-equal-p mode "LOCAL")
      (if (urb:string-equal-p direction "Final")
        (- (+ axis-start span) raw)
        (- raw axis-start))
      raw))
  (setq z (urb:cota-at-axis-distance station records))
  (if z (+ z (urb:prefab-default-alto "Bordillo")) nil))

;; Proyecta cada cota seleccionada sobre el eje (en el punto del clic) y
;; devuelve records (distancia-en-el-eje cota) ordenados, listos para
;; urb:cota-at-axis-distance.
(defun urb:picked-cotas-to-stations (picks axis / result item point closest d sources)
  ;; 5.7.2: en paralelo (sin tocar el resultado de 2 elementos que usa el
  ;; movimiento de tierras) se arma la FUENTE de cada cota para el perfil
  (foreach item picks
    (if (and (cadr item) (> (length item) 2))
      (progn
        (setq closest
          (vl-catch-all-apply 'vlax-curve-getClosestPointTo (list axis (cadr item))))
        (if (not (vl-catch-all-error-p closest))
          (progn
            (setq d (vl-catch-all-apply 'vlax-curve-getDistAtPoint (list axis closest)))
            (if (not (vl-catch-all-error-p d))
              (setq sources (cons (list d (car item) (nth 2 item) (nth 3 item)) sources))))))))
  (setq *urb-road-picked-sources* sources)
  (foreach item picks
    (setq point (cadr item))
    (if point
      (progn
        (setq closest
          (vl-catch-all-apply 'vlax-curve-getClosestPointTo (list axis point)))
        (if (not (vl-catch-all-error-p closest))
          (progn
            (setq d
              (vl-catch-all-apply 'vlax-curve-getDistAtPoint (list axis closest)))
            (if (not (vl-catch-all-error-p d))
              (setq result (cons (list d (car item)) result))))))))
  (vl-sort result '(lambda (a b) (< (car a) (car b)))))

(defun urb:picks-have-locations-p (picks / ok item)
  ;; Dos cotas seleccionadas no significan necesariamente inicio/final: pueden
  ;; ser dos pozos intermedios. Solo el ingreso digitado sin punto carece de
  ;; estacion y debe conservar el comportamiento lineal de extremo a extremo.
  (setq ok (and picks (> (length picks) 1)))
  (foreach item picks
    (if (or (null (cadr item))
            (not (numberp (car (cadr item))))
            (not (numberp (cadr (cadr item)))))
      (setq ok nil)))
  ok)

;; 2026-09-12: al EDITAR una via, decide si la capa de cotas ya guardada
;; se puede reusar (T) o si hay que volver a pedirla (nil). Se reusa solo
;; si el metodo sigue siendo "Textos por capa", ya lo era antes y hay una
;; capa guardada. Volver a pedirla siempre era lo que tumbaba la edicion
;; al flujo de PENDIENTE (ver la nota en urb:edit-road).
(defun urb:road-cota-capa-reusable-p (modo-dialogo modo-viejo capa-vieja)
  (if (and (urb:string-equal-p modo-dialogo "Textos por capa")
           (urb:string-equal-p (urb:safe-string modo-viejo "") "Textos por capa")
           (/= (urb:safe-string capa-vieja "") ""))
    T
    nil)
)

(defun urb:road-cota-reference
  (mode / selected ename edata layer texts count obj txt via-cota picks road-name)
  (cond
    ((urb:string-equal-p mode "Textos por capa")
      ;; nentsel (no entsel) para poder tomar un texto anidado en un xref.
      (setq selected
        (nentsel
          (strcat
            "\nSeleccione un texto de cota (cualquier capa/XREF)"
            " o una VIA ya creada como cota inicial: ")))
      ;; nentsel puede devolver un TEXT/MTEXT ANIDADO en la via. El
      ;; contenedor URB_VIA manda sobre el tipo grafico del subobjeto.
      (setq road-name (if selected (urb:pick-road-name selected)))
      (setq via-cota (if road-name (urb:cota-from-pick selected)))
      (while (and selected road-name (null via-cota))
        (prompt (strcat "\n" road-name
          " no tiene rasante guardada. Seleccione otra via o un texto de cota;"
          " para arreglarla use EDITAR y asigne cotas con pendiente."))
        (setq selected
          (nentsel "\nOtra via o texto de cota (Enter cancela): "))
        (setq road-name (if selected (urb:pick-road-name selected)))
        (setq via-cota (if road-name (urb:cota-from-pick selected))))
      (if selected
        (progn
          (setq ename (car selected) edata (entget ename))
          (if (and (null road-name)
                   (member (cdr (assoc 0 edata)) '("TEXT" "MTEXT")))
            (progn
              (setq layer (cdr (assoc 8 edata)))
              ;; urb:collect-cota-texts ya sabe leer capas de xref (no
              ;; se usa ssget aqui: siempre da 0 en contenido anidado).
              (urb:clear-cota-calibration layer)
              (setq texts (urb:collect-cota-texts layer))
              (setq count (length texts))
              ;; El punto donde el usuario hizo clic es la unica coordenada
              ;; WCS fiable para ciertos proxies de etiquetas Civil 3D.
              ;; Se usa para calibrar el desfase de toda la capa/XREF.
              (urb:calibrate-cota-layer layer selected texts)
              (prompt
                (strcat "\nCotas detectadas en la capa " layer ": " (itoa count)))
              (list layer (itoa count) (if (> count 0) "DETECTADAS" "PENDIENTE")))
            ;; 2026-08-12 AUTO-DETECT (pedido del usuario): si el primer
            ;; clic no fue TEXT/MTEXT pero si una etiqueta con numero
            ;; (MLeader, etiqueta Civil 3D) o una VIA ya creada (toma su
            ;; RASANTE en el punto del clic), el flujo NO se cancela:
            ;; cambia a cotas seleccionadas (mismo picker del modo
            ;; Pendiente) y sigue pidiendo la cota final y las intermedias.
            (progn
              ;; Una via puede contener atributos numericos; su rasante
              ;; tiene prioridad sobre cualquier texto anidado.
              (if (null via-cota)
                (setq via-cota (urb:cota-from-pick selected)))
              (if via-cota
                (prompt
                  (strcat
                    "\nCota tomada de la RASANTE interpolada en el clic: "
                    (rtos via-cota 2 3)))
                (progn
                  (setq via-cota (urb:cota-from-model-punto selected))
                  (if via-cota
                    (prompt
                      (strcat "\nCota tomada del POZO/ELEMENTO del modelo: "
                        (rtos via-cota 2 3)))
                    (progn
                      (setq via-cota (urb:selected-cota-number selected))
                      (if via-cota
                        (prompt
                          (strcat "\nCota leida de la etiqueta: "
                            (rtos via-cota 2 3))))))))
              (if via-cota
                (progn
                  (setq picks
                    (urb:pick-road-cotas-loop
                      (list (list via-cota (cadr selected)))))
                  (if picks
                    (list "PICKED" picks "DETECTADAS")
                    (progn
                      (prompt "\nSe necesitan al menos 2 cotas.")
                      (list "" "0" "PENDIENTE"))))
                (progn
                  (prompt
                    "\nEl objeto no es texto, etiqueta con numero ni via creada.")
                  (list "" "0" "PENDIENTE"))))))
        (list "" "0" "PENDIENTE")))
    ((urb:string-equal-p mode "Perfil Civil 3D")
      (setq selected (entsel "\nSeleccione el perfil Civil 3D: "))
      (if selected
        (list (cdr (assoc 5 (entget (car selected)))) "1" "DETECTADO")
        (list "" "0" "PENDIENTE")))
    (T (list "" "0" "PENDIENTE"))))

(defun urb:resolve-road-surface (surface / selected ename obj name)
  (if (not (urb:string-equal-p surface "Seleccionar en dibujo"))
    surface
    (progn
      ;; nentsel (no entsel) para poder tomar una superficie anidada en un xref.
      (setq selected
        (nentsel "\nSeleccione la superficie topografica de Civil 3D: "))
      (if selected
        (progn
          (setq ename (car selected))
          (setq obj
            (vl-catch-all-apply 'vlax-ename->vla-object (list ename)))
          (if (and obj (not (vl-catch-all-error-p obj)))
            (setq name (vl-catch-all-apply 'vla-get-Name (list obj))))
          (if (and name (not (vl-catch-all-error-p name)) (/= name ""))
            name
            (progn
              (prompt "\nEl objeto no es una superficie Civil 3D valida.")
              "NO SELECCIONADA")))
        "NO SELECCIONADA"))))

;; via-id (indice 22, opcional/agregado 2026-07-06): identificador
;; estable de la via, independiente de su handle -- el handle cambia
;; cada vez que la via se desempaca/empaca en un bloque al editarla
;; (ver urb:package-road/urb:explode-road-block-boundary), pero el
;; via-id se conserva igual, generado una sola vez en la creacion.
(defun urb:set-road-data
  (boundary name stage substage profile axis surface cota cota-reference cota-count
   station-start interval direction overwidth left-over right-over nominal-width
   area axis-length status alignment-mode axis-start via-id / old base extras)
  (setq old (urb:get-xdata-strings boundary "URB_VIA"))
  (setq base
    (list "VIA" name stage substage profile axis surface cota cota-reference
      cota-count station-start interval direction overwidth left-over right-over
      nominal-width area axis-length status alignment-mode axis-start via-id))
  ;; Editar una via no debe borrar su rasante/movimiento ya calculados.
  ;; 2026-08-13: nthcdr NO existe en AutoLISP (es de Common Lisp) --
  ;; reventaba TODOS los EDITAR de vias con movimiento guardado con
  ;; "no function definition: NTHCDR".
  (if (> (length old) 23)
    (progn
      (setq extras old)
      (repeat 23 (setq extras (cdr extras)))))
  (urb:set-xdata-strings boundary "URB_VIA"
    (append base extras)))

(defun urb:road-data-defaults (data)
  (list
    (cons "name" (nth 1 data))
    (cons "stage" (nth 2 data))
    (cons "substage" (nth 3 data))
    (cons "profile" (nth 4 data))
    (cons "surface" (nth 6 data))
    (cons "cota" (nth 7 data))
    (cons "station_interval" (nth 11 data))
    (cons "alignment" (nth 20 data))
    (cons "overwidth" (nth 13 data))
    (cons "left_over" (nth 14 data))
    (cons "right_over" (nth 15 data))
    (cons "nominal_width" (nth 16 data))))

(defun urb:draw-road-boundary (/ ename obj area)
  (urb:ensure-layer "URB-VIA" 8 T)
  (setq ename
    (urb:draw-polyline
      "\nDibuje el contorno de la via. Enter termina y el programa lo cerrara: "
      "URB-VIA"))
  (if ename
    (progn
      (setq obj (vlax-ename->vla-object ename))
      (if (vlax-property-available-p obj 'Closed T)
        (vla-put-Closed obj :vlax-true))
      (setq area (vl-catch-all-apply 'vla-get-Area (list obj)))
      (if (or (vl-catch-all-error-p area) (<= area 1e-8))
        (progn
          (prompt "\nEl contorno no genera un area valida.")
          nil)
        ename))))

;; 2026-08-11: eje central AUTOMATICO para via con alineamiento "Nuevo"
;; (pedido del usuario: dibujar el contorno primero y no tener que dibujar
;; el eje aparte). v2 (mismo dia): generalizado a contornos con ARCOS y
;; cualquier numero de vertices via cadenas laterales -- para 4 vertices
;; rectos los extremos se detectan solos; para el resto el usuario toca
;; los 2 bordes extremos y el eje es el promedio punto a punto de las 2
;; cadenas laterales. Los extremos usados quedan en *urb-road-end-edges*
;; para que los sardineles reutilicen las mismas cadenas sin repreguntar.
(defun urb:road-axis-from-boundary (boundary / ends axis)
  (setq *urb-road-end-edges* nil)
  (setq ends (urb:road-end-edges boundary))
  (if ends
    (progn
      (setq axis
        (urb:road-axis-from-chains boundary (car ends) (cadr ends)))
      (if axis (setq *urb-road-end-edges* ends))
      axis)
    nil))

;; Proyeccion escalar (clampeada) de un punto sobre el segmento pa->dir.
(defun urb:project-param-on-segment (pa dir len p / tt)
  (setq tt (+ (* (- (car p) (car pa)) (car dir))
              (* (- (cadr p) (cadr pa)) (cadr dir))))
  (max 0.0 (min len tt)))

;; ------------------------------------------------------------------
;; 2026-08-11 v2: infraestructura de CADENAS LATERALES de un contorno de
;; via (soporta arcos y cualquier numero de vertices). El contorno se
;; parte en 2 bordes EXTREMOS + 2 cadenas laterales; el eje automatico es
;; el promedio punto a punto de las cadenas y los sardineles se
;; construyen sobre ellas. Para cuadrilateros rectos los extremos se
;; detectan solos; para el resto el usuario los toca con 2 clics.
;; ------------------------------------------------------------------

;; vertices y bulges del LWPOLYLINE en orden (bulge i = arco del vertice
;; i al i+1)
(defun urb:lwpoly-vertex-bulges (ename / edata item pts bulges)
  (setq edata (entget ename))
  (foreach item edata
    (cond
      ((= (car item) 10)
        (setq pts (cons (cdr item) pts))
        (setq bulges (cons 0.0 bulges)))
      ((= (car item) 42)
        (setq bulges (cons (cdr item) (cdr bulges))))))
  (list (reverse pts) (reverse bulges)))

(defun urb:dist-point-seg (p a b / len dir tt proj)
  (setq p (list (car p) (cadr p)))
  (setq len (distance a b))
  (if (< len 1e-9)
    (distance p a)
    (progn
      (setq dir (mapcar '(lambda (x y) (/ (- y x) len)) a b))
      (setq tt
        (max 0.0
          (min len
            (+ (* (- (car p) (car a)) (car dir))
               (* (- (cadr p) (cadr a)) (cadr dir))))))
      (setq proj (mapcar '(lambda (x d) (+ x (* d tt))) a dir))
      (distance p proj))))

;; indice del borde (vertice i -> i+1) mas cercano al punto p
(defun urb:nearest-edge-index (pts p / n i best best-d d)
  (setq n (length pts) i 0)
  (while (< i n)
    (setq d (urb:dist-point-seg p (nth i pts) (nth (rem (1+ i) n) pts)))
    (if (or (null best-d) (< d best-d)) (setq best-d d best i))
    (setq i (1+ i)))
  best)

;; polilinea ABIERTA temporal con los vertices i-from..i-to (avance
;; circular), conservando los bulges de los bordes intermedios
(defun urb:make-chain-poly (pts bulges i-from i-to / n idx verts vb)
  (setq n (length pts) idx i-from verts nil vb nil)
  (while (/= idx i-to)
    (setq verts (cons (nth idx pts) verts))
    (setq vb (cons (nth idx bulges) vb))
    (setq idx (rem (1+ idx) n)))
  (setq verts (cons (nth i-to pts) verts))
  (setq vb (cons 0.0 vb))
  (setq verts (reverse verts) vb (reverse vb))
  (if (> (length verts) 1)
    (entmakex
      (append
        (list (cons 0 "LWPOLYLINE") (cons 100 "AcDbEntity")
              (cons 100 "AcDbPolyline") (cons 8 "URB-VIA")
              (cons 90 (length verts)) (cons 70 0))
        (apply 'append
          (mapcar '(lambda (pt b) (list (cons 10 pt) (cons 42 b)))
            verts vb))))
    nil))

;; Punto medio (por cuerda) del borde i del contorno.
(defun urb:edge-midpoint (pts i / n)
  (setq n (length pts))
  (mapcar '(lambda (a b) (* 0.5 (+ a b)))
    (nth i pts) (nth (rem (1+ i) n) pts)))

;; Bordes extremos del contorno, AUTOMATICO para cualquier forma
;; (2026-08-11 v5, "quiero que sea mas facil"): los extremos de una via
;; son el par de bordes NO adyacentes cuyos puntos medios quedan mas
;; lejos entre si -- funciona igual para el cuadrilatero recto y para
;; contornos con arcos, jogs de cruces o muchos vertices, sin pedirle
;; clics al usuario. e1 = el extremo mas cercano al PRIMER vertice
;; dibujado (direccion de abscisado predecible). Devuelve (e1 e2) o nil.
;; 5.7.3 (reporte del usuario, foto de una via abocinada en un cruce): el
;; criterio "par de bordes mas alejados" tomaba como extremo un tramo corto
;; del lado CURVO y el eje arrancaba en una esquina. Ahora: direccion
;; principal de la via (PCA de los vertices); candidatos = bordes
;; TRANSVERSALES (|cos| con la direccion principal < 0,6) de al menos 1 m;
;; extremos = el candidato de proyeccion minima y el de maxima. Si no hay
;; dos candidatos validos se usa el criterio anterior.
(defun urb:road-end-edges-pca (pts / n cx cy sxx syy sxy ang ux uy i a b len c proj lo hi e1 e2)
  (setq n (length pts) cx 0.0 cy 0.0 sxx 0.0 syy 0.0 sxy 0.0)
  (foreach p pts (setq cx (+ cx (car p)) cy (+ cy (cadr p))))
  (setq cx (/ cx n) cy (/ cy n))
  (foreach p pts
    (setq sxx (+ sxx (* (- (car p) cx) (- (car p) cx)))
          syy (+ syy (* (- (cadr p) cy) (- (cadr p) cy)))
          sxy (+ sxy (* (- (car p) cx) (- (cadr p) cy)))))
  (setq ang (* 0.5 (atan (* 2.0 sxy) (- sxx syy))) ux (cos ang) uy (sin ang) i 0)
  (while (< i n)
    (setq a (nth i pts) b (nth (rem (1+ i) n) pts) len (distance a b))
    (if (>= len 1.0)
      (progn
        (setq c (abs (/ (+ (* (- (car b) (car a)) ux) (* (- (cadr b) (cadr a)) uy)) len))
              proj (+ (* (- (* 0.5 (+ (car a) (car b))) cx) ux)
                      (* (- (* 0.5 (+ (cadr a) (cadr b))) cy) uy)))
        (if (< c 0.6)
          (progn
            (if (or (null lo) (< proj (car lo))) (setq lo (list proj i)))
            (if (or (null hi) (> proj (car hi))) (setq hi (list proj i)))))))
    (setq i (1+ i)))
  ;; no adyacentes (si comparten vertice una de las cadenas laterales
  ;; quedaria vacia)
  (if (and lo hi (/= (cadr lo) (cadr hi))
           (/= (rem (1+ (cadr lo)) n) (cadr hi))
           (/= (rem (1+ (cadr hi)) n) (cadr lo))
           (> (- (car hi) (car lo)) 1.0))
    (list (cadr lo) (cadr hi))
    nil))

(defun urb:road-end-edges (boundary / vb pts n i j mi mj d best e1 e2 swap pca)
  (setq vb (urb:lwpoly-vertex-bulges boundary))
  (setq pts (car vb) n (length pts))
  (if (>= n 4) (setq pca (urb:road-end-edges-pca pts)))
  (if pca (setq e1 (car pca) e2 (cadr pca) best 1.0))
  (if (< n 4)
    nil
    (progn
      (setq i (if pca n 0))
      (while (< i n)
        (setq mi (urb:edge-midpoint pts i))
        (setq j (1+ i))
        (while (< j n)
          ;; no adyacentes: comparten vertice si j=i+1 o (i=0 y j=n-1)
          (if (not (or (= j (1+ i)) (and (= i 0) (= j (1- n)))))
            (progn
              (setq mj (urb:edge-midpoint pts j))
              (setq d (distance mi mj))
              (if (or (null best) (> d best))
                (setq best d e1 i e2 j))))
          (setq j (1+ j)))
        (setq i (1+ i)))
      (if best
        (progn
          ;; e1 = extremo mas cercano al primer vertice dibujado
          (if (> (distance (nth 0 pts) (urb:edge-midpoint pts e1))
                 (distance (nth 0 pts) (urb:edge-midpoint pts e2)))
            (setq swap e1 e1 e2 e2 swap))
          (list e1 e2))
        nil))))

;; Cadenas laterales del contorno dados sus bordes extremos: lista
;; (chainA chainB) de polilineas TEMPORALES (el que llama las borra).
;; chainA va del extremo inicial al final; chainB en el mismo sentido
;; geometrico pero recorrida al reves (usar length-fraccion invertida).
(defun urb:road-side-chains (boundary e1 e2 / vb pts bulges n a b)
  (setq vb (urb:lwpoly-vertex-bulges boundary))
  (setq pts (car vb) bulges (cadr vb) n (length pts))
  (setq a (urb:make-chain-poly pts bulges (rem (1+ e1) n) e2))
  (setq b (urb:make-chain-poly pts bulges (rem (1+ e2) n) e1))
  (if (and a b)
    (list a b)
    (progn
      (if a (entdel a))
      (if b (entdel b))
      nil)))

;; Eje central por promedio punto a punto de las 2 cadenas laterales.
;; Devuelve el ename del eje (LWPOLYLINE en URB-VIA) o nil.
;; 5.7.2 (reporte del usuario con fotos): (1) donde la via NO es uniforme
;; (bahia, abocinamiento en un cruce) el eje se desviaba hacia el ensanche:
;; el promedio con el punto mas cercano del otro lado se corre la MITAD del
;; ensanche. (2) a veces el eje terminaba en una PUNTA (esquina) y no en el
;; centro del borde final. Ahora:
;;  - se mide el ancho en cada muestra y su MEDIANA (ancho tipico);
;;  - donde el ancho se sale de lo tipico (> max(0,5 m; 15%)), el centro se
;;    ancla al lado REGULAR: a media calzada tipica desde ese borde, eligiendo
;;    el candidato que sigue la linea de los centros buenos vecinos;
;;  - el eje empieza y termina SIEMPRE en el punto medio de los bordes
;;    extremos del contorno.
(defun urb:median (vals / s n)
  (setq s (mapcar '(lambda (k) (nth k vals)) (vl-sort-i vals '<)) n (length s))
  (if (= n 0) 0.0
    (if (= (rem n 2) 1) (nth (/ n 2) s)
      (* 0.5 (+ (nth (1- (/ n 2)) s) (nth (/ n 2) s))))))

(defun urb:percentile (vals q / s n)
  (setq s (mapcar '(lambda (k) (nth k vals)) (vl-sort-i vals '<)) n (length s))
  (if (= n 0) 0.0 (nth (min (1- n) (fix (* q (1- n)))) s)))

(defun urb:axis-proj-param (m p q / dx dy l2)
  (setq dx (- (car q) (car p)) dy (- (cadr q) (cadr p)) l2 (+ (* dx dx) (* dy dy)))
  (if (< l2 1e-12) 0.0
    (max 0.0 (min 1.0 (/ (+ (* (- (car m) (car p)) dx) (* (- (cadr m) (cadr p)) dy)) l2)))))

(defun urb:axis-lerp (p q tt)
  (list (+ (car p) (* tt (- (car q) (car p)))) (+ (cadr p) (* tt (- (cadr q) (cadr p))))))

(defun urb:road-axis-from-chains (boundary e1 e2 / chains ca cb la lb k steps
   frac pa pb mids ename samples wmed tol n i good prev next cand1 cand2 ref
   ux uy w pts vb start-mid end-mid out)
  (setq chains (urb:road-side-chains boundary e1 e2))
  (if chains
    (progn
      (setq ca (car chains) cb (cadr chains))
      (setq la (vlax-curve-getDistAtParam ca (vlax-curve-getEndParam ca)))
      (setq lb (vlax-curve-getDistAtParam cb (vlax-curve-getEndParam cb)))
      ;; muestreo cada ~1 m (antes ~2 m, tope 60): el ancho se lee mejor
      (setq steps (max 8 (min 400 (fix (max la lb)))))
      ;; 2026-08-11 v5: emparejamiento por PROYECCION PERPENDICULAR (punto
      ;; mas cercano de la otra cadena), no por fraccion de longitud.
      ;; samples: (pa pb ancho)
      (setq k 0 samples nil)
      (while (<= k steps)
        (setq frac (/ (float k) steps))
        (setq pa (vlax-curve-getPointAtDist ca (* frac la)))
        (setq pb
          (if pa
            (vl-catch-all-apply 'vlax-curve-getClosestPointTo (list cb pa))
            nil))
        (if (and pa pb (not (vl-catch-all-error-p pb)))
          (setq samples
            (cons (list (list (car pa) (cadr pa)) (list (car pb) (cadr pb))
                        (distance (list (car pa) (cadr pa)) (list (car pb) (cadr pb))))
                  samples)))
        (setq k (1+ k)))
      ;; 5.7.3: ancho TIPICO = percentil 30 (no la mediana): en una via
      ;; corta abocinada en un cruce la mitad o mas de las muestras estan en
      ;; el abocinamiento y la mediana ya era "ancho de cruce". Los
      ;; abocinamientos y bahias solo ENSANCHAN, asi que el ancho tipico es
      ;; el de la parte baja de la distribucion.
      (setq samples (reverse samples)
            wmed (urb:percentile (mapcar 'caddr samples) 0.30)
            tol (max 0.25 (* 0.05 wmed))
            n (length samples))
      ;; centros de los bordes extremos: anclas del principio y del final
      (setq vb (urb:lwpoly-vertex-bulges boundary) pts (car vb)
            start-mid (urb:edge-midpoint pts e1)
            end-mid (urb:edge-midpoint pts e2)
            start-mid (list (car start-mid) (cadr start-mid))
            end-mid (list (car end-mid) (cadr end-mid)))
      (if (and samples
               (> (distance start-mid (urb:axis-lerp (car (car samples)) (cadr (car samples)) 0.5))
                  (distance end-mid (urb:axis-lerp (car (car samples)) (cadr (car samples)) 0.5))))
        (setq k start-mid start-mid end-mid end-mid k))
      ;; buenos = ancho tipico; lista (indice centro) de los buenos, que se
      ;; recorre con un cursor (sin nth dentro del ciclo). Los centros de
      ;; los bordes extremos entran como buenos en -1 y n.
      (setq i 0 good nil)
      (foreach s samples
        (if (<= (abs (- (caddr s) wmed)) tol)
          (setq good (cons (list i (urb:axis-lerp (car s) (cadr s) 0.5)) good)))
        (setq i (1+ i)))
      (setq good (append (list (list -1 start-mid)) (reverse good) (list (list n end-mid))))
      (setq i 0 mids nil prev nil next good)
      (foreach s samples
        (setq pa (car s) pb (cadr s) w (caddr s))
        ;; cursor: prev = ultimo bueno con indice <= i; next = primero > i
        (while (and next (<= (car (car next)) i))
          (setq prev (car next) next (cdr next)))
        (if (or (and prev (= (car prev) i)) (< w 1e-6) (null good))
          (setq mids (cons (urb:axis-lerp pa pb 0.5) mids))
          (progn
            (setq next (car next))
            (setq ref
              (cond
                ;; 5.7.3: parametro por PROYECCION del centro natural sobre
                ;; la recta entre centros buenos (el indice de muestra no
                ;; sirve: sobre el lado curvo las muestras no avanzan parejo
                ;; y el eje salia en zigzag)
                ((and prev next)
                  (urb:axis-lerp (cadr prev) (cadr next)
                    (urb:axis-proj-param (urb:axis-lerp pa pb 0.5) (cadr prev) (cadr next))))
                (prev (cadr prev))
                (T (cadr next))))
            (setq ux (/ (- (car pb) (car pa)) w) uy (/ (- (cadr pb) (cadr pa)) w)
                  cand1 (list (+ (car pa) (* ux 0.5 wmed)) (+ (cadr pa) (* uy 0.5 wmed)))
                  cand2 (list (- (car pb) (* ux 0.5 wmed)) (- (cadr pb) (* uy 0.5 wmed))))
            ;; bahia a UN lado: el candidato anclado al lado regular cae
            ;; sobre la linea de los centros buenos (se usa, sigue curvas).
            ;; Abocinamiento hacia el extremo: ningun candidato cae cerca y
            ;; el eje va RECTO entre el ultimo centro bueno y el centro del
            ;; borde final (la linea amarilla del reporte).
            ;; (medido: alternar entre candidato anclado y recta dejaba un
            ;; quiebre en zigzag donde empieza el abocinamiento; la recta
            ;; entre centros buenos cubre los dos casos sin saltos)
            (setq mids (cons ref mids))
            ;; restaurar el cursor (next se uso como elemento suelto)
            (setq next (vl-member-if '(lambda (g) (> (car g) i)) good))))
        (setq i (1+ i)))
      (setq mids (reverse mids))
      ;; extremos: centro de los bordes extremos del contorno (se descartan
      ;; las muestras a menos de 0,5 m de ellos para no hacer "gancho")
      (setq out nil)
      (foreach p mids
        (if (and (> (distance p start-mid) 0.5) (> (distance p end-mid) 0.5))
          (setq out (cons p out))))
      (setq mids (append (list start-mid) (reverse out) (list end-mid)))
      ;; suavizado: promedio movil de 3 (extremos intactos) para limar el
      ;; residuo de los jogs
      (if (> (length mids) 4)
        (progn
          (setq k 1)
          (setq frac (list (car mids)))
          (while (< k (1- (length mids)))
            (setq frac
              (cons
                (mapcar
                  '(lambda (a b c) (/ (+ a b c) 3.0))
                  (nth (1- k) mids) (nth k mids) (nth (1+ k) mids))
                frac))
            (setq k (1+ k)))
          (setq frac (cons (nth (1- (length mids)) mids) frac))
          (setq mids (reverse frac))))
      ;; 5.7.2: con muestreo cada ~1 m se aligera la polilinea: se quitan
      ;; los vertices que se desvian menos de 2 cm de la recta entre el
      ;; ultimo conservado y el siguiente
      (if (> (length mids) 3)
        (progn
          (setq out (list (car mids)) k (cdr mids))
          (while (cdr k)
            (if (> (urb:dist-point-seg (car k) (car out) (cadr k)) 0.02)
              (setq out (cons (car k) out)))
            (setq k (cdr k)))
          (setq mids (reverse (cons (last mids) out)))))
      (entdel ca)
      (entdel cb)
      (if (> (length mids) 1)
        (progn
          (urb:ensure-layer "URB-VIA" 8 T)
          (setq ename
            (entmakex
              (append
                (list (cons 0 "LWPOLYLINE") (cons 100 "AcDbEntity")
                      (cons 100 "AcDbPolyline") (cons 8 "URB-VIA")
                      (cons 90 (length mids)) (cons 70 0))
                (mapcar '(lambda (p) (cons 10 p)) mids))))
          ename)
        nil))
    nil))

;; 5.7.3 (pedido del usuario: "el alineamiento tiene que quedar como el
;; amarillo, me lo creo como el naranja"): el eje automatico se MUESTRA y
;; se confirma antes de seguir. Extremos = el usuario toca los 2 bordes
;; extremos del contorno y se recalcula; Dibujar = eje a mano. Devuelve
;; el eje aceptado (o nil si se cancela).
(defun urb:confirm-auto-axis (boundary axis / ans obj p1 p2 pts e1 e2 done)
  (while (and axis (not done))
    (setq obj (vlax-ename->vla-object axis))
    (vl-catch-all-apply 'vla-put-Color (list obj 6))
    (vl-catch-all-apply 'vla-put-ConstantWidth (list obj 0.15))
    (vl-catch-all-apply 'vla-Update (list obj))
    (initget "Si Extremos Dibujar")
    (setq ans (getkword "\nEje automatico (magenta). Es correcto? [Si/Extremos/Dibujar] <Si>: "))
    (cond
      ((or (null ans) (= ans "Si"))
        (vl-catch-all-apply 'vla-put-Color (list obj 256))
        (vl-catch-all-apply 'vla-put-ConstantWidth (list obj 0.0))
        (setq done T))
      ((= ans "Extremos")
        (setq p1 (getpoint "\nClic sobre el borde del INICIO de la via: ")
              p2 (if p1 (getpoint "\nClic sobre el borde del FINAL de la via: ")))
        (if (and p1 p2)
          (progn
            (setq pts (car (urb:lwpoly-vertex-bulges boundary))
                  e1 (urb:nearest-edge-index pts p1)
                  e2 (urb:nearest-edge-index pts p2))
            (if (and e1 e2 (/= e1 e2))
              (progn
                (entdel axis)
                (setq axis (urb:road-axis-from-chains boundary e1 e2))
                (if axis (setq *urb-road-end-edges* (list e1 e2))))
              (prompt "\nLos dos clics cayeron en el mismo borde; se conserva el eje.")))))
      ((= ans "Dibujar")
        (entdel axis)
        (setq axis (urb:select-or-draw-road-axis "Nuevo") done T))))
  axis)

;; Resalta una cadena temporal con entidad magenta gruesa y selection glow.
;; A diferencia de grdraw solo, el resaltado persiste mientras getkword espera.
(defun urb:set-chain-highlight (chain enabled / obj)
  (if (and chain (entget chain))
    (progn
      (setq obj (vlax-ename->vla-object chain))
      (if enabled
        (progn
          (vl-catch-all-apply 'vla-put-Color (list obj 6))
          (vl-catch-all-apply 'vla-put-Lineweight (list obj 70))
          (vl-catch-all-apply 'vla-put-ConstantWidth (list obj 0.04))
          (vl-catch-all-apply 'vla-Highlight (list obj :vlax-true)))
        (vl-catch-all-apply 'vla-Highlight (list obj :vlax-false)))
      (vl-catch-all-apply 'vla-Update (list obj))
      (redraw chain (if enabled 3 4))))
  chain)

(defun urb:highlight-chain (chain / len d step p1 p2)
  (urb:set-chain-highlight chain T)
  (setq len (vlax-curve-getDistAtParam chain (vlax-curve-getEndParam chain)))
  (setq step (max 0.25 (/ len 80.0)))
  (setq d 0.0)
  (while (< d (- len 1e-6))
    (setq p1 (vlax-curve-getPointAtDist chain d))
    (setq p2 (vlax-curve-getPointAtDist chain (min len (+ d step))))
    (if (and p1 p2) (grdraw p1 p2 3 1))
    (setq d (+ d step)))
  len)

;; Sub-polilinea de una cadena entre las distancias d1..d2, muestreada
;; cada 0.25 m (sigue arcos con precision suficiente para el sardinel).
(defun urb:chain-subpoly (chain d1 d2 / len steps k d pt pts)
  (setq len (- d2 d1))
  (setq steps (max 1 (fix (/ len 0.25))))
  (setq k 0 pts nil)
  (while (<= k steps)
    (setq d (+ d1 (* len (/ (float k) steps))))
    (setq pt (vlax-curve-getPointAtDist chain d))
    (if pt (setq pts (cons (list (car pt) (cadr pt)) pts)))
    (setq k (1+ k)))
  (setq pts (reverse pts))
  (if (> (length pts) 1)
    (entmakex
      (append
        (list (cons 0 "LWPOLYLINE") (cons 100 "AcDbEntity")
              (cons 100 "AcDbPolyline") (cons 8 "URB-VIA")
              (cons 90 (length pts)) (cons 70 0))
        (mapcar '(lambda (p) (cons 10 p)) pts)))
    nil))

;; 2026-08-11 v2: SARDINELES AUTOMATICOS sobre las CADENAS laterales del
;; contorno (soporta arcos y cualquier numero de vertices, ya no solo
;; cuadrilateros -- reporte del usuario). Por cada costado: pregunta
;; [Si/No] (por si un costado ya tiene sardinel de otra via), resalta la
;; cadena en verde, y el usuario marca pares INICIO/FIN de los tramos SIN
;; sardinel (bocas de cruce); Enter sigue. Espesor fijo 0.20 (pedido del
;; usuario). Reutiliza los bordes extremos ya elegidos para el eje
;; automatico (*urb-road-end-edges*) sin repreguntar.
;; 2026-09-02 (reporte del usuario con foto: en tramos CURVOS el sardinel
;; izquierdo salia INTERNO): el test del lado por producto punto contra el
;; CENTROIDE falla en contornos curvos o en L (el centroide puede quedar
;; del mismo lado que el exterior local). Ahora el lado se decide con un
;; test real de punto-dentro-del-contorno: se muestrea el contorno cada
;; 0.25 m (los arcos quedan bien representados) y se lanza ray-casting.
(defun urb:curve-sample-points (curve step / len n i pts d p)
  (setq len (vl-catch-all-apply 'vlax-curve-getDistAtParam
              (list curve (vlax-curve-getEndParam curve))))
  (if (or (vl-catch-all-error-p len) (null len) (<= len 1e-6))
    nil
    (progn
      (setq n (max 24 (fix (/ len step))) i 0 pts nil)
      (while (< i n)
        (setq d (* len (/ (float i) n)))
        (setq p (vl-catch-all-apply 'vlax-curve-getPointAtDist (list curve d)))
        (if (not (vl-catch-all-error-p p))
          (setq pts (cons (list (car p) (cadr p)) pts)))
        (setq i (1+ i)))
      (reverse pts))))

(defun urb:point-in-poly-2d (pt pts / x y prev p xi yi xj yj inside)
  (setq x (car pt) y (cadr pt) inside nil prev (last pts))
  (foreach p pts
    (setq xi (car p) yi (cadr p) xj (car prev) yj (cadr prev))
    (if (and (/= (> yi y) (> yj y))
             (< x (+ xi (/ (* (- xj xi) (- y yi)) (- yj yi)))))
      (setq inside (not inside)))
    (setq prev p))
  inside)

(defun urb:create-road-sardineles (boundary etapa subetapa
   / ends chains chain len kw pts centroid g1 g2 c1 c2 tt1 tt2 swap gaps
   kept prev item seg ename mid-pt deriv dlen normal side-point count
   bnd-samples probe)
  (setq ends
    (if (and (boundp '*urb-road-end-edges*) *urb-road-end-edges*)
      *urb-road-end-edges*
      (urb:road-end-edges boundary)))
  (if (null ends)
    (progn
      (prompt "\nSardineles automaticos: no se pudieron determinar los costados.")
      nil)
    (progn
      (setq chains (urb:road-side-chains boundary (car ends) (cadr ends)))
      (if (null chains)
        (progn
          (prompt "\nSardineles automaticos: no se pudieron construir los costados.")
          nil)
        (progn
          (setq pts (urb:lwpoly-points boundary))
          (setq centroid
            (list
              (/ (apply '+ (mapcar 'car pts)) (float (length pts)))
              (/ (apply '+ (mapcar 'cadr pts)) (float (length pts)))))
          ;; muestreo del contorno para el test de lado (curvas incluidas)
          (setq bnd-samples (urb:curve-sample-points boundary 0.25))
          (setq count 0)
          (foreach chain chains
            (setq len (urb:highlight-chain chain))
            (initget "Si No")
            (setq kw
              (getkword
                (strcat "\nSardinel en el costado resaltado ("
                        (rtos len 2 2) " m)? [Si/No] <Si>: ")))
            (if (not (= kw "No"))
              (progn
                (setq gaps nil g1 T)
                (while g1
                  (setq g1
                    (getpoint
                      "\n  INICIO de tramo SIN sardinel (cruce; Enter si no hay mas): "))
                  (if g1
                    (progn
                      (setq g2 (getpoint g1 "\n  FIN del tramo sin sardinel: "))
                      (if g2
                        (progn
                          (setq c1
                            (vl-catch-all-apply
                              'vlax-curve-getClosestPointTo (list chain g1)))
                          (setq c2
                            (vl-catch-all-apply
                              'vlax-curve-getClosestPointTo (list chain g2)))
                          (if (and (not (vl-catch-all-error-p c1))
                                   (not (vl-catch-all-error-p c2)))
                            (progn
                              (setq tt1 (vlax-curve-getDistAtPoint chain c1))
                              (setq tt2 (vlax-curve-getDistAtPoint chain c2))
                              (if (and tt1 tt2)
                                (progn
                                  (if (> tt1 tt2)
                                    (setq swap tt1 tt1 tt2 tt2 swap))
                                  (setq gaps (cons (list tt1 tt2) gaps)))))))))))
                (setq gaps (vl-sort gaps '(lambda (a b) (< (car a) (car b)))))
                (setq kept nil prev 0.0)
                (foreach item gaps
                  (if (> (- (car item) prev) 0.10)
                    (setq kept (cons (list prev (car item)) kept)))
                  (setq prev (max prev (cadr item))))
                (if (> (- len prev) 0.10)
                  (setq kept (cons (list prev len) kept)))
                (setq kept (reverse kept))
                (foreach seg kept
                  (setq ename (urb:chain-subpoly chain (car seg) (cadr seg)))
                  (if ename
                    (progn
                      ;; lado de crecimiento: hacia AFUERA de la via
                      (setq mid-pt
                        (vlax-curve-getPointAtDist chain
                          (* 0.5 (+ (car seg) (cadr seg)))))
                      (setq deriv
                        (vlax-curve-getFirstDeriv chain
                          (vlax-curve-getParamAtDist chain
                            (* 0.5 (+ (car seg) (cadr seg))))))
                      (setq dlen (distance '(0.0 0.0 0.0) deriv))
                      (setq normal
                        (if (> dlen 1e-9)
                          (list (- (/ (cadr deriv) dlen)) (/ (car deriv) dlen))
                          (list 0.0 1.0)))
                      ;; lado por test punto-dentro-del-contorno (curvas OK);
                      ;; el centroide queda solo como fallback sin muestreo
                      (if bnd-samples
                        (progn
                          (setq probe
                            (list (+ (car mid-pt) (* 0.30 (car normal)))
                                  (+ (cadr mid-pt) (* 0.30 (cadr normal)))))
                          (if (urb:point-in-poly-2d probe bnd-samples)
                            (setq normal (mapcar '- normal))))
                        (if (< (+ (* (car normal) (- (car mid-pt) (car centroid)))
                                  (* (cadr normal) (- (cadr mid-pt) (cadr centroid))))
                               0.0)
                          (setq normal (mapcar '- normal))))
                      (setq side-point
                        (list (+ (car mid-pt) (car normal))
                              (+ (cadr mid-pt) (cadr normal))))
                      (if (urb:build-prefab-from-reference
                            ename side-point "Sardinel" 0.20 etapa subetapa
                            "Exterior" "Via")
                        (setq count (1+ count))))))))
            (urb:set-chain-highlight chain nil)
            (redraw))
          (foreach chain chains (if (entget chain) (entdel chain)))
          (prompt (strcat "\nSardineles creados: " (itoa count) " tramo(s)."))
          count)))))

;; El eje puede ser mucho mas largo que el tramo (varias vias por etapa
;; comparten un mismo alineamiento). En vez de pedir al usuario que
;; digite donde empieza y cuanto mide su tramo, se proyecta cada vertice
;; del contorno ya dibujado sobre el eje y se toma el rango [min,max] de
;; esas distancias: eso es exactamente el tramo que el usuario dibujo.
(defun urb:axis-range-for-boundary
  (axis boundary-ename / points p closest dist minv maxv)
  (setq points (urb:lwpoly-points boundary-ename))
  (foreach p points
    (setq closest
      (vl-catch-all-apply 'vlax-curve-getClosestPointTo (list axis p)))
    (if (not (vl-catch-all-error-p closest))
      (progn
        (setq dist
          (vl-catch-all-apply 'vlax-curve-getDistAtPoint (list axis closest)))
        (if (not (vl-catch-all-error-p dist))
          (progn
            (if (or (null minv) (< dist minv)) (setq minv dist))
            (if (or (null maxv) (> dist maxv)) (setq maxv dist))))))
  )
  (if (and minv maxv) (list minv (- maxv minv)) nil)
)

;; BUG (2026-07-06, mismo patron que distance/length): "type" es una
;; funcion nativa de AutoLISP (devuelve el tipo de un valor). Usarla
;; como variable local la tapa MIENTRAS ESTA ACTIVA -- y
;; urb:string-equal-p (via urb:safe-string) SI llama (type value)
;; internamente, asi que el foreach de abajo rompia con "no function
;; definition: TYPE" apenas se llegaba a la memoria final de una via
;; (primera vez que el flujo completo se ejecutaba de principio a fin).
;; Renombrado a layer-type.
(defun urb:road-profile-memory (profile-name area base-area left-area right-area / profile layers layer layer-type layer-scope layer-area quantity result)
  (setq profile (urb:road-profile-by-name profile-name))
  (setq layers (cadr profile))
  (setq result
    (strcat
      "Via - memoria de cantidades\n"
      "Perfil: " profile-name
      "\nArea total: " (rtos area 2 2) " m2"
      "\nArea base: " (rtos base-area 2 2) " m2"
      "\nSobreancho izquierdo: " (rtos left-area 2 2) " m2"
      "\nSobreancho derecho: " (rtos right-area 2 2) " m2\n"))
  (foreach layer layers
    (setq layer-type (nth 1 layer))
    (setq layer-scope (nth 4 layer))
    (setq layer-area (if (urb:string-equal-p layer-scope "Base") base-area area))
    (setq quantity
      (if (urb:string-equal-p layer-type "Volumen")
        (* layer-area (atof (nth 2 layer)))
        (* layer-area (+ 1.0 (/ (atof (nth 3 layer)) 100.0)))))
    (setq result
      (strcat result "\n"
        (urb:budget-road-layer-name (nth 0 layer)) ": "
        (rtos quantity 2 2)
        (if (urb:string-equal-p layer-type "Volumen") " m3" " m2"))))
  result)

(defun urb:road-memory-from-data
  (boundary data / area road-length left right over-area left-area right-area
   base-area mov result start-number end-label average-width)
  ;; *urb-memoria-stage*: rastro fino para cazar el "consp nil" reportado
  ;; en vivo (2026-08-11) que no se ha podido reproducir headless -- el
  ;; aviso blindado de urb:create-road lo imprime junto al error.
  (setq *urb-memoria-stage* "areas-17")
  (setq area (atof (urb:safe-string (nth 17 data) "0")))
  (setq *urb-memoria-stage* "areas-18")
  (setq road-length (atof (urb:safe-string (nth 18 data) "0")))
  (setq *urb-memoria-stage* "areas-14")
  (setq left (atof (urb:safe-string (nth 14 data) "0")))
  (setq *urb-memoria-stage* "areas-15")
  (setq right (atof (urb:safe-string (nth 15 data) "0")))
  (setq *urb-memoria-stage* "areas-aritmetica")
  ;; 2026-08-30: contorno = CALZADA; el sobreancho es ADICIONAL
  (setq left-area (* road-length left))
  (setq right-area (* road-length right))
  (setq over-area (+ left-area right-area))
  (setq base-area area)
  (setq area (+ area over-area))
  (setq average-width
    (if (> road-length 1e-9) (/ area road-length) 0.0))
  (setq *urb-memoria-stage* "abscisas")
  (setq start-number
    (urb:station-number (urb:safe-string (nth 10 data) "0+000")))
  (setq end-label (urb:format-station (+ start-number road-length)))
  (setq *urb-memoria-stage* "perfil")
  (setq result
    (urb:road-profile-memory (nth 4 data) area base-area left-area right-area))
  (setq *urb-memoria-stage* "geometria")
  (setq result
    (strcat result
      "\n\nGeometria del tramo:"
      "\nLongitud: " (rtos road-length 2 2) " m"
      "\nAncho medio real (area/longitud): " (rtos average-width 2 2) " m"
      "\nAbscisado: " (urb:safe-string (nth 10 data) "0+000")
      " a " end-label))
  (setq *urb-memoria-stage* "movimiento")
  (setq mov (urb:road-movement-data boundary))
  (if mov
    (setq result
      (strcat result
        "\n\nMovimiento de tierras (" (urb:safe-string (nth 2 mov) "") "):"
        "\nCORTE: " (urb:safe-string (nth 0 mov) "0") " m3"
        "\nRELLENO: " (urb:safe-string (nth 1 mov) "0") " m3"
        "\nSecciones evaluadas: " (urb:safe-string (nth 3 mov) "0")
        " | omitidas: " (urb:safe-string (nth 4 mov) "0")
        "\nAncho usado: " (urb:safe-string (nth 5 mov) "0") " m"
        " | profundidad: " (urb:safe-string (nth 6 mov) "0") " m")))
  (setq *urb-memoria-stage* "fin")
  result)

(defun urb:text-to-mtext (text / position result head)
  (setq text (urb:safe-string text ""))
  (setq result "")
  (while (setq position (vl-string-search "\n" text))
    (setq head (if (> position 0) (substr text 1 position) ""))
    (setq result (strcat result head "\\P"))
    (setq text (substr text (+ position 2))))
  (strcat result text)
)

(defun urb:road-summary-point (boundary / points centroid minx miny maxx maxy point)
  (setq points (urb:lwpoly-points boundary))
  (setq centroid (urb:polygon-centroid points))
  (if centroid
    (list (car centroid) (cadr centroid) 0.0)
    (progn
      ;; Respaldo para contornos degenerados: centro de su caja envolvente.
      (foreach point points
        (if (or (null minx) (< (car point) minx)) (setq minx (car point)))
        (if (or (null miny) (< (cadr point) miny)) (setq miny (cadr point)))
        (if (or (null maxx) (> (car point) maxx)) (setq maxx (car point)))
        (if (or (null maxy) (> (cadr point) maxy)) (setq maxy (cadr point))))
      (if (and minx miny maxx maxy)
        (list (/ (+ minx maxx) 2.0) (/ (+ miny maxy) 2.0) 0.0)
        '(0.0 0.0 0.0))))
)

;; Crea una memoria visible junto a la via. Se etiqueta como geometria
;; generada para que viaje dentro del bloque y se regenere al editar.
(defun urb:road-summary-angle (axis point / closest param derivative angle-value)
  (if axis
    (progn
      (setq closest
        (vl-catch-all-apply 'vlax-curve-getClosestPointTo (list axis point)))
      (if (not (vl-catch-all-error-p closest))
        (progn
          (setq param
            (vl-catch-all-apply 'vlax-curve-getParamAtPoint (list axis closest)))
          (if (not (vl-catch-all-error-p param))
            (progn
              (setq derivative
                (vl-catch-all-apply 'vlax-curve-getFirstDeriv (list axis param)))
              (if (and (not (vl-catch-all-error-p derivative))
                       derivative
                       (> (distance '(0.0 0.0 0.0) derivative) 1e-9))
                (progn
                  (setq angle-value (atan (cadr derivative) (car derivative)))
                  ;; Mantiene el texto paralelo al eje pero siempre legible:
                  ;; si quedaria cabeza abajo, se gira 180 grados.
                  (if (> angle-value (/ pi 2.0))
                    (setq angle-value (- angle-value pi)))
                  (if (< angle-value (- (/ pi 2.0)))
                    (setq angle-value (+ angle-value pi)))
                  angle-value))))))))
)

(defun urb:create-road-summary
  (boundary axis / data content point textheight width mtext handle rotation)
  (setq data (urb:get-xdata-strings boundary "URB_VIA"))
  (if data
    (progn
      (urb:ensure-layer "URB-VIA" 8 T)
      (setq content
        (strcat
          "VIA: " (urb:safe-string (nth 1 data) "")
          "\nETAPA: " (urb:safe-string (nth 2 data) "")
          " | SUBETAPA: " (urb:safe-string (nth 3 data) "")
          "\nESTADO: " (urb:safe-string (nth 19 data) "")
          "\nCAPA DE COTAS: " (urb:safe-string (nth 8 data) "")
          "\n\n" (urb:road-memory-from-data boundary data)))
      (setq point (urb:road-summary-point boundary))
      (setq textheight (max 0.20 (getvar "TEXTSIZE")))
      (setq width (* textheight 55.0))
      (setq mtext
        (vla-AddMText
          (urb:space) (vlax-3d-point point) width
          (urb:text-to-mtext content)))
      ;; El punto calculado es el centro real del contorno; se usa tambien
      ;; como punto medio del cuadro de texto para que el resumen quede
      ;; centrado visualmente dentro de la via.
      (vl-catch-all-apply 'vla-put-AttachmentPoint (list mtext 5))
      (vl-catch-all-apply
        'vla-put-InsertionPoint (list mtext (vlax-3d-point point)))
      (setq rotation (urb:road-summary-angle axis point))
      (if rotation
        (vl-catch-all-apply 'vla-put-Rotation (list mtext rotation)))
      (vla-put-Layer mtext "URB-VIA")
      (vla-put-Color mtext 256)
      (vl-catch-all-apply 'vla-put-TextHeight (list mtext textheight))
      (vl-catch-all-apply 'vla-put-BackgroundFill (list mtext :vlax-true))
      (setq handle
        (vla-get-Handle (vlax-ename->vla-object boundary)))
      (urb:tag-road-generated mtext handle)
      mtext))
)

(defun urb:replace-nth (index value lst / i result item)
  (setq i 0 result nil)
  (foreach item lst
    (setq result (cons (if (= i index) value item) result))
    (setq i (1+ i)))
  (reverse result)
)

;; Desde 4.5.0 el movimiento vive dentro del mismo registro URB_VIA.
;; Indices 23..32: corte, relleno, metodo, secciones, omitidas, ancho,
;; profundidad, cota inicial, cota final y muestras compactas de rasante.
;; Esto evita la perdida observada
;; en Civil 3D al intentar conservar dos aplicaciones XDATA independientes.
(defun urb:road-movement-data (ename / data legacy)
  (setq data (urb:get-xdata-strings ename "URB_VIA"))
  (if (and data (> (length data) 31)
           (/= (urb:safe-string (nth 23 data) "") ""))
    (append (list
      (nth 23 data) (nth 24 data) (nth 25 data)
      (nth 26 data) (nth 27 data) (nth 28 data)
      (nth 29 data) (nth 30 data) (nth 31 data))
      (if (> (length data) 32) (list (nth 32 data)) nil))
    (progn
      ;; Compatibilidad de lectura con vias de versiones 4.4.x.
      (setq legacy (urb:get-xdata-strings ename "URB_VIA_MOV"))
      legacy))
)

(defun urb:set-road-movement-data (boundary mov / data index value)
  (setq data (urb:get-xdata-strings boundary "URB_VIA"))
  (if data
    (progn
      (while (< (length data) 33)
        (setq data (append data (list ""))))
      (setq data
        (urb:replace-nth 19 "MOVIMIENTO DE TIERRAS CALCULADO" data))
      (setq index 0)
      (foreach value mov
        (if (< index 10)
          (setq data
            (urb:replace-nth (+ 23 index)
              (urb:safe-string value "") data)))
        (setq index (1+ index)))
      (urb:set-xdata-strings boundary "URB_VIA" data)
      mov)
    nil)
)

(defun urb:invalidate-road-movement (boundary clear-grade reason / data index)
  ;; Nunca conservar cantidades calculadas para otro eje o una cobertura
  ;; incompleta. Las cotas se pueden conservar si el eje no ha cambiado.
  (setq data (urb:get-xdata-strings boundary "URB_VIA"))
  (if data
    (progn
      (setq data (urb:replace-nth 19 reason data) index 23)
      (while (< index (min (length data) (if clear-grade 33 30)))
        (setq data (urb:replace-nth index "" data) index (1+ index)))
      (urb:set-xdata-strings boundary "URB_VIA" data)
      (urb:set-xdata-strings boundary "URB_VIA_MOV" nil)
      (vl-catch-all-apply 'vlax-ldata-delete (list boundary "URB_VIA_AUDIT"))
      (if clear-grade
        (progn
          (vl-catch-all-apply 'vlax-ldata-delete (list boundary "URB_VIA_RASANTE_SRC"))
          (vl-catch-all-apply 'vlax-ldata-delete (list boundary "URB_VIA_RASANTE_FULL"))))))
  nil)

;; Cota al final de un tramo a partir de la cota inicial, la pendiente en %
;; y la longitud. Pura, para poder autoprobarla.
(defun urb:cota-por-pendiente (c0 slope span)
  (+ c0 (* (/ slope 100.0) span)))

(defun urb:store-selected-road-grade
  (boundary axis-start span direction
   / data records item local c0 c1 src k)
  ;; Persiste la rasante escogida por el usuario ANTES de intentar leer la
  ;; superficie. Asi una via sin TN calculada sigue sirviendo como fuente
  ;; de cota inicial para otra via.
  (cond
    ((and *urb-road-picked-stations*
          (> (length *urb-road-picked-stations*) 1))
      (foreach item *urb-road-picked-stations*
        (setq local
          (if (urb:string-equal-p direction "Final")
            (- (+ axis-start span) (car item))
            (- (car item) axis-start)))
        (setq records (cons (list local (cadr item)) records)))
      (setq records
        (vl-sort records '(lambda (a b) (< (car a) (car b)))))
      (setq c0 (urb:cota-at-axis-distance 0.0 records)
            c1 (urb:cota-at-axis-distance span records)))
    ((and *urb-road-picked-cotas* (= (length *urb-road-picked-cotas*) 2))
      (setq c0 (car *urb-road-picked-cotas*)
            c1 (cadr *urb-road-picked-cotas*)
            records (list (list 0.0 c0) (list span c1))))
    ;; 2026-09-10: UNA sola cota de referencia + pendiente. Cubre "tengo
    ;; via al principio pero no al final" y "no tengo via en ninguno de
    ;; los dos extremos" (ahi la cota se digita). La rasante se arma con
    ;; los mismos records de siempre, asi que todo lo que viene despues
    ;; -- movimiento de tierras, memoria, exportacion -- no cambia.
    ((and *urb-road-picked-cotas*
          (= (length *urb-road-picked-cotas*) 1)
          (numberp *urb-road-picked-slope*))
      (setq c0 (car *urb-road-picked-cotas*)
            c1 (urb:cota-por-pendiente c0 *urb-road-picked-slope* span)
            records (list (list 0.0 c0) (list span c1)))))
  ;; 5.7.2: fuentes de las cotas (pozo / via / texto / digitada) en
  ;; abscisa LOCAL, para que el PERFIL las dibuje
  (if records
    (progn
      (setq src nil)
      (if (and *urb-road-picked-stations* *urb-road-picked-sources*)
        (foreach item *urb-road-picked-sources*
          (setq src (cons (list (if (urb:string-equal-p direction "Final")
                                  (- (+ axis-start span) (car item))
                                  (- (car item) axis-start))
                                (nth 1 item) (nth 2 item) (nth 3 item))
                          src)))
        (if *urb-road-picks-raw*
          (progn
            (setq k 0)
            (foreach item *urb-road-picks-raw*
              (if (and (< k 2) (> (length item) 2))
                (setq src (cons (list (if (= k 0) 0.0 span) (car item) (nth 2 item) (nth 3 item)) src)))
              (setq k (1+ k))))))
      (vl-catch-all-apply 'vlax-ldata-put
        (list boundary "URB_VIA_RASANTE_SRC" (reverse src)))))
  (setq *urb-road-picks-raw* nil *urb-road-picked-sources* nil)
  (if records
    (progn
      (vlax-ldata-put boundary "URB_VIA_RASANTE_FULL" records)
      (setq data (urb:get-xdata-strings boundary "URB_VIA"))
      (while (< (length data) 33)
        (setq data (append data (list ""))))
      (setq data (urb:replace-nth 30 (rtos c0 2 8) data)
            data (urb:replace-nth 31 (rtos c1 2 8) data)
            data (urb:replace-nth 32 (urb:serialize-lisp
              (urb:compact-road-grade-samples
                (mapcar '(lambda (r) (list (car r) nil (cadr r))) records))) data))
      (urb:set-xdata-strings boundary "URB_VIA" data)))
  records
)

(defun urb:set-road-status (boundary status / data)
  (setq data (urb:get-xdata-strings boundary "URB_VIA"))
  (if (and data (> (length data) 19))
    (urb:set-xdata-strings boundary "URB_VIA"
      (urb:replace-nth 19 status data)))
  status
)

(defun urb:create-road
  (/ dialog axis auto-axis direction surface cota-info boundary obj area range
   axis-start axis-length handle label start interval data status picks
   memory-data packaged-data memoria-result via-id block-ref doc undo-open
   undo-result *error*)
  (setq doc (urb:doc))
  (defun *error* (message)
    ;; limpiar TAMBIEN los globales del flujo: si un error corta la
    ;; creacion, unas cotas/estaciones viejas no deben contaminar la
    ;; siguiente via (2026-08-11 v2)
    (setq *urb-road-picked-cotas* nil)
    (setq *urb-road-picked-stations* nil)
    (setq *urb-road-picked-slope* nil)
    (setq *urb-road-end-edges* nil)
    (if undo-open
      (progn
        (vl-catch-all-apply 'vla-EndUndoMark (list doc))
        (setq undo-open nil)))
    (if (and message
             (not (member message '("Function cancelled" "quit / exit abort"))))
      (prompt (strcat "\nERROR AL CREAR VIA: " message)))
    (princ))
  (setq undo-result
    (vl-catch-all-apply 'vla-StartUndoMark (list doc)))
  (setq undo-open (not (vl-catch-all-error-p undo-result)))
  (setq dialog
    (if (urb:confirm-meter-units)
      (urb:dialog-road nil)
      nil))
  (if dialog
    (progn
      (if (urb:road-name-exists-p (nth 0 dialog))
        (prompt
          (strcat "\nAVISO: ya existe una via llamada "
            (urb:safe-string (nth 0 dialog) "")
            " en este dibujo. Considere un nombre distinto para no"
            " confundir memorias y presupuesto.")))
      ;; 2026-08-11: con alineamiento "Nuevo" ya NO se dibuja el eje antes
      ;; del contorno -- se dibuja el contorno primero y el eje central se
      ;; calcula solo (urb:road-axis-from-boundary); si el contorno no lo
      ;; permite (mas de 4 vertices o arcos), se dibuja a mano como antes.
      (setq auto-axis (urb:string-equal-p (nth 4 dialog) "Nuevo"))
      (setq axis
        (if auto-axis T (urb:select-or-draw-road-axis (nth 4 dialog))))
      (if axis
        (progn
          ;; 2026-08-11 v3: flujo REORDENADO a pedido del usuario ("esta
          ;; largo y no tiene orden"): 1) contorno, 2) eje, 3) sentido,
          ;; 4) superficie y cotas. Antes el sentido del abscisado y la
          ;; referencia de cotas se preguntaban antes de dibujar nada.
          (setq boundary (urb:draw-road-boundary))
          (if (and boundary auto-axis)
            (progn
              (setq axis (urb:road-axis-from-boundary boundary))
              (if axis (setq axis (urb:confirm-auto-axis boundary axis)))
              (if axis
                (prompt "\nEje central calculado automaticamente del contorno.")
                (progn
                  (prompt
                    "\nNo se pudo calcular el eje central de este contorno.")
                  (setq axis (urb:select-or-draw-road-axis "Nuevo"))))))
          (if (and boundary (not (and axis (urb:curve-entity-p axis))))
            (progn
              (prompt "\nSin eje valido; via cancelada.")
              (setq boundary nil)))
          (if boundary
            (progn
              (setq direction (urb:road-axis-direction))
              (setq surface (urb:resolve-road-surface (nth 5 dialog)))
              (setq cota-info (urb:road-cota-reference (nth 6 dialog)))
              ;; modo Pendiente: PRIMERO el poligono (ya dibujado), y AHORA
              ;; las cotas -- 2 = pendiente lineal inicial/final; 3 o mas =
              ;; rasante por tramos proyectando cada clic sobre el eje
              (setq *urb-road-picked-cotas* nil)
              (setq *urb-road-picked-stations* nil)
              (setq *urb-road-picked-slope* nil)
              (setq picks nil)
              (if (urb:string-equal-p (nth 6 dialog) "Pendiente")
                (setq picks (urb:pick-road-cotas)))
              ;; auto-detect en "Textos por capa": el primer clic fue una
              ;; via creada o una etiqueta -> mismo camino que Pendiente
              (if (urb:string-equal-p
                    (urb:safe-string (car cota-info) "") "PICKED")
                (progn
                  (setq picks (cadr cota-info))
                  (setq cota-info (list "" "0" "PENDIENTE"))))
              (cond
                ((null picks) nil)
                ;; una sola cota: se completa con la pendiente (v4.87)
                ((= (length picks) 1)
                  (setq *urb-road-picked-cotas* (mapcar 'car picks)))
                ((urb:picks-have-locations-p picks)
                  (setq *urb-road-picked-stations*
                    (urb:picked-cotas-to-stations picks axis))
                  (prompt
                    (strcat "\nRasante por tramos con "
                      (itoa (length *urb-road-picked-stations*))
                      " cotas proyectadas sobre el eje.")))
                (T
                  (setq *urb-road-picked-cotas* (mapcar 'car picks))))
              (setq obj (vlax-ename->vla-object boundary))
              (setq area (vla-get-Area obj))
              ;; El eje puede ser mas largo que esta via (compartido entre
              ;; varias); axis-start/axis-length se detectan solos
              ;; proyectando el contorno recien dibujado sobre el eje.
              (setq range (urb:axis-range-for-boundary axis boundary))
              (if range
                (progn
                  (setq axis-start (car range))
                  (setq axis-length (cadr range)))
                (progn
                  (prompt
                    (strcat
                      "\nNo se pudo ubicar el contorno sobre el eje;"
                      " se usara el eje completo."))
                  (setq axis-start 0.0)
                  (setq axis-length
                    (vlax-curve-getDistAtParam axis (vlax-curve-getEndParam axis)))))
              (if (<= axis-length 0.01)
                (prompt
                  "\nEl contorno dibujado no genera un tramo valido sobre el eje.")
                (progn
                  (setq handle (vla-get-Handle obj))
                  ;; via-id: identificador estable de esta via (ver nota en
                  ;; urb:set-road-data) usado como llave de la cache de eje,
                  ;; en vez del handle (que cambiara cada vez que se edite).
                  (setq via-id (strcat handle "-" (itoa (getvar "MILLISECS"))))
                  (urb:cache-road-axis via-id axis)
                  (setq label (urb:prompt-station-start (urb:format-station axis-start)))
                  (setq start (urb:station-number label))
                  (setq interval (atof (nth 8 dialog)))
                  (setq status
                    (if (and (not (urb:string-equal-p surface "NO SELECCIONADA"))
                             (urb:string-equal-p (nth 2 cota-info) "DETECTADAS"))
                      "DATOS PRELIMINARES" "MOVIMIENTO DE TIERRAS PENDIENTE"))
                  (vl-catch-all-apply
                    'urb:set-xdata-strings
                    (list axis "URB_VIA_EJE" (list handle via-id)))
                  (urb:set-road-data boundary
                    (nth 0 dialog) (nth 1 dialog) (nth 2 dialog) (nth 3 dialog)
                    (vla-get-Handle (vlax-ename->vla-object axis))
                    surface (nth 6 dialog) (nth 0 cota-info) (nth 1 cota-info)
                    label (nth 8 dialog) direction (nth 9 dialog)
                    (nth 10 dialog) (nth 11 dialog) (nth 12 dialog)
                    (rtos area 2 6) (rtos axis-length 2 6) status (nth 4 dialog)
                    (rtos axis-start 2 6) via-id)
                  (urb:store-selected-road-grade
                    boundary axis-start axis-length direction)
                  (urb:generate-road-stations
                    axis handle start interval direction axis-start axis-length)
                  ;; Calculo automatico e integrado: si hay superficie y cotas
                  ;; de proyecto (o el usuario las digita), queda listo sin
                  ;; comandos adicionales.
                  ;; compute-road-earthworks guarda estado y movimiento en
                  ;; una sola escritura de URB_VIA.
                  (if (urb:try-road-earthworks boundary axis)
                    (setq status "MOVIMIENTO DE TIERRAS CALCULADO"))
                  ;; Representacion grafica ligera: eje dentro del bloque y
                  ;; hatch amarillo transparente. Los datos quedan solo en
                  ;; Propiedades, sin texto superpuesto a la calzada.
                  (urb:create-road-axis-display boundary axis)
                  (urb:create-road-display-hatch boundary)
                  ;; Sardineles a los costados (2026-08-11): antes de
                  ;; empaquetar, con el contorno todavia como polilinea.
                  (urb:create-road-sardineles
                    boundary (nth 1 dialog) (nth 2 dialog))
                  ;; Contorno + abscisado quedan empacados en un bloque con
                  ;; atributos invisibles: los datos calculados se ven en el
                  ;; panel Properties con solo seleccionar la via, sin correr
                  ;; ningun comando adicional (mismo patron que anden).
                  ;; 2026-08-12: la xdata se lee ANTES de empaquetar y se
                  ;; usa de respaldo -- en vivo el usuario recibio el aviso
                  ;; "etapa areas-17 | data: nil": tras empaquetar, la
                  ;; relectura sobre el bloque devolvio nil y la memoria
                  ;; se armaba con data vacia.
                  (setq data (urb:get-xdata-strings boundary "URB_VIA"))
                  ;; Copia estable para la alerta final. AutoLISP usa
                  ;; alcance dinamico y una llamada profunda puede reutilizar
                  ;; el simbolo DATA; en vivo eso dejo DATA=T aunque la XDATA
                  ;; del bloque si estaba bien guardada.
                  (if (and (listp data) (> (length data) 18))
                    (setq memory-data (mapcar '(lambda (item) item) data)))
                  (setq block-ref (urb:package-road boundary))
                  ;; or de AutoLISP devuelve T, no el valor -- con or,
                  ;; boundary quedaba en T y la memoria se armaba con
                  ;; data ilegible (el famoso aviso "areas-17 | data: nil")
                  (if (urb:as-ename block-ref)
                    (setq boundary (urb:as-ename block-ref)))
                  (setq packaged-data
                    (urb:get-xdata-strings boundary "URB_VIA"))
                  (if (and (listp packaged-data)
                           (> (length packaged-data) 18))
                    (setq memory-data packaged-data))
                  (vla-Regen (urb:doc) 1)
                  ;; blindado (2026-08-11 v2): un fallo al ARMAR la memoria
                  ;; no debe abortar la creacion (la via ya existe completa
                  ;; en este punto) -- el usuario reporto "bad argument
                  ;; type: consp nil" justo aqui y perdia el cierre limpio.
                  (setq memoria-result
                    (if (and (listp memory-data)
                             (> (length memory-data) 18))
                      (vl-catch-all-apply
                        '(lambda ()
                           (strcat
                             (urb:road-memory-from-data boundary memory-data)
                             "\n\nEstado: " status)))
                      nil))
                  (if (or (null memoria-result)
                          (vl-catch-all-error-p memoria-result))
                    (progn
                      (prompt
                        (strcat
                          "\nAviso: la via quedo creada pero no se pudo armar la memoria: "
                          (if (vl-catch-all-error-p memoria-result)
                            (vl-catch-all-error-message memoria-result)
                            "datos URB_VIA incompletos")
                          " | etapa memoria: "
                          (urb:safe-string
                            (if (boundp '*urb-memoria-stage*)
                              *urb-memoria-stage* nil)
                            "desconocida")
                          " | data: "
                          (urb:safe-string
                            (vl-catch-all-apply
                              '(lambda ()
                                 (substr
                                   (vl-princ-to-string memory-data) 1 180)))
                            "(ilegible)")))
                      (alert (strcat "Via creada.\n\nEstado: " status)))
                    (alert memoria-result))))))))))
  (setq *urb-road-picked-cotas* nil)
  (setq *urb-road-picked-stations* nil)
  (setq *urb-road-picked-slope* nil)
  (setq *urb-road-end-edges* nil)
  (if undo-open
    (progn
      (vl-catch-all-apply 'vla-EndUndoMark (list doc))
      (setq undo-open nil)))
  (princ))

(defun urb:road-parent-from-entity (ename / data generated parent parent-data)
  (cond
    ((and
       (setq data (urb:get-xdata-strings ename "URB_VIA"))
       (urb:string-equal-p (car data) "VIA"))
      ename)
    ((setq generated (urb:get-xdata-strings ename "URB_VIA_GEN"))
      (setq parent
        (if (/= (urb:safe-string (car generated) "") "")
          (handent (car generated))
          nil))
      (setq parent-data
        (if parent (urb:get-xdata-strings parent "URB_VIA") nil))
      (if (and parent-data (urb:string-equal-p (car parent-data) "VIA"))
        parent
        nil))
    (T nil)))

(defun urb:selected-roads (selection / index ename parent result)
  (setq index 0)
  (if selection
    (repeat (sslength selection)
      (setq ename (ssname selection index))
      (setq parent (urb:road-parent-from-entity ename))
      (if (and parent (not (member parent result)))
        (setq result (cons parent result)))
      (setq index (1+ index))))
  (reverse result))

(defun urb:edit-road
  (boundary / old dialog axis surface data obj area range axis-start
   axis-length label start interval handle via-id block-ref original-block
   edit-completed cota-info picks cota-capa cota-textos old-axis axis-choice
   owned-axis axis-changed)
  ;; Si la via ya esta empacada en un bloque (atributos visibles en
  ;; Properties), se desempaca primero: se recupera el contorno crudo
  ;; con su xdata intacta y se sigue el mismo flujo de siempre; al
  ;; final se vuelve a empacar con los datos nuevos.
  (if (urb:road-block-p boundary)
    (progn
      ;; Se conserva la referencia anterior hasta que el bloque nuevo haya
      ;; sido creado correctamente. vla-Explode NO elimina el bloque origen.
      (setq original-block boundary)
      (setq boundary (urb:explode-road-block-boundary boundary))))
  (if (not boundary)
    (prompt "\nNo se pudo desempacar el bloque de la via.")
    (progn
      (setq old (urb:get-xdata-strings boundary "URB_VIA"))
      (if old
        (progn
          (setq dialog (urb:dialog-road (urb:road-data-defaults old)))
          (if dialog
            (progn
              ;; via-id: identificador estable de esta via que sobrevive
              ;; al empacado/desempacado en bloque (a diferencia del
              ;; handle, que cambia cada vez que se explota y se vuelve a
              ;; crear la referencia). Se usa como llave de la cache de eje.
              (setq via-id
                (if (and (> (length old) 22) (/= (nth 22 old) ""))
                  (nth 22 old)
                  (strcat
                    (vla-get-Handle (vlax-ename->vla-object boundary))
                    "-" (itoa (getvar "MILLISECS")))))
              (setq axis (handent (nth 5 old)))
              ;; Si el eje vive en un xref, handent nunca lo resuelve; se
              ;; intenta primero la cache de sesion (misma via, mismo eje de
              ;; la ultima vez) antes de pedirle al usuario que lo seleccione
              ;; de nuevo.
              (if (not axis)
                (setq axis (urb:cached-road-axis via-id)))
              (setq old-axis axis)
              (if axis
                (progn
                  (initget "Conservar Recalcular Seleccionar")
                  (setq axis-choice (getkword
                    "\nEje de la via [Conservar/Recalcular/Seleccionar] <Conservar>: "))
                  (cond
                    ((= axis-choice "Recalcular")
                      (setq axis (urb:road-axis-from-boundary boundary))
                      (if axis (setq axis (urb:confirm-auto-axis boundary axis)))
                      (setq owned-axis axis))
                    ((= axis-choice "Seleccionar")
                      (setq axis (urb:select-or-draw-road-axis "Existente"))))))
              (if (not axis)
                (if (not old-axis)
                  (setq axis (urb:select-or-draw-road-axis (nth 4 dialog)))))
              (setq axis-changed (and axis (not (equal axis old-axis))))
              (if axis-changed
                (progn
                  ;; La rasante antigua esta en abscisas del eje antiguo.
                  ;; No trasladarla silenciosamente al nuevo recorrido.
                  (setq *urb-road-picked-cotas* nil *urb-road-picked-stations* nil
                        *urb-road-picked-slope* nil *urb-road-picked-sources* nil
                        *urb-road-picks-raw* nil)
                  (if (not (urb:string-equal-p (nth 6 dialog) "Textos por capa"))
                    (progn
                      (prompt "\nEje cambiado: vuelva a definir las cotas de rasante para este recorrido.")
                      (setq picks (urb:pick-road-cotas))
                      (cond
                        ((or (>= (length picks) 2)
                             (and (= (length picks) 1) (numberp *urb-road-picked-slope*)))
                          (if (urb:picks-have-locations-p picks)
                            (setq *urb-road-picked-stations* (urb:picked-cotas-to-stations picks axis))
                            (setq *urb-road-picked-cotas* (mapcar 'car picks))))
                        (T (setq axis nil)
                           (prompt "\nSin rasante nueva: no se reemplaza la via.")))))
                  (if axis
                    (progn
                      (urb:invalidate-road-movement boundary T "PENDIENTE: EJE CAMBIADO")
                      (setq old (urb:get-xdata-strings boundary "URB_VIA"))))))
              (if axis
                (progn
                  (setq surface (urb:resolve-road-surface (nth 5 dialog)))
                  ;; 2026-09-12 (reporte del usuario: "si elijo la opcion de
                  ;; texto por capas me reconoce todas las capas del
                  ;; alineamiento, pero al momento de edicion de movimiento
                  ;; de tierras me pone como si lo fuera a calcular por
                  ;; pendiente"). Al EDITAR una via que YA tenia el modo
                  ;; "Textos por capa" se volvia a pedir el texto de cota
                  ;; siempre, y ahi pasaba lo del reporte: si el clic no caia
                  ;; exactamente en un TEXT/MTEXT -- una etiqueta Civil 3D,
                  ;; el bloque de una via ya creada, un proxy -- el
                  ;; auto-detect cambiaba el metodo a cotas seleccionadas, o
                  ;; sea al flujo de PENDIENTE. De paso
                  ;; urb:clear-cota-calibration borraba la calibracion de la
                  ;; capa que ya estaba validada contra el eje.
                  ;; Ahora la capa guardada (indice 8) se REUSA -- solo se
                  ;; vuelven a contar sus textos, que es lo que puede haber
                  ;; cambiado -- y la calibracion persistida en el dibujo
                  ;; (urb:cota-calib-key) se aprovecha tal cual. Solo se
                  ;; vuelve a preguntar si no hay capa guardada o si el
                  ;; usuario acaba de cambiar el metodo en la ventana.
                  (setq cota-capa (urb:safe-string (nth 8 old) ""))
                  (setq cota-info
                    (cond
                      ((not (urb:string-equal-p (nth 6 dialog) "Textos por capa"))
                        (list (nth 8 old) (nth 9 old) "DETECTADAS"))
                      ((not (urb:road-cota-capa-reusable-p
                              (nth 6 dialog) (nth 7 old) cota-capa))
                        (urb:road-cota-reference (nth 6 dialog)))
                      (T
                        (setq cota-textos
                          (vl-catch-all-apply 'urb:collect-cota-texts
                            (list cota-capa)))
                        (if (vl-catch-all-error-p cota-textos)
                          (setq cota-textos nil))
                        (prompt
                          (strcat "\nCotas por capa " cota-capa ": "
                            (itoa (length cota-textos))
                            " textos (se conserva la capa y su calibracion;"
                            " no hay que volver a marcarla)."))
                        (list cota-capa (itoa (length cota-textos))
                          (if cota-textos "DETECTADAS" "PENDIENTE")))))
                  ;; auto-detect: el primer clic fue una via creada o una
                  ;; etiqueta -> cotas seleccionadas (como modo Pendiente)
                  (if (urb:string-equal-p
                        (urb:safe-string (car cota-info) "") "PICKED")
                    (progn
                      (setq *urb-road-picked-cotas* nil
                            *urb-road-picked-stations* nil
                            *urb-road-picked-slope* nil)
                      (if (urb:picks-have-locations-p (cadr cota-info))
                        (setq *urb-road-picked-stations*
                          (urb:picked-cotas-to-stations
                            (cadr cota-info) axis))
                        (setq *urb-road-picked-cotas*
                          (mapcar 'car (cadr cota-info))))
                      (setq cota-info (list "" "0" "PENDIENTE"))))
                  (setq obj (vlax-ename->vla-object boundary))
                  (setq area (vla-get-Area obj))
                  ;; Se reproyecta el contorno (sin cambios) sobre el eje por
                  ;; si este se volvio a seleccionar durante la edicion.
                  (setq range (urb:axis-range-for-boundary axis boundary))
                  (if range
                    (progn
                      (setq axis-start (car range))
                      (setq axis-length (cadr range)))
                    (progn
                      (prompt
                        (strcat
                          "\nNo se pudo ubicar el contorno sobre el eje;"
                          " se usara el eje completo."))
                      (setq axis-start 0.0)
                      (setq axis-length
                        (vlax-curve-getDistAtParam axis (vlax-curve-getEndParam axis)))))
                  (if (<= axis-length 0.01)
                    (prompt
                      "\nEl contorno de la via no genera un tramo valido sobre el eje.")
                    (progn
                      (setq handle (vla-get-Handle obj))
                      (vl-catch-all-apply
                        'urb:set-xdata-strings
                        (list axis "URB_VIA_EJE" (list handle via-id)))
                      (urb:delete-road-generated handle)
                      (setq label
                        (urb:prompt-station-start
                          (urb:safe-string (nth 10 old) (urb:format-station axis-start))))
                      (setq start (urb:station-number label))
                      (urb:set-road-data boundary
                        (nth 0 dialog) (nth 1 dialog) (nth 2 dialog) (nth 3 dialog)
                        (vla-get-Handle (vlax-ename->vla-object axis))
                        surface (nth 6 dialog) (nth 0 cota-info) (nth 1 cota-info)
                        label (nth 8 dialog) (nth 12 old) (nth 9 dialog)
                        (nth 10 dialog) (nth 11 dialog) (nth 12 dialog)
                        (rtos area 2 6) (rtos axis-length 2 6) (nth 19 old)
                        (nth 4 dialog) (rtos axis-start 2 6) via-id)
                      ;; 2026-09-10 (pedido del usuario): despues de aceptar
                      ;; la ventana se puede rehacer la rasante. Con Enter
                      ;; (No) la edicion sigue exactamente como antes.
                      ;; 2026-09-12: esta pregunta llamaba SIEMPRE al selector
                      ;; de cotas del modo Pendiente, aunque la via este
                      ;; configurada con "Textos por capa" -- la otra mitad
                      ;; del reporte ("al momento de edicion de movimiento de
                      ;; tierras me pone como si lo fuera a calcular por
                      ;; pendiente"). Ahora cada metodo rehace lo suyo: por
                      ;; capa se vuelve a marcar LA CAPA de cotas (y se
                      ;; recalibra contra el eje), por pendiente se vuelven a
                      ;; tomar las cotas como antes.
                      (if (and (not axis-changed) (urb:ask-edit-movimiento "la via"))
                        (if (urb:string-equal-p (nth 6 dialog) "Textos por capa")
                          (progn
                            (setq cota-info
                              (urb:road-cota-reference (nth 6 dialog)))
                            (if (urb:string-equal-p
                                  (urb:safe-string (car cota-info) "") "PICKED")
                              (progn
                                (setq *urb-road-picked-cotas* nil
                                      *urb-road-picked-stations* nil
                                      *urb-road-picked-slope* nil)
                                (if (urb:picks-have-locations-p (cadr cota-info))
                                  (setq *urb-road-picked-stations*
                                    (urb:picked-cotas-to-stations
                                      (cadr cota-info) axis))
                                  (setq *urb-road-picked-cotas*
                                    (mapcar 'car (cadr cota-info))))
                                (setq cota-info (list "" "0" "PENDIENTE"))))
                            ;; la capa nueva (o la rasante marcada) tiene que
                            ;; quedar guardada: se reescribe la xdata
                            (urb:set-road-data boundary
                              (nth 0 dialog) (nth 1 dialog) (nth 2 dialog) (nth 3 dialog)
                              (vla-get-Handle (vlax-ename->vla-object axis))
                              surface (nth 6 dialog) (nth 0 cota-info) (nth 1 cota-info)
                              label (nth 8 dialog) (nth 12 old) (nth 9 dialog)
                              (nth 10 dialog) (nth 11 dialog) (nth 12 dialog)
                              (rtos area 2 6) (rtos axis-length 2 6) (nth 19 old)
                              (nth 4 dialog) (rtos axis-start 2 6) via-id))
                          (progn
                            (setq picks (urb:pick-road-cotas))
                            (cond
                              ((null picks) nil)
                              ((urb:picks-have-locations-p picks)
                                (setq *urb-road-picked-cotas* nil)
                                (setq *urb-road-picked-stations*
                                  (urb:picked-cotas-to-stations picks axis)))
                              (T
                                (setq *urb-road-picked-stations* nil)
                                (setq *urb-road-picked-cotas* (mapcar 'car picks)))))))
                      (urb:store-selected-road-grade
                        boundary axis-start axis-length (nth 12 old))
                      (setq interval (atof (nth 8 dialog)))
                      (urb:generate-road-stations
                        axis handle start interval (nth 12 old)
                        axis-start axis-length)
                      ;; Recalcula el movimiento de tierras si la edicion agrego o
                      ;; cambio la superficie/cotas; si aun falta informacion,
                      ;; queda como estaba (no interrumpe la edicion).
                      ;; El calculo guarda estado y movimiento juntos.
                      (urb:try-road-earthworks boundary axis)
                      ;; Regenera el resumen visible con los datos editados.
                      (urb:create-road-axis-display boundary axis)
                      (urb:create-road-display-hatch boundary)
                      ;; Empaqueta de nuevo en un bloque con atributos: los
                      ;; datos recalculados quedan visibles en Properties
                      ;; con solo seleccionar la via, sin correr comandos.
                      (setq block-ref (urb:package-road boundary))
                      (if (and block-ref original-block)
                        (urb:copy-quantity-scope original-block block-ref))
                      (if block-ref
                        (if (and original-block
                                 (not (urb:delete-anden-block original-block)))
                          (progn
                            ;; Si la referencia anterior no se puede borrar,
                            ;; se descarta la nueva para no duplicar la via.
                            (urb:delete-anden-block (urb:as-ename block-ref))
                            (setq block-ref nil boundary nil)
                            (prompt
                              "\nNo se pudo reemplazar la via anterior; se conservo intacta."))
                          (progn
                            (setq edit-completed T)
                            (urb:cache-road-axis via-id axis)
                            (setq boundary (urb:as-ename block-ref))
                            (vla-Regen (urb:doc) 1)
                            (alert (urb:road-memory-from-data boundary
                              (urb:get-xdata-strings boundary "URB_VIA")))))
                        (progn
                          ;; Si el empaquetado falla, se descarta la copia de
                          ;; trabajo y se mantiene intacto el bloque anterior.
                          (urb:delete-road-generated handle)
                          (urb:safe-delete obj)
                          (prompt
                            "\nNo se pudo actualizar la via; se conservo el bloque anterior.")))))))))))))
  ;; Si se cancelo el dialogo o no se pudo resolver el eje, elimina
  ;; solamente la copia de trabajo producida por Explode. El bloque
  ;; original permanece intacto y no aparecen vias superpuestas.
  (if (and original-block boundary (not edit-completed))
    (progn
      (setq obj
        (vl-catch-all-apply 'vlax-ename->vla-object (list boundary)))
      (if (not (vl-catch-all-error-p obj)) (urb:safe-delete obj))))
  (if (and owned-axis (not edit-completed) (entget owned-axis))
    (entdel owned-axis))
  (princ))

;; Si el usuario ya tiene la via seleccionada (un clic selecciona todo
;; el grupo: contorno + abscisado), se usa esa seleccion directamente
;; en vez de pedirle que vuelva a hacer clic.
(defun urb:road-quantity-command (/ ss ename boundary data)
  (setq ss (ssget "_I"))
  (setq ename
    (if (and ss (> (sslength ss) 0))
      (ssname ss 0)
      (car (entsel "\nSeleccione el contorno o una abscisa de la via: "))))
  (if (and ename (setq boundary (urb:road-parent-from-entity ename)))
    (progn
      (setq data (urb:get-xdata-strings boundary "URB_VIA"))
      (alert (strcat (urb:road-memory-from-data boundary data)
        "\n\nEtapa: " (nth 2 data) " | Subetapa: " (nth 3 data)
        "\nSuperficie: " (nth 6 data)
        "\nEstado: " (nth 19 data))))
    (prompt "\nEl objeto seleccionado no pertenece a una via cuantificable."))
  (princ))

;; ============================================================
;; MOVIMIENTO DE TIERRAS INTEGRADO (4.1.0)
;; Se calcula automaticamente al crear o editar la via y queda
;; guardado dentro de URB_VIA (la memoria de via lo muestra).
;; Metodo de areas extremas: terreno muestreado en 7 ordenadas
;; por abscisa con FindElevationAtXY; rasante
;; tomada de los textos de cota de proyecto (el texto numerico
;; mas cercano a cada abscisa) o, si no alcanzan, cota inicial
;; + pendiente digitadas. Resultado aproximado para presupuesto;
;; el definitivo se obtiene en Civil 3D con corredor + superficie
;; de volumen. Se calcula solo, dentro de crear/editar via.
;; ============================================================

(defun urb:cache-surface-object (name object / key old)
  (setq key (strcase (urb:safe-string name "")))
  (if (and (/= key "") (urb:valid-vla-object-p object))
    (progn
      (if (setq old (assoc key *urb-surface-cache*))
        (setq *urb-surface-cache*
          (subst (cons key object) old *urb-surface-cache*))
        (setq *urb-surface-cache*
          (cons (cons key object) *urb-surface-cache*)))))
  object
)

(defun urb:surface-object-by-name (name / cached ss index ename obj found result)
  (setq cached (cdr (assoc (strcase (urb:safe-string name ""))
                           *urb-surface-cache*)))
  (if (urb:valid-vla-object-p cached) (setq found cached))
  (setq ss
    (if (not found)
      (ssget "_X"
        '((0 . "AECC_TIN_SURFACE,AECC_GRID_SURFACE,AECC_TIN_VOLUME_SURFACE")))))
  (if (and ss (not found))
    (progn
      (setq index 0)
      (while (and (< index (sslength ss)) (not found))
        (setq ename (ssname ss index))
        (setq obj (vlax-ename->vla-object ename))
        (setq result (vl-catch-all-apply 'vla-get-Name (list obj)))
        (if (and (not (vl-catch-all-error-p result))
                 (urb:string-equal-p result name))
          (setq found (urb:cache-surface-object name obj)))
        (setq index (1+ index)))))
  found
)

(defun urb:select-surface-object (stored-name / obj selected result)
  (if (and stored-name
           (/= stored-name "")
           (not (urb:string-equal-p stored-name "NO SELECCIONADA"))
           (not (urb:string-equal-p stored-name "Seleccionar en dibujo")))
    (setq obj (urb:surface-object-by-name stored-name)))
  (if obj
    (prompt
      (strcat "\nSuperficie seleccionada: "
        (urb:safe-string stored-name "")))
    (progn
      ;; nentsel (no entsel) para poder tomar una superficie anidada en un xref.
      (setq selected
        (nentsel "\nSeleccione la superficie topografica de Civil 3D: "))
      (if selected
        (progn
          (setq result
            (vl-catch-all-apply
              'vlax-ename->vla-object
              (list (car selected))))
          (if (not (vl-catch-all-error-p result))
            (progn
              (setq obj result)
              (urb:cache-surface-object
                (urb:safe-string
                  (vl-catch-all-apply 'vla-get-Name (list obj))
                  stored-name)
                obj)
              (if (/= (urb:safe-string stored-name "") "")
                (urb:cache-surface-object stored-name obj))))))))
  obj
)

;; 2026-09-12 (plano real URB_MASTER_GENERAL): SUP_TN tenia un punto con
;; cota 60,84 m -- medido en (83642, 96236) -- en un terreno cuya media es
;; 2.565,91. Con el estilo "Contours 2m" eso dibuja 1.252 curvas de nivel
;; concentricas (el "circulo" que reporto el usuario) y, mas grave, si un
;; elemento cae sobre esos triangulos su movimiento de tierras sale
;; absurdo SIN avisar. Aqui no se corrige la superficie -- no es del
;; plugin -- pero si se AVISA una vez por dibujo en cuanto una lectura se
;; sale del rango del resto.
(setq *urb-surface-ref-z* nil)
(setq *urb-surface-aviso* nil)

(defun urb:surface-elevation (surface x y / result)
  (setq result
    (vl-catch-all-apply
      'vlax-invoke
      (list surface 'FindElevationAtXY x y)))
  (if (vl-catch-all-error-p result)
    nil
    (progn
      (if (numberp result)
        (progn
          (if (null *urb-surface-ref-z*) (setq *urb-surface-ref-z* result))
          (if (and (not *urb-surface-aviso*)
                   (> (abs (- result *urb-surface-ref-z*)) 100.0))
            (progn
              (setq *urb-surface-aviso* T)
              (prompt
                (strcat "\nAVISO: la superficie devuelve cotas incoherentes ("
                  (rtos *urb-surface-ref-z* 2 2) " y " (rtos result 2 2)
                  " m). Tiene puntos malos: revise sus curvas de nivel antes"
                  " de confiar en el movimiento de tierras."))))))
      result))
)

(defun urb:road-profile-depth (profile-name / profile total layer)
  (setq profile (urb:road-profile-by-name profile-name))
  (setq total 0.0)
  (foreach layer (if profile (cadr profile) nil)
    (if (urb:string-equal-p (nth 1 layer) "Volumen")
      (setq total (+ total (atof (nth 2 layer))))))
  total
)

(defun urb:collect-local-cota-texts (layer / ss index ename edata content value point source-id result)
  (setq ss
    (ssget "_X"
      (list '(0 . "TEXT,MTEXT") (cons 8 layer))))
  (if ss
    (progn
      (setq index 0)
      (repeat (sslength ss)
        (setq ename (ssname ss index))
        (setq edata (entget ename))
        (setq content (urb:safe-string (cdr (assoc 1 edata)) ""))
        (setq value (urb:parse-real content))
        (setq point (cdr (assoc 10 edata)))
        (setq source-id (urb:safe-string (cdr (assoc 5 edata)) "LOCAL"))
        (if (and (numberp value) (> value 0.0) point)
          (setq result (cons (list point value source-id) result)))
        (setq index (1+ index)))))
  result
)

;; ssget nunca alcanza contenido anidado en un xref, asi que para capas
;; con el patron "XREF|CAPA" (como entget las reporta) hay que ir por el
;; xref manualmente: localizar su INSERT en el dibujo actual (eso si es
;; un objeto de primer nivel, ssget lo encuentra bien), leer su punto de
;; insercion/rotacion/escala, y recorrer la DEFINICION del bloque del
;; xref (vlax-for si perfora dentro) buscando los textos de esa capa,
;; transformando cada punto local a coordenadas reales del dibujo.
(defun urb:xref-insert-transform (xref-name / ss ename obj)
  (setq ss (ssget "_X" (list '(0 . "INSERT") (cons 2 xref-name))))
  (if (and ss (> (sslength ss) 0))
    (progn
      (setq ename (ssname ss 0))
      (setq obj (vlax-ename->vla-object ename))
      (list
        (vlax-get obj 'InsertionPoint)
        (vla-get-Rotation obj)
        (vla-get-XScaleFactor obj)
        (vla-get-YScaleFactor obj)
        (vla-get-ZScaleFactor obj)))
    nil)
)

;; Un mismo XREF puede estar insertado mas de una vez o existir tambien
;; en una presentacion. La version anterior tomaba siempre el primer INSERT
;; encontrado por ssget; si ese no era el que el usuario estaba viendo, las
;; 2641 cotas se transformaban con una insercion equivocada y ninguna quedaba
;; cerca del eje. Se devuelven todas las transformaciones y la proyeccion
;; posterior conserva automaticamente solo la instancia cercana al tramo.
(defun urb:xref-insert-transforms
  (xref-name / ss index ename obj transform result)
  (setq ss (ssget "_X" (list '(0 . "INSERT") (cons 2 xref-name))))
  (if ss
    (progn
      (setq index 0)
      (while (< index (sslength ss))
        (setq ename (ssname ss index))
        (setq obj
          (vl-catch-all-apply 'vlax-ename->vla-object (list ename)))
        (if (not (vl-catch-all-error-p obj))
          (progn
            (setq transform
              (vl-catch-all-apply 'urb:block-instance-transform (list obj)))
            (if (not (vl-catch-all-error-p transform))
              (setq result (cons transform result)))))
        (setq index (1+ index)))))
  (reverse result)
)

(defun urb:point3d-list (value / raw x y z tail tail2)
  (cond
    ((= (type value) 'VARIANT)
      (setq raw (vlax-variant-value value))
      (if (= (type raw) 'SAFEARRAY)
        (setq value (vlax-safearray->list raw))
        (setq value raw)))
    ((= (type value) 'SAFEARRAY)
      (setq value (vlax-safearray->list value))))
  ;; Admite tanto listas normales (x y z)/(x y) como pares punteados
  ;; devueltos por algunos proxies Civil 3D: (x . y).
  (if (= (type value) 'LIST)
    (progn
      (setq x (car value))
      (setq tail (cdr value))
      (cond
        ((numberp tail)
          (setq y tail z 0.0))
        ((= (type tail) 'LIST)
          (setq y (if tail (car tail) nil))
          (setq tail2 (if tail (cdr tail) nil))
          (cond
            ((numberp tail2) (setq z tail2))
            ((and (= (type tail2) 'LIST) tail2)
              (setq z (car tail2)))
            (T (setq z 0.0))))))
    (setq x nil y nil z nil))
  (if (and (numberp x) (numberp y))
    (list x y (if (numberp z) z 0.0))
    nil)
)

(defun urb:xref-local-to-world
  (local-point transform / pos rot xs ys zs cosine sine lx ly lz)
  (setq local-point (urb:point3d-list local-point))
  (setq pos (urb:point3d-list (nth 0 transform)) rot (nth 1 transform)
        xs (nth 2 transform) ys (nth 3 transform) zs (nth 4 transform))
  (if (and local-point pos)
    (progn
      (setq lx (* (car local-point) xs))
      (setq ly (* (cadr local-point) ys))
      (setq lz (* (caddr local-point) zs))
      (setq cosine (cos rot) sine (sin rot))
      (list
        (+ (car pos) (- (* lx cosine) (* ly sine)))
        (+ (cadr pos) (+ (* lx sine) (* ly cosine)))
        (+ (caddr pos) lz)))
    nil)
)

;; Transformacion (insercion/rotacion/escala) de CUALQUIER referencia de
;; bloque, sea el INSERT de un xref o una referencia anidada dentro de
;; otra definicion -- misma forma (pos rot xs ys zs) para las dos.
(defun urb:block-instance-transform (obj)
  (list
    (urb:point3d-list (vlax-get obj 'InsertionPoint))
    (vla-get-Rotation obj)
    (vla-get-XScaleFactor obj)
    (vla-get-YScaleFactor obj)
    (vla-get-ZScaleFactor obj))
)

;; Si item es un TEXT/MTEXT en layer con contenido numerico > 0,
;; devuelve (punto-local valor); nil si no aplica. layer va con el
;; prefijo completo del xref si aplica (ver nota mas abajo).
(defun urb:cota-text-value (item layer / content point value source-id)
  (if (and (member (vla-get-ObjectName item) '("AcDbText" "AcDbMText"))
           (urb:string-equal-p
             (urb:safe-string
               (vl-catch-all-apply 'vla-get-Layer (list item)) "")
             layer))
    (progn
      (setq content (vl-catch-all-apply 'vla-get-TextString (list item)))
          (setq point (vl-catch-all-apply 'vlax-get (list item 'InsertionPoint)))
      (if (or (vl-catch-all-error-p content) (vl-catch-all-error-p point))
        nil
        (progn
          (setq value (urb:parse-real content))
          (if (and value (> value 0.0))
            (progn
              (setq source-id
                (urb:safe-string
                  (vl-catch-all-apply 'vla-get-Handle (list item)) "TEXT"))
              (list (urb:point3d-list point) value source-id))
            nil))))
    nil)
)

;; Caso real de este proyecto: la etiqueta de cota no esta suelta
;; dentro del xref, sino un nivel mas adentro -- dentro de OTRO bloque
;; insertado dentro del xref (p.ej. un punto COGO de Civil 3D, con
;; nombre anonimo tipo "*U..."). Si item es esa clase de bloque, entra
;; a su definicion y devuelve la lista de (punto valor) que encuentre,
;; ya llevados al sistema LOCAL del CONTENEDOR (el xref), componiendo
;; la transformacion propia de item. nil si item no es un bloque o si
;; algo falla al resolverlo.
(defun urb:nested-block-cota-texts
  (item layer blks / inner-transform inner-origin inner-name inner-def
   sub found raw-point transformed-point value source-id result)
  (if (/= (vla-get-ObjectName item) "AcDbBlockReference")
    nil
    (progn
      (setq inner-transform
        (vl-catch-all-apply 'urb:block-instance-transform (list item)))
      (if (not (vl-catch-all-error-p inner-transform))
        (setq inner-origin (nth 0 inner-transform)))
      ;; El handle de la referencia COGO identifica una etiqueta fisica.
      ;; Sus varias geometrías candidatas conservan el mismo identificador,
      ;; lo que permite elegir despues una sola posicion representativa.
      (setq source-id
        (urb:safe-string
          (vl-catch-all-apply 'vla-get-Handle (list item)) "COGO"))
      (setq inner-name
        (vl-catch-all-apply 'vla-get-EffectiveName (list item)))
      (if (or (vl-catch-all-error-p inner-transform)
              (vl-catch-all-error-p inner-name))
        nil
        (progn
          (setq inner-def
            (vl-catch-all-apply 'vla-Item (list blks inner-name)))
          (if (vl-catch-all-error-p inner-def)
            nil
            (progn
              (vlax-for sub inner-def
                (setq found (urb:cota-text-value sub layer))
                (if found
                  (progn
                    (setq raw-point (urb:point3d-list (car found)))
                    (setq value (cadr found))
                    (setq transformed-point
                      (if raw-point
                        (urb:xref-local-to-world
                          raw-point inner-transform)))
                    ;; Los proxies/etiquetas COGO no son consistentes entre
                    ;; estilos: algunos guardan el texto respecto al bloque,
                    ;; otros respecto al dibujo fuente y otros solo conservan
                    ;; bien el anclaje del punto. Se entregan las tres posiciones
                    ;; candidatas; el filtro de distancia al eje conserva la
                    ;; representacion correcta y descarta las otras dos.
                    (if inner-origin
                      (setq result
                        (cons (list inner-origin value source-id) result)))
                    (if transformed-point
                      (setq result
                        (cons (list transformed-point value source-id) result)))
                    (if raw-point
                      (setq result
                        (cons (list raw-point value source-id) result))))))
              result))))))
)

;; Recorre blk (la definicion del xref) buscando textos de cota en
;; layer, ya sea sueltos o un nivel mas adentro (ver
;; urb:nested-block-cota-texts). Devuelve (punto valor) en el sistema
;; LOCAL de blk -- todavia falta llevarlo a coordenadas del dibujo.
(defun urb:collect-cota-in-block (blk layer blks / item found nested n result)
  (vlax-for item blk
    (setq found (urb:cota-text-value item layer))
    (if found
      (setq result (cons found result))
      (progn
        (setq nested (urb:nested-block-cota-texts item layer blks))
        (foreach n nested (setq result (cons n result))))))
  result
)

(defun urb:collect-xref-cota-texts
  (xref-name layer / transforms transform doc blks blk locals item result)
  (setq transforms (urb:xref-insert-transforms xref-name))
  (if transforms
    (progn
      (setq doc (urb:doc))
      (setq blks (vla-get-Blocks doc))
      (setq blk (vl-catch-all-apply 'vla-Item (list blks xref-name)))
      (if (not (vl-catch-all-error-p blk))
        (progn
          (setq locals (urb:collect-cota-in-block blk layer blks))
          (foreach transform transforms
            (foreach item locals
              (setq result
                (cons
                  (list
                    (urb:xref-local-to-world (car item) transform)
                    (cadr item)
                    (urb:safe-string (nth 2 item) "XREF"))
                  result))))))))
  result
)

;; Textos de la capa cuyo contenido sea un numero > 0: cotas de proyecto.
;; Los textos no numericos de la misma capa se descartan solos. Si la
;; capa llego con el patron "XREF|CAPA" (entget la reporta asi para
;; entidades anidadas), se usa el metodo de xref; si no, ssget normal.
;;
;; OJO: al recorrer un xref con vlax-for, ActiveX reporta la capa de
;; CUALQUIER entidad que pertenezca a ese xref con el prefijo completo
;; "XREF|CAPA" -- incluso viendola desde DENTRO de un bloque anidado un
;; nivel mas (confirmado en vivo: un MTEXT dentro de un bloque de punto
;; COGO, que a su vez esta dentro del xref, seguia reportando
;; "COTAS VIA|V-NODE-TEXT", no solo "V-NODE-TEXT"). Por eso se compara
;; contra la capa COMPLETA en todo el recorrido del xref, no la version
;; sin el prefijo.
(setq *urb-cota-layer-calibrations* nil)

(defun urb:clear-cota-calibration (layer / key entry)
  (setq key (strcase (urb:safe-string layer "")))
  (setq entry (assoc key *urb-cota-layer-calibrations*))
  (if entry
    (setq *urb-cota-layer-calibrations*
      (vl-remove entry *urb-cota-layer-calibrations*)))
  ;; borra tambien la persistida en el dibujo (v4.57.1)
  (vl-catch-all-apply 'urb:config-write
    (list (urb:cota-calib-key layer) ""))
  nil
)

;; clave de config valida para el diccionario del dibujo: el nombre de
;; la capa trae "|" (xref) y espacios -- con esos caracteres la entrada
;; de diccionario fallaba EN SILENCIO y la persistencia no escribia
;; nada (cazado por la suite r3 del 2026-08-25: set OK, get nil).
;; Todo caracter fuera de [A-Z0-9-] se vuelve "_".
(defun urb:cota-calib-key (layer / out i c)
  (setq out "" i 1)
  (setq layer (strcase (urb:safe-string layer "")))
  (repeat (strlen layer)
    (setq c (substr layer i 1))
    (setq out
      (strcat out
        (if (vl-string-search c "ABCDEFGHIJKLMNOPQRSTUVWXYZ0123456789-")
          c
          "_")))
    (setq i (1+ i)))
  (strcat "URB_COTA_CALIB_" out))

;; 2026-08-25: la calibracion ahora tambien se PERSISTE en el dibujo
;; (urb:cota-calib-key via urb:config-write). Antes vivia solo en la
;; memoria de la sesion: al reabrir el dibujo o recalcular una via
;; existente el desfase de las etiquetas COGO volvia a dejar 0
;; candidatos y el movimiento de tierras nunca se calculaba (reporte
;; del usuario: 7785 textos leidos, 0 cercanos, desfase real 121-229 m
;; medido en VIA-01/VIA-02 del master).
(defun urb:set-cota-calibration (layer offset / key entry pair)
  (setq key (strcase (urb:safe-string layer "")))
  (setq pair (cons key offset))
  (setq entry (assoc key *urb-cota-layer-calibrations*))
  (if entry
    (setq *urb-cota-layer-calibrations*
      (subst pair entry *urb-cota-layer-calibrations*))
    (setq *urb-cota-layer-calibrations*
      (cons pair *urb-cota-layer-calibrations*)))
  (vl-catch-all-apply 'urb:config-write
    (list (urb:cota-calib-key layer) (urb:serialize-lisp offset)))
  offset
)

(defun urb:get-cota-calibration (layer / key entry saved parsed)
  (setq key (strcase (urb:safe-string layer "")))
  (setq entry (assoc key *urb-cota-layer-calibrations*))
  (cond
    (entry (cdr entry))
    (T
      ;; respaldo persistido en el dibujo (sobrevive sesiones y EDITAR)
      (setq saved
        (vl-catch-all-apply 'urb:config-read
          (list (urb:cota-calib-key layer))))
      (if (vl-catch-all-error-p saved) (setq saved nil))
      (if (and saved (/= (urb:safe-string saved "") ""))
        (progn
          (setq parsed (urb:read-lisp-safe saved))
          (if (and (listp parsed)
                   (= (length parsed) 3)
                   (numberp (car parsed))
                   (numberp (cadr parsed))
                   (numberp (caddr parsed)))
            (progn
              (setq *urb-cota-layer-calibrations*
                (cons (cons key parsed) *urb-cota-layer-calibrations*))
              parsed)))))))

(defun urb:apply-cota-calibration
  (layer texts / offset item point value source-id result)
  (setq offset (urb:get-cota-calibration layer))
  (if offset
    (progn
      (foreach item texts
        (setq point (urb:point3d-list (car item)))
        (setq value (cadr item))
        (setq source-id (urb:safe-string (nth 2 item) "COTA"))
        (if (and point (numberp value))
          (setq result
            (cons (list (mapcar '+ point offset) value source-id) result))))
      (reverse result))
    texts)
)

(defun urb:calibrate-cota-layer
  (layer selected texts / ename edata obj raw-content content selected-value
   pick item point item-value dist best-distance best-point offset item-tail)
  (setq ename (if selected (car selected) nil))
  (setq pick
    (if (and selected (cadr selected))
      (urb:point3d-list (cadr selected))
      nil))
  (setq edata (if ename (entget ename) nil))
  (setq obj
    (if ename
      (vl-catch-all-apply 'vlax-ename->vla-object (list ename))))
  (setq raw-content
    (if (and obj (not (vl-catch-all-error-p obj)))
      (vl-catch-all-apply 'vla-get-TextString (list obj))))
  (setq content
    (urb:safe-string
      (if (and raw-content (not (vl-catch-all-error-p raw-content)))
        raw-content
        (cdr (assoc 1 edata)))
      ""))
  (setq selected-value (urb:parse-real content))
  (if (and pick (numberp selected-value) (> selected-value 0.0))
    (foreach item texts
      (setq point
        (if (= (type item) 'LIST)
          (urb:point3d-list (car item))
          nil))
      (setq item-tail (if (= (type item) 'LIST) (cdr item) nil))
      (setq item-value
        (cond
          ((numberp item-tail) item-tail)
          ((and (= (type item-tail) 'LIST) item-tail) (car item-tail))
          (T nil)))
      (if (and point (numberp item-value)
               (< (abs (- item-value selected-value)) 0.001))
        (progn
          (setq dist (distance pick point))
          (if (or (null best-distance) (< dist best-distance))
            (setq best-distance dist best-point point))))))
  (if best-point
    (progn
      (setq offset (mapcar '- pick best-point))
      (urb:set-cota-calibration layer offset)
      (prompt
        (strcat
          "\nCalibracion de cotas aplicada: desplazamiento "
          (rtos (car offset) 2 3) ", "
          (rtos (cadr offset) 2 3) " m."
          " Referencia seleccionada: " (rtos selected-value 2 3) "."))
      offset)
    (progn
      (prompt
        "\nNo se pudo calibrar la posicion visible de la cota seleccionada.")
      nil))
)

;; ---------- recalibracion VALIDADA CONTRA EL EJE (2026-08-25) ----------
;; Las etiquetas COGO (V-NODE-TEXT) reportan su posicion con un desfase
;; uniforme de cientos de metros (proxy del estilo); ademas el mismo
;; VALOR de cota se repite en muchos puntos del plano, asi que calibrar
;; con "el texto mas cercano al clic" puede elegir el punto equivocado y
;; dejar un desfase igual de inutil. Este nucleo prueba, entre los
;; textos cuyo valor coincide con el clickeado, los mas cercanos al clic
;; (hasta 8) y se queda con el PRIMER desfase que deje cotas reales
;; proyectando dentro del radio del eje de ESTA via -- validacion
;; geometrica, no adivinanza. Headless-testeable (sin UI).
(defun urb:cota-offset-por-pick
  (layer texts-raw pick valor axis axis-start span radius interval
   / cands item point iv c offset probe n proyectados)
  (setq cands nil)
  (foreach item texts-raw
    (setq point (urb:point3d-list (car item)))
    (setq iv
      (cond
        ((numberp (cadr item)) (cadr item))
        (T nil)))
    (if (and point (numberp iv) (< (abs (- iv valor)) 0.001))
      (setq cands (cons (list (distance pick point) point) cands))))
  (setq cands
    (vl-sort cands '(lambda (a b) (< (car a) (car b)))))
  (setq offset nil n 0)
  (foreach c cands
    (if (and (null offset) (< n 8))
      (progn
        (setq n (1+ n))
        (setq probe (mapcar '- pick (cadr c)))
        ;; probar el desfase SIN tocar la calibracion global
        (setq proyectados
          (urb:cota-stations-on-axis axis
            (mapcar
              '(lambda (it)
                 (list
                   (mapcar '+ (urb:point3d-list (car it)) probe)
                   (cadr it)
                   (if (> (length it) 2)
                     (urb:safe-string (nth 2 it) "COTA") "COTA")))
              texts-raw)
            (- axis-start (* 2.0 interval))
            (+ span (* 4.0 interval)) radius))
        (if (>= (length proyectados) 2)
          (setq offset probe)))))
  offset
)

;; wrapper interactivo: UN clic sobre una cota visible de la via, nucleo
;; validado, calibracion persistida en el dibujo. Devuelve T si calibro.
(defun urb:recalibrate-cota-interactive
  (layer axis axis-start span radius interval
   / sel ename edata obj raw content valor pick texts-raw offset)
  (prompt
    (strcat
      "\nLas etiquetas de la capa " layer " reportan una posicion"
      " desfasada (etiquetas COGO). Seleccione UNA cota visible de"
      " ESTA via para calibrar (Enter cancela): "))
  (setq sel (vl-catch-all-apply 'nentsel))
  (if (vl-catch-all-error-p sel) (setq sel nil))
  (if sel
    (progn
      (setq ename (car sel)
            pick (urb:point3d-list (cadr sel))
            edata (entget ename))
      (setq obj
        (vl-catch-all-apply 'vlax-ename->vla-object (list ename)))
      (setq raw
        (if (and obj (not (vl-catch-all-error-p obj)))
          (vl-catch-all-apply 'vla-get-TextString (list obj))))
      (setq content
        (urb:safe-string
          (if (and raw (not (vl-catch-all-error-p raw)))
            raw
            (cdr (assoc 1 edata)))
          ""))
      (setq valor (urb:parse-real content))
      (if (and pick (numberp valor) (> valor 0.0))
        (progn
          ;; textos CRUDOS (sin la calibracion previa, que pudo ser mala)
          (urb:clear-cota-calibration layer)
          (setq texts-raw (urb:collect-cota-texts layer))
          (setq offset
            (urb:cota-offset-por-pick layer texts-raw pick valor
              axis axis-start span radius interval))
          (if offset
            (progn
              (urb:set-cota-calibration layer offset)
              (prompt
                (strcat
                  "\nCalibracion validada contra el eje: desplazamiento "
                  (rtos (car offset) 2 2) ", "
                  (rtos (cadr offset) 2 2)
                  " m (guardada en el dibujo)."))
              T)
            (progn
              (prompt
                (strcat
                  "\nNingun texto con el valor " (rtos valor 2 2)
                  " deja cotas proyectando sobre esta via -- verifique"
                  " que la cota clickeada pertenezca a la via."))
              nil)))
        (progn
          (prompt "\nLa seleccion no es un texto de cota numerico.")
          nil)))
    nil)
)

(defun urb:collect-cota-texts (layer / bar-pos xref-name result)
  (setq layer (urb:safe-string layer ""))
  (if (/= layer "")
    (progn
      (setq bar-pos (vl-string-search "|" layer))
      (setq result
        (if bar-pos
          (progn
            (setq xref-name (substr layer 1 bar-pos))
            (urb:collect-xref-cota-texts xref-name layer))
          (urb:collect-local-cota-texts layer)))))
  (urb:apply-cota-calibration layer result)
)

(defun urb:nearest-cota (point texts radius / best best-dist item dist)
  (setq best-dist radius)
  (foreach item texts
    (setq dist
      (distance
        (list (car point) (cadr point))
        (list (car (car item)) (cadr (car item)))))
    (if (< dist best-dist)
      (progn
        (setq best (cadr item))
        (setq best-dist dist))))
  best
)

;; Proyecta cada texto de cota sobre el eje seleccionado (aunque el eje y
;; los textos vivan en XREF diferentes). Solo conserva textos cercanos al
;; tramo real de la via y devuelve registros (distancia-eje cota desfase).
(defun urb:project-one-cota-on-axis
  (axis item / point item-tail value source-id closest station offset)
  (setq point
    (if (= (type item) 'LIST)
      (urb:point3d-list (car item))
      nil))
  (setq item-tail (if (= (type item) 'LIST) (cdr item) nil))
  (setq value
    (cond
      ((numberp item-tail) item-tail)
      ((and (= (type item-tail) 'LIST) item-tail) (car item-tail))
      (T nil)))
  (setq source-id
    (if (and (= (type item) 'LIST) (> (length item) 2))
      (urb:safe-string (nth 2 item) "COTA")
      "COTA"))
  (if (and point (numberp value))
    (progn
      (setq closest (vlax-curve-getClosestPointTo axis point))
      (setq closest (urb:point3d-list closest))
      (if closest
        (progn
          (setq station (vlax-curve-getDistAtPoint axis closest))
          (setq offset (distance point closest))
          (list station value offset source-id))
        nil))
    nil)
)

(defun urb:normalize-cota-projection-record
  (record / station tail value tail2 offset source-id)
  (if (= (type record) 'LIST)
    (progn
      (setq station (car record))
      (setq tail (cdr record))
      (if (and (= (type tail) 'LIST) tail)
        (progn
          (setq value (car tail))
          (setq tail2 (cdr tail))
          (if (and (= (type tail2) 'LIST) tail2)
            (progn
              (setq offset (car tail2))
              (if (> (length tail2) 1)
                (setq source-id
                  (urb:safe-string (cadr tail2) "COTA")))))))))
  (if (and (numberp station) (numberp value) (numberp offset))
    (list station value offset (urb:safe-string source-id "COTA"))
    nil)
)

(defun urb:insert-cota-record-sorted
  (record records / item result inserted)
  (foreach item records
    (if (and (not inserted) (< (car record) (car item)))
      (progn
        (setq result (cons record result))
        (setq inserted T)))
    (setq result (cons item result)))
  (if (not inserted) (setq result (cons record result)))
  (reverse result)
)

(defun urb:cota-stations-on-axis
  (axis texts axis-start span max-offset
   / axis-end item projected normalized station offset records
   failed error-message)
  (setq axis-end (+ axis-start span))
  (setq *urb-last-cota-min-offset* nil)
  (setq failed 0 error-message nil)
  (setq *urb-earthwork-stage*
    "proyeccion de cotas sobre el eje - evaluacion individual")
  (foreach item texts
    (setq projected
      (vl-catch-all-apply
        'urb:project-one-cota-on-axis
        (list axis item)))
    (if (vl-catch-all-error-p projected)
      (progn
        (setq failed (1+ failed))
        (setq error-message (vl-catch-all-error-message projected)))
      (progn
        (setq normalized
          (vl-catch-all-apply
            'urb:normalize-cota-projection-record
            (list projected)))
        (if (and (not (vl-catch-all-error-p normalized)) normalized)
        (progn
          (setq station (nth 0 normalized))
          (setq offset (nth 2 normalized))
          (if (or (null *urb-last-cota-min-offset*)
                  (< offset *urb-last-cota-min-offset*))
            (setq *urb-last-cota-min-offset* offset))
          (if (and
                (>= station (- axis-start 1e-6))
                (<= station (+ axis-end 1e-6))
                (<= offset max-offset))
            (setq records (cons normalized records))))
        (if (or (vl-catch-all-error-p normalized) (null normalized))
          (setq failed (1+ failed)))))))
  (setq *urb-last-cota-projection-failures* failed)
  (setq *urb-last-cota-projection-error* error-message)
  (setq *urb-earthwork-stage*
    "proyeccion de cotas sobre el eje - lista terminada")
  records
)

;; Una etiqueta COGO puede producir varias posiciones candidatas (anclaje,
;; texto transformado y proxy). Se conserva solamente la candidata de cada
;; etiqueta cuya distancia transversal al eje sea menor.
(defun urb:cota-best-per-source (records / choices record key entry result)
  (foreach record records
    (setq key (urb:safe-string (nth 3 record) "COTA"))
    (setq entry (assoc key choices))
    (if entry
      (if (< (nth 2 record) (nth 2 (cdr entry)))
        (setq choices (subst (cons key record) entry choices)))
      (setq choices (cons (cons key record) choices))))
  (foreach entry choices (setq result (cons (cdr entry) result)))
  result
)

;; Ajusta el anclaje proyectado a la grilla real del proyecto. Ejemplo:
;; una via que inicia en 0+015.33 se evalua en 0+020, 0+025... y no en
;; 0+020.33, 0+025.33. Solo se ajustan puntos ya cercanos a la grilla.
(defun urb:cota-snap-to-project-grid
  (records axis-start span station-start interval direction
   / record raw traveled project-station grid-station grid-traveled
   snapped-raw tolerance result)
  (setq tolerance (min 1.50 (* interval 0.35)))
  (foreach record records
    (setq raw (nth 0 record))
    (setq traveled
      (if (urb:string-equal-p direction "Final")
        (- (+ axis-start span) raw)
        (- raw axis-start)))
    (setq project-station (+ station-start traveled))
    (setq grid-station
      (* interval (fix (+ (/ project-station interval) 0.50))))
    (setq grid-traveled (- grid-station station-start))
    (if (and (<= (abs (- project-station grid-station)) tolerance)
             ;; Dos intervalos exteriores permiten interpolar contornos que
             ;; empiezan/terminan muy cerca, pero no antes, de la siguiente
             ;; abscisa redonda (p.ej. fin 0+054.12 necesita la cota 0+060).
             (>= grid-traveled (- (* 2.0 interval)))
             (<= grid-traveled (+ span (* 2.0 interval))))
      (setq snapped-raw
        (if (urb:string-equal-p direction "Final")
          (- (+ axis-start span) grid-traveled)
          (+ axis-start grid-traveled)))
      (setq snapped-raw raw))
    (setq result
      (cons (urb:replace-nth 0 snapped-raw record) result)))
  (reverse result)
)

(defun urb:cota-sort-records (records / record result)
  (foreach record records
    (setq result (urb:insert-cota-record-sorted record result)))
  result
)

;; Si varias etiquetas terminan en la misma estacion de proyecto, conserva
;; la que este mas cerca transversalmente del eje.
(defun urb:cota-deduplicate-stations
  (records tolerance / sorted record previous result)
  (setq sorted (urb:cota-sort-records records))
  (foreach record sorted
    (setq previous (car result))
    (if (and previous
             (<= (abs (- (nth 0 record) (nth 0 previous))) tolerance))
      (if (< (nth 2 record) (nth 2 previous))
        (setq result (cons record (cdr result))))
      (setq result (cons record result))))
  (reverse result)
)

(defun urb:cota-at-axis-distance
  (axis-distance records / lower upper item station span ratio
   second-lower second-upper slope)
  (foreach item records
    (setq station (car item))
    (if (<= station axis-distance)
      (if (or (null lower) (> station (car lower)))
        (setq lower item)))
    (if (>= station axis-distance)
      (if (or (null upper) (< station (car upper)))
        (setq upper item))))
  (cond
    ((and lower (< (abs (- axis-distance (car lower))) 0.01))
      (cadr lower))
    ((and upper (< (abs (- axis-distance (car upper))) 0.01))
      (cadr upper))
    ((and lower upper (> (- (car upper) (car lower)) 1e-9))
      (setq span (- (car upper) (car lower)))
      (setq ratio (/ (- axis-distance (car lower)) span))
      (+ (cadr lower) (* ratio (- (cadr upper) (cadr lower)))))
    ;; 2026-08-26 (pedido del usuario: "con 13 cotas ya me deberia
    ;; extrapolar para el resto de la via"): fuera del rango de cotas
    ;; la rasante se EXTRAPOLA con la PENDIENTE del tramo de borde
    ;; (antes: valor constante, que aplanaba el extremo y con huecos
    ;; grandes el gate directamente descartaba todo).
    ((and (null lower) upper)
      ;; antes del primer punto: pendiente de los 2 primeros
      (foreach item records
        (setq station (car item))
        (if (and (> station (car upper))
                 (or (null second-upper) (< station (car second-upper))))
          (setq second-upper item)))
      (if (and second-upper
               (> (- (car second-upper) (car upper)) 1e-9))
        (progn
          (setq slope
            (/ (- (cadr second-upper) (cadr upper))
               (- (car second-upper) (car upper))))
          (+ (cadr upper) (* slope (- axis-distance (car upper)))))
        (cadr upper)))
    ((and lower (null upper))
      ;; despues del ultimo punto: pendiente de los 2 ultimos
      (foreach item records
        (setq station (car item))
        (if (and (< station (car lower))
                 (or (null second-lower) (> station (car second-lower))))
          (setq second-lower item)))
      (if (and second-lower
               (> (- (car lower) (car second-lower)) 1e-9))
        (progn
          (setq slope
            (/ (- (cadr lower) (cadr second-lower))
               (- (car lower) (car second-lower))))
          (+ (cadr lower) (* slope (- axis-distance (car lower)))))
        (cadr lower)))
    (T nil))
)

(defun urb:cota-stations-cover-p
  (records axis-start axis-end tolerance / item station min-station max-station)
  ;; 2026-08-25: la tolerancia de borde ahora es 2 x intervalo, alineada
  ;; con los margenes que YA usan la recoleccion y el snap (+-2
  ;; intervalos). Caso real del usuario (VIA-02): cotas cada 10 m con
  ;; intervalo de abscisas de 5 m -- la ultima cota quedaba a 9.84 m del
  ;; final del tramo, el chequeo exigia <=5 m y DESCARTABA las 22
  ;; estaciones detectadas, pidiendo cotas manuales. El tramo de borde
  ;; sin cota se resuelve con la extrapolacion que urb:cota-at-axis-
  ;; distance ya trae (valor del borde mas cercano).
  (setq tolerance (* 2.0 tolerance))
  (if (>= (length records) 2)
    (progn
      (foreach item records
        (setq station (car item))
        (if (or (null min-station) (< station min-station))
          (setq min-station station))
        (if (or (null max-station) (> station max-station))
          (setq max-station station)))
      (and
        min-station max-station
        (> (- max-station min-station) 0.01)
        (<= min-station (+ axis-start tolerance))
        (>= max-station (- axis-end tolerance))))
    nil)
)

(defun urb:terrain-at-section
  (surface axis d half-width
   / point param deriv len normal fractions fraction offset z p profile
   rest first second integral width)
  ;; Siete ordenadas transversales, incluidas ambas orillas y el eje.
  ;; Devuelve (cota-media punto perfil), donde perfil contiene pares
  ;; (desfase cota). La cota media se integra por trapecios, no por el
  ;; promedio simple de tres puntos que usaban las versiones anteriores.
  (setq point
    (vl-catch-all-apply 'vlax-curve-getPointAtDist (list axis d)))
  (if (vl-catch-all-error-p point) (setq point nil))
  (if point
    (progn
      (setq param (vlax-curve-getParamAtDist axis d))
      (setq deriv (vlax-curve-getFirstDeriv axis param))
      (setq len (distance '(0.0 0.0 0.0) deriv))
      (setq normal
        (if (> len 1e-9)
          (list (- (/ (cadr deriv) len)) (/ (car deriv) len) 0.0)
          '(0.0 0.0 0.0)))
      (setq fractions '(-1.0 -0.6666666667 -0.3333333333 0.0
                         0.3333333333 0.6666666667 1.0))
      (foreach fraction fractions
        (setq offset (* fraction half-width)
              p (mapcar '+ point
                  (mapcar '(lambda (v) (* v offset)) normal)))
        (setq z (urb:surface-elevation surface (car p) (cadr p)))
        (if (numberp z)
          (setq profile (append profile (list (list offset z))))))
      ;; Una seccion parcial no se extrapola: se marca omitida para no
      ;; fabricar volumen fuera de la cobertura real de la superficie.
      (if (= (length profile) (length fractions))
        (progn
          (setq rest profile integral 0.0)
          (while (cadr rest)
            (setq first (car rest) second (cadr rest)
                  integral
                    (+ integral
                      (* 0.5 (+ (cadr first) (cadr second))
                        (- (car second) (car first))))
                  rest (cdr rest)))
          (setq width (* 2.0 half-width))
          (list (if (> width 1e-9) (/ integral width) (cadr (nth 3 profile)))
                point profile))
        nil))
    nil)
)

;; BUG (2026-07-06, pre-existente): antes esta funcion re-resolvia el eje
;; con (handent (nth 5 data)) -- pero handent solo busca en la tabla de
;; handles del dibujo ACTUAL, nunca dentro de un xref. Si el eje vive en
;; un xref (caso normal del usuario), handent siempre devolvia nil y la
;; funcion abortaba con "la via no tiene un eje valido" antes incluso de
;; preguntar la cota/pendiente manual. Ahora el eje llega ya resuelto
;; como parametro, tal como lo tiene create-road/edit-road recien
;; seleccionado (con nentsel, que si funciona sobre xrefs).
(defun urb:road-section-samples
  (surface axis axis-start span interval direction width-total
   cota-stations cota-coverage station-start
   / s d section terrain rasante profile result positions end-station next-grid knot)
  ;; Secciones en inicio/final reales y en las abscisas redondas de proyecto.
  ;; Para inicio 0+015.33: 15.33, 20, 25... 50, 54.12.
  (setq positions (list 0.0))
  (setq end-station (+ station-start span))
  (setq next-grid (* interval (fix (1+ (/ station-start interval)))))
  (if (<= next-grid (+ station-start 1e-6))
    (setq next-grid (+ next-grid interval)))
  (while (< next-grid (- end-station 1e-6))
    (setq positions
      (append positions (list (- next-grid station-start))))
    (setq next-grid (+ next-grid interval)))
  (if (> span 1e-6) (setq positions (append positions (list span))))
  ;; Incluir quiebres de rasante aunque no caigan en la malla regular.
  (if cota-coverage
    (foreach knot cota-stations
      (setq s (if (urb:string-equal-p direction "Final")
        (- (+ axis-start span) (car knot)) (- (car knot) axis-start)))
      (if (and (> s 1e-6) (< s (- span 1e-6)))
        (setq positions (cons s positions)))))
  (setq positions (vl-sort positions '<))
  (foreach s positions
    (setq d
      (+ axis-start
        (if (urb:string-equal-p direction "Final")
          (max 0.0 (- span s))
          (min span s))))
    (setq section
      (urb:terrain-at-section surface axis d (/ width-total 2.0)))
    (setq terrain (if section (car section) nil))
    (setq profile (if section (nth 2 section) nil))
    (setq rasante
      (if cota-coverage
        (urb:cota-at-axis-distance d cota-stations)
        nil))
    (setq result (cons (list s terrain rasante profile) result)))
  (reverse result)
)

(defun urb:road-apply-linear-grade
  (samples cota0 cota-final span / slope item result)
  (setq slope
    (if (> span 0.0)
      (* (/ (- cota-final cota0) span) 100.0)
      0.0))
  (foreach item samples
    (setq result
      (cons
        (list
          (nth 0 item)
          (nth 1 item)
          (+ cota0 (* (/ slope 100.0) (nth 0 item)))
          (nth 3 item))
        result)))
  (list (reverse result) slope)
)

(defun urb:road-resolve-grade
  (samples cota-coverage station-count old-cota0 old-cota-final span data
   / cota0 cota-final slope metodo start-num end-label grade)
  (cond
    (cota-coverage
      (list
        samples
        (if (and (boundp '*urb-road-picked-stations*)
                 *urb-road-picked-stations*)
          (strcat
            "rasante por tramos ("
            (itoa station-count) " cotas seleccionadas)")
          (strcat
            "cotas de proyecto interpoladas ("
            (itoa station-count) " textos)"))
        nil
        nil))
    ((and old-cota0 old-cota-final)
      (setq cota0 old-cota0)
      (setq cota-final old-cota-final)
      (setq grade
        (urb:road-apply-linear-grade samples cota0 cota-final span))
      (setq slope (cadr grade))
      (setq metodo
        (strcat
          "cota " (rtos cota0 2 2)
          " -> cota " (rtos cota-final 2 2)
          " (pendiente " (rtos slope 2 2)
          (if *urb-road-picked-cotas*
            "%, cotas seleccionadas en el dibujo)"
            "%, conservada de la edicion anterior)")))
      (list (car grade) metodo cota0 cota-final))
    (T
      (prompt "\nNo hay suficientes cotas de proyecto cerca del eje.")
      (setq start-num
        (urb:station-number (urb:safe-string (nth 10 data) "0+000")))
      (setq end-label (urb:format-station (+ start-num span)))
      (setq cota0
        (getreal
          (strcat
            "\nCota de rasante en la abscisa inicial "
            (urb:safe-string (nth 10 data) "0+000")
            " (Enter omite el calculo): ")))
      (if cota0
        (setq cota-final
          (getreal
            (strcat
              "\nCota de rasante en la abscisa final "
              end-label " (Enter omite el calculo): "))))
      (if (and cota0 cota-final)
        (progn
          (setq grade
            (urb:road-apply-linear-grade samples cota0 cota-final span))
          (setq slope (cadr grade))
          (setq metodo
            (strcat
              "cota " (rtos cota0 2 2)
              " -> cota " (rtos cota-final 2 2)
              " (pendiente " (rtos slope 2 2) "%)"))
          (list (car grade) metodo cota0 cota-final))
        nil)))
)

;; Calcula el aporte de UN intervalo con la misma regla usada por
;; urb:road-integrate-earthworks. Se separa para construir una tabla de
;; auditoria cuyos subtotales reproducen exactamente el total de la via.
(defun urb:road-earthwork-segment
  (delta1 delta2 width-total ds / cut fill average cross-ratio ds1 ds2)
  (setq cut 0.0 fill 0.0)
  (cond
    ((and (>= delta1 0.0) (>= delta2 0.0))
      (setq average (/ (+ delta1 delta2) 2.0))
      (setq cut (* average width-total ds)))
    ((and (<= delta1 0.0) (<= delta2 0.0))
      (setq average (/ (+ (- delta1) (- delta2)) 2.0))
      (setq fill (* average width-total ds)))
    (T
      (setq cross-ratio
        (/ (abs delta1) (+ (abs delta1) (abs delta2))))
      (setq ds1 (* ds cross-ratio))
      (setq ds2 (- ds ds1))
      (if (> delta1 0.0)
        (progn
          (setq cut (* 0.5 delta1 width-total ds1))
          (setq fill (* 0.5 (- delta2) width-total ds2)))
        (progn
          (setq fill (* 0.5 (- delta1) width-total ds1))
          (setq cut (* 0.5 delta2 width-total ds2)))))
  )
  (list cut fill)
)

(defun urb:road-section-earthwork-areas
  (profile terrain rasante width-total depth
   / rest first second design1 design2 delta1 delta2 segment dx cut fill delta)
  ;; Areas transversales separadas de corte/relleno. Cada intervalo entre
  ;; ordenadas se parte exactamente en el cruce por cero, evitando que el
  ;; corte de un costado cancele el relleno del otro.
  (setq cut 0.0 fill 0.0)
  (if (and profile (> (length profile) 1) (numberp rasante))
    (progn
      (setq rest profile)
      (while (cadr rest)
        (setq first (car rest)
              second (cadr rest)
              ;; Corona simetrica: la rasante almacenada corresponde al
              ;; eje; hacia cada borde baja abs(offset)*bombeo. El fondo
              ;; estructural conserva la misma pendiente transversal.
              design1 (- rasante
                         (* (abs (car first)) *urb-road-crossfall*) depth)
              design2 (- rasante
                         (* (abs (car second)) *urb-road-crossfall*) depth)
              delta1 (- (cadr first) design1)
              delta2 (- (cadr second) design2)
              dx (- (car second) (car first))
              ;; 5.6.5 sobreexcavacion: con h = material no portante, en
              ;; cada ordenada excavacion = max(delta,h) y relleno =
              ;; max(0,h-delta). Se reusa el corte exacto por cruce por
              ;; cero desplazando las ordenadas en h y sumando la franja
              ;; h x dx que SIEMPRE se excava.
              segment
                (urb:road-earthwork-segment
                  (- delta1 (max 0.0 *urb-overexc-depth*))
                  (- delta2 (max 0.0 *urb-overexc-depth*)) 1.0 dx)
              cut (+ cut (* (max 0.0 *urb-overexc-depth*) dx) (car segment))
              fill (+ fill (cadr segment))
              rest (cdr rest)))
      (list cut fill))
    (if (and (numberp terrain) (numberp rasante))
      (progn
        ;; Compatibilidad con pruebas/muestras antiguas sin perfil.
        ;; Respaldo para registros antiguos sin siete ordenadas: compara
        ;; contra el fondo medio de la seccion coronada.
        (setq delta
          (- terrain
             (- rasante depth
                (* 0.25 width-total *urb-road-crossfall*))))
        (setq delta (urb:cut-fill-at delta))
        (list (* (car delta) width-total) (* (cadr delta) width-total)))
      nil))
)

(defun urb:road-integrate-earthworks
  (samples width-total depth / item prev-areas prev-s areas ds
   cut fill skipped)
  ;; Metodo de areas extremas sobre secciones de siete ordenadas.
  (setq cut 0.0 fill 0.0 skipped 0 prev-areas nil prev-s nil)
  (foreach item samples
    (setq areas
      (urb:road-section-earthwork-areas
        (nth 3 item) (nth 1 item) (nth 2 item) width-total depth))
    (if areas
      (progn
        (if (and prev-areas prev-s)
          (progn
            (setq ds (- (nth 0 item) prev-s))
            (setq cut
              (+ cut (* 0.5 (+ (car prev-areas) (car areas)) ds)))
            (setq fill
              (+ fill (* 0.5 (+ (cadr prev-areas) (cadr areas)) ds)))))
        (setq prev-areas areas
              prev-s (nth 0 item)))
      (progn
        (setq skipped (1+ skipped))
        (setq prev-areas nil prev-s nil))))
  (list cut fill skipped)
)

;; Cada registro:
;; (distancia TN rasante fondo delta area-corte area-relleno vol-corte vol-relleno)
(defun urb:road-earthwork-audit-rows
  (samples width-total depth / item terrain rasante fondo delta area-cut area-fill
   prev-areas prev-s ds areas vol-cut vol-fill result)
  (setq prev-areas nil prev-s nil result nil)
  (foreach item samples
    (setq terrain (nth 1 item))
    (setq rasante (nth 2 item))
    (setq areas
      (urb:road-section-earthwork-areas
        (nth 3 item) terrain rasante width-total depth))
    (if areas
      (progn
        (setq fondo (- rasante depth))
        (setq delta (- terrain fondo))
        (setq area-cut (car areas))
        (setq area-fill (cadr areas))
        (setq vol-cut 0.0 vol-fill 0.0)
        (if (and prev-areas prev-s)
          (progn
            (setq ds (- (nth 0 item) prev-s))
            (setq vol-cut
              (* 0.5 (+ (car prev-areas) area-cut) ds))
            (setq vol-fill
              (* 0.5 (+ (cadr prev-areas) area-fill) ds))))
        (setq result
          (cons
            (list (nth 0 item) terrain rasante fondo delta
              area-cut area-fill vol-cut vol-fill)
            result))
        (setq prev-areas areas prev-s (nth 0 item)))
      (setq prev-areas nil prev-s nil)))
  (reverse result)
)

(defun urb:road-audit-table-point
  (boundary / points point maxx maxy textheight bname ent ed it)
  ;; OJO v2: lwpoly-points agarra TODOS los grupos 10 sin mirar el tipo
  ;; de entidad -- sobre un INSERT devuelve su punto de insercion
  ;; ((0,0,0) en las vias empacadas), NO nil, y la guarda de abajo nunca
  ;; disparaba. Solo aplica a polilineas reales.
  (setq points
    (if (= (cdr (assoc 0 (entget boundary))) "LWPOLYLINE")
      (urb:lwpoly-points boundary)
      nil))
  ;; 2026-08-13: con la via EMPACADA el contorno vive dentro del bloque
  ;; y lwpoly-points del INSERT devuelve nil -- la tabla terminaba en el
  ;; origen del plano, a millones de metros de la via (reproducido:
  ;; distancia 2401698 m). Se busca el contorno cerrado en la definicion
  ;; del bloque. OJO: urb:lwpoly-points usa (trans ... ename 0) y trans
  ;; devuelve NIL para entidades dentro de definiciones de bloque
  ;; (radiografiado: entget da las coordenadas reales y lwpoly-points da
  ;; nils) -- extraccion CRUDA de los grupos 10, que aqui ya son WCS
  ;; (bloque con base 0,0 insertado en 0,0 escala 1).
  (if (null points)
    (progn
      (setq bname
        (vl-catch-all-apply
          '(lambda () (vla-get-Name (vlax-ename->vla-object boundary)))))
      (if (not (vl-catch-all-error-p bname))
        (progn
          (setq ent (cdr (assoc -2 (tblsearch "BLOCK" bname))))
          (while (and ent (null points))
            (setq ed (entget ent))
            (if (and (= (cdr (assoc 0 ed)) "LWPOLYLINE")
                     (= 1 (logand 1 (cdr (assoc 70 ed)))))
              (foreach it ed
                (if (= (car it) 10)
                  (setq points
                    (cons (list (cadr it) (caddr it) 0.0) points)))))
            (setq ent (entnext ent)))))))
  (foreach point points
    (if (or (null maxx) (> (car point) maxx)) (setq maxx (car point)))
    (if (or (null maxy) (> (cadr point) maxy)) (setq maxy (cadr point))))
  (setq textheight (* 0.60 (max 0.20 (getvar "TEXTSIZE"))))
  (if (and maxx maxy)
    (list (+ maxx (* textheight 4.0)) maxy 0.0)
    '(0.0 0.0 0.0))
)

(defun urb:set-table-text-safe (table row column value)
  (vl-catch-all-apply
    'vla-SetText
    (list table row column (urb:safe-string value "")))
)

;; Tabla visible de comprobacion manual. Se etiqueta como objeto generado
;; para que se regenere al EDITAR y quede empacada junto con la via.
;; 2026-08-13: las filas se PERSISTEN (ldata URB_VIA_AUDIT) al calcular,
;; para que MOSTRAR/OCULTAR pueda repintar la tabla al instante SIN
;; recalcular (sin superficie, sin eje, sin efectos secundarios).
(defun urb:create-road-earthwork-audit
  (boundary axis samples width-total depth data cut fill metodo / audit)
  (setq audit (urb:road-earthwork-audit-rows samples width-total depth))
  (if audit
    (progn
      (vl-catch-all-apply 'vlax-ldata-put
        (list boundary "URB_VIA_AUDIT" (list audit metodo cut fill)))
      (urb:draw-road-audit-table boundary axis audit data cut fill metodo)))
)

;; Dibujador PURO de la tabla ancha de verificacion: recibe las filas ya
;; calculadas (o recien leidas de URB_VIA_AUDIT). axis solo se usa para
;; la rotacion (nil = sin rotar). El punto: el elegido por el usuario, o
;; la esquina del contorno, o la caja del bloque como respaldo.
(defun urb:draw-road-audit-table
  (boundary axis audit data cut fill metodo
   / point textheight rowheight colwidth rows-count table headers
   row item station-start row-index column handle rotation)
  (if audit
    (progn
      ;; Capa PROPIA para la tabla de verificacion: permite apagarla o
      ;; congelarla sin ocultar la via (antes iba en URB-VIA junto con
      ;; todo lo demas y no se podia esconder por separado).
      (urb:ensure-layer "URB-VIA-TABLA" 4 T)
      ;; punto elegido por el usuario (comando de Cantidades) o, como
      ;; respaldo, la esquina superior derecha del contorno como antes
      (setq point
        (if (and (boundp '*urb-road-audit-point*) *urb-road-audit-point*)
          *urb-road-audit-point*
          (urb:road-audit-table-point boundary)))
      ;; boundary puede ser el BLOQUE de la via (sin lwpoly-points):
      ;; respaldo con su caja envolvente
      (if (equal point '(0.0 0.0 0.0))
        (setq point (urb:road-memory-table-point boundary)))
      (setq textheight (* 0.60 (max 0.20 (getvar "TEXTSIZE"))))
      (setq rowheight (* textheight 2.20))
      (setq colwidth (* textheight 11.0))
      ;; Titulo + encabezado + muestras + total.
      (setq rows-count (+ (length audit) 3))
      (setq table
        (vla-AddTable
          (urb:space) (vlax-3d-point point)
          rows-count 9 rowheight colwidth))
      (vla-put-Layer table "URB-VIA-TABLA")
      (vla-put-Color table 256)
      (vl-catch-all-apply 'vla-put-RegenerateTableSuppressed
        (list table :vlax-true))
      (vl-catch-all-apply 'vla-MergeCells (list table 0 0 0 8))
      (urb:set-table-text-safe table 0 0
        (strcat "VERIFICACION MOVIMIENTO DE TIERRAS - "
          (urb:safe-string (nth 1 data) "VIA")
          " | Metodo: " (urb:safe-string metodo "")))
      (setq headers
        '("Abscisa" "TN" "Rasante" "Fondo estr." "Delta"
          "A.corte" "A.relleno" "V.corte tramo" "V.relleno tramo"))
      (setq column 0)
      (foreach item headers
        (urb:set-table-text-safe table 1 column item)
        (setq column (1+ column)))
      (setq station-start
        (urb:station-number (urb:safe-string (nth 10 data) "0+000")))
      (setq row-index 2)
      (foreach row audit
        (urb:set-table-text-safe table row-index 0
          (urb:format-station (+ station-start (nth 0 row))))
        (setq column 1)
        (foreach item (cdr row)
          (urb:set-table-text-safe table row-index column (rtos item 2 2))
          (setq column (1+ column)))
        (setq row-index (1+ row-index)))
      (urb:set-table-text-safe table row-index 0 "TOTAL")
      (urb:set-table-text-safe table row-index 7 (rtos cut 2 2))
      (urb:set-table-text-safe table row-index 8 (rtos fill 2 2))
      (foreach item '(1 2 4)
        (vl-catch-all-apply 'vla-SetTextHeight
          (list table item textheight)))
      (setq rotation (urb:road-summary-angle axis point))
      (if rotation
        (vl-catch-all-apply 'vla-put-Rotation (list table rotation)))
      (vl-catch-all-apply 'vla-put-RegenerateTableSuppressed
        (list table :vlax-false))
      (vl-catch-all-apply 'vla-RecomputeTableBlock (list table :vlax-true))
      (setq handle (vla-get-Handle (vlax-ename->vla-object boundary)))
      ;; 2026-08-11: etiqueta PROPIA (URB_VIA_TABLA), NO URB_VIA_GEN --
      ;; los objetos URB_VIA_GEN se empacan dentro del bloque de la via al
      ;; crear/editar (urb:package-road) y la tabla debe quedar SUELTA
      ;; donde el usuario la puso.
      (urb:set-xdata-strings
        (vlax-vla-object->ename table) "URB_VIA_TABLA" (list handle))
      (prompt
        (strcat
          "\nTabla de verificacion creada: " (itoa (length audit))
          " secciones | corte " (rtos cut 2 2)
          " m3 | relleno " (rtos fill 2 2) " m3."))
      table))
)

;; Borra las tablas de verificacion GENERADAS sueltas en el dibujo (nunca
;; toca tablas hechas a mano). Reconoce el tag nuevo URB_VIA_TABLA y el
;; viejo URB_VIA_GEN (tablas de versiones anteriores que aun no se hayan
;; empacado). parent-handle nil = todas (migracion); con handle, solo las
;; de esa via.
(defun urb:delete-road-audit-tables (parent-handle / ss index ename data count app)
  (setq count 0)
  (foreach app '("URB_VIA_TABLA" "URB_VIA_GEN")
    (setq ss (ssget "_X" (list '(0 . "ACAD_TABLE") (list -3 (list app)))))
    (if ss
      (progn
        (setq index 0)
        (repeat (sslength ss)
          (setq ename (ssname ss index))
          (setq data (urb:get-xdata-strings ename app))
          (if (and data (or (null parent-handle) (= (car data) parent-handle)))
            (if (urb:safe-delete (vlax-ename->vla-object ename))
              (setq count (1+ count))))
          (setq index (1+ index))))))
  count)

(defun urb:road-memory-table-point (road / obj minpt maxpt result textheight)
  (setq obj (vlax-ename->vla-object road)
        result
          (vl-catch-all-apply
            '(lambda ()
               (vla-GetBoundingBox obj 'minpt 'maxpt)
               (setq maxpt (vlax-safearray->list maxpt))
               maxpt)))
  (if (vl-catch-all-error-p result)
    '(0.0 0.0 0.0)
    (progn
      (setq textheight (* 0.60 (max 0.20 (getvar "TEXTSIZE"))))
      (list (+ (car result) (* textheight 4.0)) (cadr result) 0.0))))

;; La fila MEMORIAS muestra los resultados YA GUARDADOS; no debe volver a
;; calcular el movimiento ni pedir eje/cotas. La verificacion detallada por
;; secciones sigue disponible en el boton Verificacion. Esta tabla resumen
;; es inmediata y tambien funciona en vias antiguas cuyo eje externo ya no
;; pueda recuperarse.
(defun urb:create-road-memory-summary
  (road / data mov area length-value left right over-area base-area rows
   point textheight rowheight colwidth table row item handle)
  (setq data (urb:get-xdata-strings road "URB_VIA")
        mov (urb:road-movement-data road))
  (if (and (listp data) (> (length data) 18))
    (progn
      (setq base-area (atof (urb:safe-string (nth 17 data) "0"))
            length-value (atof (urb:safe-string (nth 18 data) "0"))
            left (atof (urb:safe-string (nth 14 data) "0"))
            right (atof (urb:safe-string (nth 15 data) "0"))
            ;; 2026-08-30: contorno = calzada; sobreancho ADICIONAL
            over-area (* length-value (+ left right))
            area (+ base-area over-area)
            rows
              (list
                (list "Via" (urb:safe-string (nth 1 data) ""))
                (list "Etapa / subetapa"
                  (strcat (urb:safe-string (nth 2 data) "") " / "
                    (urb:safe-string (nth 3 data) "")))
                (list "Perfil" (urb:safe-string (nth 4 data) ""))
                (list "Area total" (strcat (rtos area 2 2) " m2"))
                (list "Area base" (strcat (rtos base-area 2 2) " m2"))
                (list "Area sobreancho" (strcat (rtos over-area 2 2) " m2"))
                (list "Longitud" (strcat (rtos length-value 2 2) " m"))
                (list "Corte"
                  (strcat (urb:safe-string (if mov (nth 0 mov) nil) "0") " m3"))
                (list "Relleno"
                  (strcat (urb:safe-string (if mov (nth 1 mov) nil) "0") " m3"))
                (list "Metodo"
                  (urb:safe-string (if mov (nth 2 mov) nil) "SIN CALCULAR"))
                (list "Secciones / omitidas"
                  (strcat (urb:safe-string (if mov (nth 3 mov) nil) "0")
                    " / " (urb:safe-string (if mov (nth 4 mov) nil) "0")))
                (list "Ancho / profundidad"
                  (strcat (urb:safe-string (if mov (nth 5 mov) nil) "0")
                    " m / " (urb:safe-string (if mov (nth 6 mov) nil) "0") " m"))))
      (setq point (urb:road-memory-table-point road)
            textheight (* 0.60 (max 0.20 (getvar "TEXTSIZE")))
            rowheight (* textheight 2.20)
            colwidth (* textheight 18.0)
            table
              (vla-AddTable (urb:space) (vlax-3d-point point)
                (1+ (length rows)) 2 rowheight colwidth))
      (urb:ensure-layer "URB-VIA-TABLA" 4 T)
      (vla-put-Layer table "URB-VIA-TABLA")
      (vl-catch-all-apply 'vla-put-RegenerateTableSuppressed
        (list table :vlax-true))
      (vl-catch-all-apply 'vla-MergeCells (list table 0 0 0 1))
      (urb:set-table-text-safe table 0 0 "MEMORIA DE CANTIDADES DE VIA")
      (setq row 1)
      (foreach item rows
        (urb:set-table-text-safe table row 0 (car item))
        (urb:set-table-text-safe table row 1 (cadr item))
        (setq row (1+ row)))
      (vl-catch-all-apply 'vla-put-RegenerateTableSuppressed
        (list table :vlax-false))
      (vl-catch-all-apply 'vla-RecomputeTableBlock (list table :vlax-true))
      (setq handle (cdr (assoc 5 (entget road))))
      (urb:set-xdata-strings (vlax-vla-object->ename table)
        "URB_VIA_TABLA" (list handle))
      table)
    nil))

(defun urb:road-memory-table-visible-p (parent-handle / ss index ename data found app)
  (foreach app '("URB_VIA_TABLA" "URB_VIA_GEN")
    (if (not found)
      (progn
        (setq ss (ssget "_X" (list '(0 . "ACAD_TABLE") (list -3 (list app))))
              index 0)
        (if ss
          (repeat (sslength ss)
            (setq ename (ssname ss index)
                  data (urb:get-xdata-strings ename app))
            (if (and data (= (car data) parent-handle)) (setq found T))
            (setq index (1+ index)))))))
  found)

;; Lee las filas de verificacion GUARDADAS (ldata URB_VIA_AUDIT): primero
;; sobre el propio bloque/contorno, y como respaldo sobre la copia del
;; contorno DENTRO de la definicion del bloque empacado (el diccionario
;; de extension viaja con la copia).
(defun urb:road-audit-stored (road / v bname ent)
  (setq v (vl-catch-all-apply 'vlax-ldata-get (list road "URB_VIA_AUDIT")))
  (if (vl-catch-all-error-p v) (setq v nil))
  (if (null v)
    (progn
      (setq bname
        (vl-catch-all-apply
          '(lambda () (vla-get-Name (vlax-ename->vla-object road)))))
      (if (not (vl-catch-all-error-p bname))
        (progn
          (setq ent (cdr (assoc -2 (tblsearch "BLOCK" bname))))
          (while (and ent (null v))
            (setq v
              (vl-catch-all-apply 'vlax-ldata-get
                (list ent "URB_VIA_AUDIT")))
            (if (vl-catch-all-error-p v) (setq v nil))
            (setq ent (entnext ent)))))))
  (if (and v (listp v) (>= (length v) 4) (listp (car v))) v nil))

;; T si la superficie guardada de la via existe en el dibujo por NOMBRE
;; (sin abrir ningun prompt).
(defun urb:surface-available-p (name / found)
  (setq name (urb:safe-string name ""))
  (if (or (= name "") (urb:string-equal-p name "Seleccionar en dibujo")
          (urb:string-equal-p name "NO SELECCIONADA"))
    nil
    (progn
      (foreach item (urb:civil-surface-names)
        (if (urb:string-equal-p item name) (setq found T)))
      found)))

;; 2026-08-13 v3: MOSTRAR despliega la tabla ANCHA desde datos guardados;
;; si la via aun no los tiene, los CALCULA aqui mismo UNA vez -- pero
;; SOLO cuando es 100% seguro sin prompts: eje recuperable + rasante
;; guardada + superficie presente por nombre (pedido del usuario: que el
;; clic derecho no dependa de pasar antes por Verificacion). Sin esas
;; condiciones cae a la memoria resumida (la leccion de la v4.23.11:
;; jamas un recalculo que pueda preguntar o fallar a medias).
(defun urb:show-road-audit-table (road data / stored axis)
  (setq stored (urb:road-audit-stored road))
  (setq axis
    (urb:road-axis-recover road data
      (if (> (length data) 22) (nth 22 data) "")))
  (if (and (null stored)
           axis
           (urb:road-design-grade-records road data)
           (urb:surface-available-p
             (if (> (length data) 6) (nth 6 data) "")))
    (progn
      (prompt "\nCalculando la tabla de verificacion por primera vez...")
      (setq *urb-road-audit-point* nil)
      (vl-catch-all-apply 'urb:try-road-earthworks (list road axis))
      (setq stored (urb:road-audit-stored road))))
  (if stored
    (progn
      (setq *urb-road-audit-point* nil)
      (urb:draw-road-audit-table road axis
        (nth 0 stored) data (nth 2 stored) (nth 3 stored) (nth 1 stored)))
    nil))

(defun urb:set-road-memory-visibility
  (road show / data handle created visible old-busy)
  ;; El atributo MEMORIAS se comporta como un control de dos estados en
  ;; Properties: MOSTRAR/VISIBLE crea la tabla y OCULTAR/OCULTAS la borra.
  ;; La escritura del valor normalizado se silencia para no reactivar el
  ;; reactor del propio atributo.
  (setq data (urb:get-xdata-strings road "URB_VIA")
        handle (cdr (assoc 5 (entget road))))
  (if (and data handle)
    (if show
      (if (urb:road-memory-table-visible-p handle)
        T
        (progn
        (setq created (urb:show-road-audit-table road data))
        (if (not created)
          (progn
            (prompt
              (strcat "\nEsta via aun no tiene guardada su tabla de"
                      " verificacion: corra una vez el boton Verificacion"
                      " (o EDITAR); mientras tanto se muestra la memoria"
                      " resumida."))
            (setq created (urb:create-road-memory-summary road))))
        ;; Verifica el estado real despues de crear. No dependemos del valor
        ;; devuelto por AddTable ni de escrituras anidadas de atributos.
        (setq visible (urb:road-memory-table-visible-p handle))
        (setq old-busy *urb-memory-reactor-busy*
              *urb-memory-reactor-busy* T)
        ;; No reescribir MOSTRAR si ya esta normalizado: AutoCAD dispara
        ;; nuevamente el evento de Properties aun cuando el texto no cambia.
        (if (/=
              (strcase (urb:safe-string
                (cdr (assoc "MEMORIAS" (urb:block-attribute-values road))) ""))
              (if visible "MOSTRAR" "OCULTAR"))
          (mp:setatt-one road "MEMORIAS" (if visible "MOSTRAR" "OCULTAR")))
        (setq *urb-memory-reactor-busy* old-busy)
        ;; Los reactores de propiedades se ejecutan con alcance dinamico y
        ;; pueden reutilizar el simbolo local VISIBLE. Releer al retornar
        ;; garantiza un booleano estable incluso ante ese evento anidado.
        (if (urb:road-memory-table-visible-p
              (cdr (assoc 5 (entget road)))) T nil)))
      (progn
        (urb:delete-road-audit-tables handle)
        (setq old-busy *urb-memory-reactor-busy*
              *urb-memory-reactor-busy* T)
        (mp:setatt-one road "MEMORIAS" "OCULTAR")
        (setq *urb-memory-reactor-busy* old-busy)
        T))
    nil))

(defun urb:toggle-road-memory-command
  (/ selected road data handle visible)
  (setq selected (entsel "\nSeleccione la via para mostrar/ocultar sus memorias: "))
  (setq road (if selected (urb:road-parent-from-entity (car selected)) nil))
  (if (and road (setq data (urb:get-xdata-strings road "URB_VIA")))
    (progn
      (setq handle (cdr (assoc 5 (entget road)))
            visible (urb:road-memory-table-visible-p handle))
      (if visible
        (progn
          (urb:set-road-memory-visibility road nil)
          (prompt "\nMemorias de la via ocultas."))
        (progn
          (if (urb:set-road-memory-visibility road T)
            (prompt "\nMemorias de la via desplegadas.")))))
    (prompt "\nEl objeto seleccionado no es una via creada por el programa."))
  (princ))

(defun c:QMEMORIAVIA () (urb:toggle-road-memory-command))

;; ------------------------------------------------------------------
;; 5.7.0 PERFIL LONGITUDINAL DE LA VIA (esquema de cortes). Atributo
;; PERFIL del bloque de la via, gemelo de MEMORIAS: MOSTRAR lo dibuja y
;; OCULTAR lo borra (mismo reactor diferido). Se dibuja SOLO con las
;; filas ya guardadas de la verificacion (ldata URB_VIA_AUDIT): no pide
;; nada ni recalcula. Por abscisa, en el eje: subrasante = rasante -
;; cajon, delta = TN - subrasante, excavacion = max(delta, h) y lleno =
;; max(0, h - delta) con h = *urb-overexc-depth* (la regla de
;; urb:cut-fill-at). Queda en un bloque propio que se puede mover; al
;; ocultarlo se recuerda donde estaba y vuelve a salir ahi.
(setq *urb-profile-vexag* 10.0)   ; exageracion vertical del perfil

(defun urb:profile-interp (rows s index / prev result)
  (foreach row rows
    (if (null result)
      (if (<= s (nth 0 row))
        (setq result
          (if (and prev (> (nth 0 row) (nth 0 prev)))
            (+ (nth index prev)
               (* (- (nth index row) (nth index prev))
                  (/ (- s (nth 0 prev)) (- (nth 0 row) (nth 0 prev)))))
            (nth index row)))
        (setq prev row))))
  (if result result (nth index (last rows))))

(defun urb:profile-pline (pts color closed)
  (entmakex
    (append
      (list '(0 . "LWPOLYLINE") '(100 . "AcDbEntity") '(8 . "URB-VIA-PERFIL")
            (cons 62 color) '(100 . "AcDbPolyline")
            (cons 90 (length pts)) (cons 70 (if closed 1 0)))
      (mapcar '(lambda (p) (list 10 (car p) (cadr p))) pts))))

(defun urb:profile-text (pt h str color align)
  ;; align: 0 izquierda, 1 centro, 2 derecha; siempre centrado vertical
  (entmakex
    (list '(0 . "TEXT") '(8 . "URB-VIA-PERFIL") (cons 62 color)
          (list 10 (car pt) (cadr pt) 0.0) (list 11 (car pt) (cadr pt) 0.0)
          (cons 40 h) (cons 1 str) (cons 72 align) (cons 73 2))))

(defun urb:profile-text-rot (pt h str color align rot)
  (entmakex
    (list '(0 . "TEXT") '(8 . "URB-VIA-PERFIL") (cons 62 color)
          (list 10 (car pt) (cadr pt) 0.0) (list 11 (car pt) (cadr pt) 0.0)
          (cons 40 h) (cons 1 str) (cons 50 rot) (cons 72 align) (cons 73 2))))

(defun urb:profile-circle (pt r color)
  (entmakex
    (list '(0 . "CIRCLE") '(8 . "URB-VIA-PERFIL") (cons 62 color)
          (list 10 (car pt) (cadr pt) 0.0) (cons 40 r))))

;; 5.7.2 capa POR VIA (URB-VIA-PERFIL-<via>): quien abra el dibujo sin el
;; programa instalado puede prender/apagar cada perfil desde el
;; administrador de capas
(defun urb:profile-layer-name (name / out ch i)
  (setq out "" i 1 name (urb:safe-string name "VIA"))
  (while (<= i (strlen name))
    (setq ch (substr name i 1)
          out (strcat out (if (member ch '("<" ">" "/" "\\" "\"" ":" ";" "?" "*" "|" "," "=" "`")) "_" ch))
          i (1+ i)))
  (strcat "URB-VIA-PERFIL-" out))

;; posicion recordada del perfil: primero en la via, luego por NOMBRE de
;; via en el diccionario del dibujo (sobrevive a EDITAR, que re-empaca la
;; via y le cambia el handle)
(defun urb:profile-saved-point (road name / keep)
  (setq keep (vl-catch-all-apply 'vlax-ldata-get (list road "URB_VIA_PERFIL_PT")))
  (if (or (vl-catch-all-error-p keep) (not (and (listp keep) (numberp (car keep)))))
    (progn
      (setq keep (vl-catch-all-apply 'vlax-ldata-get (list "URB_PERFIL_POS" name)))
      (if (or (vl-catch-all-error-p keep) (not (and (listp keep) (numberp (car keep)))))
        (setq keep nil))))
  keep)

(defun urb:profile-save-point (road name pt)
  (if road (vl-catch-all-apply 'vlax-ldata-put (list road "URB_VIA_PERFIL_PT" pt)))
  (if (and name (/= name ""))
    (vl-catch-all-apply 'vlax-ldata-put (list "URB_PERFIL_POS" name pt))))

;; punto automatico: a la derecha de TODAS las vias y perfiles existentes,
;; a la altura de la via (antes caia encima de la agrupacion)
(defun urb:profile-auto-point (road th / ss i o mn mx maxx miny r)
  (foreach flt (list '((0 . "INSERT") (-3 ("URB_VIA"))) '((0 . "INSERT") (-3 ("URB_VIA_PERFIL"))))
    (setq ss (ssget "_X" flt) i 0)
    (if ss
      (repeat (sslength ss)
        (setq o (vlax-ename->vla-object (ssname ss i)) i (1+ i)
              r (vl-catch-all-apply 'vla-GetBoundingBox (list o 'mn 'mx)))
        (if (not (vl-catch-all-error-p r))
          (progn
            (setq mx (vlax-safearray->list mx))
            (if (or (null maxx) (> (car mx) maxx)) (setq maxx (car mx))))))))
  (setq r (vl-catch-all-apply 'vla-GetBoundingBox (list (vlax-ename->vla-object road) 'mn 'mx)))
  (if (not (vl-catch-all-error-p r))
    (setq miny (cadr (vlax-safearray->list mn))))
  (list (+ (if maxx maxx 0.0) (* th 25.0)) (if miny miny 0.0) 0.0))

;; marcas del perfil: pozos y cotas de referencia de la rasante.
;; Fuentes guardadas al tomar las cotas (ldata URB_VIA_RASANTE_SRC) y,
;; para vias hechas antes, pozos del modelo sobre el eje de la via.
;; Cada marca: (abscisa-local cota tipo nombre)
(defun urb:road-ldata-stored (road key / v bname ent)
  (setq v (vl-catch-all-apply 'vlax-ldata-get (list road key)))
  (if (vl-catch-all-error-p v) (setq v nil))
  (if (null v)
    (progn
      (setq bname (vl-catch-all-apply '(lambda () (vla-get-Name (vlax-ename->vla-object road)))))
      (if (not (vl-catch-all-error-p bname))
        (progn
          (setq ent (cdr (assoc -2 (tblsearch "BLOCK" bname))))
          (while (and ent (null v))
            (setq v (vl-catch-all-apply 'vlax-ldata-get (list ent key)))
            (if (vl-catch-all-error-p v) (setq v nil))
            (setq ent (entnext ent)))))))
  v)

(defun urb:road-profile-marks (road data len / src out ref axis axis-start span direction
                               mode ss i e obj bname atts z q raw st half mov w)
  (setq src (urb:road-ldata-stored road "URB_VIA_RASANTE_SRC"))
  (foreach m (if (listp src) src nil)
    (if (and (listp m) (numberp (car m)) (numberp (cadr m))
             (>= (car m) -0.5) (<= (car m) (+ len 0.5)))
      (setq out (cons m out))))
  ;; pozos del modelo sobre la via (vias viejas o pozos intermedios que
  ;; no se clickearon)
  (setq ref (vl-catch-all-apply 'urb:anden-road-grade-for (list road)))
  (if (and ref (not (vl-catch-all-error-p ref)))
    (progn
      (setq axis (nth 0 ref) axis-start (nth 2 ref) span (nth 3 ref)
            direction (nth 4 ref) mode (nth 5 ref)
            mov (urb:road-movement-data road)
            w (if (and mov (> (length mov) 5)) (atof (urb:safe-string (nth 5 mov) "0")) 0.0)
            half (+ (* 0.5 (max w 6.0)) 1.0)
            ss (ssget "_X" '((0 . "INSERT"))) i 0)
      (if ss
        (repeat (sslength ss)
          (setq e (ssname ss i) i (1+ i))
          (if (wcmatch (strcase (cdr (assoc 2 (entget e)))) "MP_PUNTO_POZO*,`*U*")
            (progn
              (setq obj (vlax-ename->vla-object e)
                    bname (vl-catch-all-apply 'vla-get-EffectiveName (list obj)))
              (if (and (not (vl-catch-all-error-p bname))
                       (wcmatch (strcase bname) "MP_PUNTO_POZO*"))
                (progn
                  (setq q (vl-catch-all-apply 'vlax-curve-getClosestPointTo
                            (list axis (cdr (assoc 10 (entget e))))))
                  (if (and (not (vl-catch-all-error-p q))
                           (<= (distance (list (car q) (cadr q))
                                         (list (car (cdr (assoc 10 (entget e))))
                                               (cadr (cdr (assoc 10 (entget e))))))
                               half))
                    (progn
                      (setq raw (vlax-curve-getDistAtPoint axis q)
                            st (if (urb:string-equal-p mode "LOCAL")
                                 (if (urb:string-equal-p direction "Final")
                                   (- (+ axis-start span) raw) (- raw axis-start))
                                 raw))
                      (if (and (>= st -0.5) (<= st (+ len 0.5))
                               (not (vl-some '(lambda (m) (and (= (nth 2 m) "POZO")
                                                               (< (abs (- (car m) st)) 1.0)))
                                             out)))
                        (progn
                          (setq atts (mp:att-alist e)
                                z (mp:numeric-real (mp:getval "COTA_TAPA" atts "")))
                          (if (null z) (setq z (mp:numeric-real (mp:getval "COTA_TN_INI" atts ""))))
                          (if z
                            (setq out (cons (list st z "POZO"
                                                  (mp:getval "ID" atts (mp:getval "CODIGO" atts "")))
                                            out)))))))))))))))
  (vl-sort out '(lambda (a b) (< (car a) (car b)))))

;; hatch solido con transparencia; la polilinea de borde se borra
(defun urb:profile-hatch (pts color / pl hatch)
  (setq pl (urb:profile-pline pts color T))
  (if pl
    (progn
      (setq hatch
        (vl-catch-all-apply 'urb:add-solid-hatch
          (list (vlax-ename->vla-object pl) "URB-VIA-PERFIL" color)))
      (entdel pl)
      (if (vl-catch-all-error-p hatch)
        nil
        (progn
          (vl-catch-all-apply 'vla-put-EntityTransparency (list hatch "55"))
          (vlax-vla-object->ename hatch))))
    nil))

;; INSERTs de perfil de la via (parent-handle nil = todos)
(defun urb:road-profile-entities (parent-handle / ss i e d out)
  (setq ss (ssget "_X" '((0 . "INSERT") (-3 ("URB_VIA_PERFIL")))) i 0)
  (if ss
    (repeat (sslength ss)
      (setq e (ssname ss i)
            d (urb:get-xdata-strings-entget e "URB_VIA_PERFIL"))
      (if (and d (or (null parent-handle) (= (car d) parent-handle)))
        (setq out (cons e out)))
      (setq i (1+ i))))
  out)

(defun urb:road-profile-visible-p (parent-handle)
  (if (urb:road-profile-entities parent-handle) T nil))

;; perfiles cuya via ya no existe (la via se re-empaco al EDITAR y
;; cambio de handle): se borran para no dejar perfiles viejos sueltos
(defun urb:delete-orphan-road-profiles (/ e d p n)
  (setq n 0)
  (foreach e (urb:road-profile-entities nil)
    (setq d (urb:get-xdata-strings-entget e "URB_VIA_PERFIL")
          p (if d (handent (car d)) nil))
    (if (or (null p) (null (entget p)))
      (progn (urb:profile-remove-insert e nil) (setq n (1+ n)))))
  n)

;; 5.7.2: borra un perfil guardando ANTES donde estaba (en la via y por
;; nombre de via) y retira su definicion de bloque, para que mostrar/
;; ocultar no vaya acumulando definiciones URB_PERFIL_* en el dibujo
(defun urb:profile-remove-insert (e road / ed d bname)
  (setq ed (entget e) d (urb:get-xdata-strings-entget e "URB_VIA_PERFIL"))
  (if (= (cdr (assoc 0 ed)) "INSERT")
    (progn
      (urb:profile-save-point road (if (> (length d) 1) (cadr d) "") (cdr (assoc 10 ed)))
      (setq bname (cdr (assoc 2 ed)))
      (entdel e)
      (if (wcmatch bname "URB_PERFIL_*")
        (vl-catch-all-apply
          '(lambda () (vla-Delete (vla-Item (vla-get-Blocks (urb:doc)) bname))))))
    (entdel e)))

(defun urb:draw-road-profile
  (road data stored / audit rows h vx d0 d1 len s0 th rh obj minpt maxpt
   base x0 y0 yp zmin zmax zbase ztop pts-tn pts-ras pts-sub pts-bot
   pts-fill maxfill ents e z s step stations y k tn ras sub delta exc fil
   labels vals txt color depth handle bname bdef ins cut fill name keep)
  (setq audit (nth 0 stored)
        rows (vl-remove-if-not
               '(lambda (r) (and (listp r) (> (length r) 3)
                                 (numberp (nth 0 r)) (numberp (nth 1 r))
                                 (numberp (nth 2 r)) (numberp (nth 3 r))))
               audit)
        h (if (numberp *urb-overexc-depth*) (max 0.0 *urb-overexc-depth*) 0.0)
        vx (if (numberp *urb-profile-vexag*) *urb-profile-vexag* 10.0)
        handle (cdr (assoc 5 (entget road))))
  (if (< (length rows) 2)
    (progn (prompt "\nLa verificacion guardada no tiene secciones suficientes para el perfil.") nil)
    (progn
      (setq d0 (nth 0 (car rows)) d1 (nth 0 (last rows)) len (- d1 d0)
            s0 (urb:station-number (urb:safe-string (nth 10 data) "0+000"))
            depth (- (nth 2 (car rows)) (nth 3 (car rows)))
            th (max (* 0.60 (max 0.20 (getvar "TEXTSIZE"))) (/ len 150.0))
            rh (* th 2.6))
      ;; 5.7.2 punto: (1) donde el usuario lo dejo la ultima vez (por via o
      ;; por nombre); (2) desde el clic derecho, el punto que el usuario
      ;; indique; (3) automatico, a la derecha de TODAS las vias y perfiles
      ;; (antes caia sobre la agrupacion)
      (setq name (urb:safe-string (nth 1 data) "VIA")
            keep (urb:profile-saved-point road name))
      (cond
        (keep (setq base keep))
        ((and *urb-profile-ask-point*
              (setq base (getpoint (strcat "\nUbique el perfil de " name
                                           " (esquina inferior izquierda de la reticula)"
                                           " <Enter = automatico>: "))))
          (setq base (list (car base) (cadr base) 0.0)))
        (T (setq base (urb:profile-auto-point road th))))
      (urb:profile-save-point road name base)
      (setq x0 (car base) y0 (cadr base)
            yp (+ y0 (* 6.0 rh) (* 2.0 th)))
      ;; alturas por seccion
      (setq zmin nil zmax nil)
      (foreach r rows
        (setq tn (nth 1 r) ras (nth 2 r) sub (nth 3 r) delta (- tn sub)
              exc (max delta h) fil (max 0.0 (- h delta)))
        (setq pts-tn (cons (list (+ x0 (- (nth 0 r) d0)) tn) pts-tn)
              pts-ras (cons (list (+ x0 (- (nth 0 r) d0)) ras) pts-ras)
              pts-sub (cons (list (+ x0 (- (nth 0 r) d0)) sub) pts-sub)
              pts-bot (cons (list (+ x0 (- (nth 0 r) d0)) (- tn exc)) pts-bot)
              pts-fill (cons (list (+ x0 (- (nth 0 r) d0)) (+ (- tn exc) fil)) pts-fill))
        (if (or (null maxfill) (> fil maxfill)) (setq maxfill fil))
        (foreach z (list tn ras (- tn exc))
          (if (or (null zmin) (< z zmin)) (setq zmin z))
          (if (or (null zmax) (> z zmax)) (setq zmax z))))
      (setq zbase (float (fix (- zmin 0.2)))
            ztop (float (1+ (fix (+ zmax 0.05)))))
      ;; cota -> Y del dibujo
      (defun urb:pf-y (z) (+ yp (* (- z zbase) vx)))
      (defun urb:pf-pts (pts) (mapcar '(lambda (p) (list (car p) (urb:pf-y (cadr p)))) pts))
      (setq pts-tn (urb:pf-pts (reverse pts-tn)) pts-ras (urb:pf-pts (reverse pts-ras))
            pts-sub (urb:pf-pts (reverse pts-sub)) pts-bot (urb:pf-pts (reverse pts-bot))
            pts-fill (urb:pf-pts (reverse pts-fill)))
      (urb:ensure-layer "URB-VIA-PERFIL" 4 T)
      ;; reticula de cotas cada metro
      (setq z zbase)
      (while (<= z ztop)
        (setq ents (cons (urb:profile-pline
                           (list (list x0 (urb:pf-y z)) (list (+ x0 len) (urb:pf-y z))) 8 nil) ents)
              ents (cons (urb:profile-text (list (- x0 th) (urb:pf-y z)) (* th 0.8)
                           (rtos z 2 0) 8 2) ents)
              z (+ z 1.0)))
      ;; rellenos: excavacion, lleno, cajon
      (setq ents (cons (urb:profile-hatch (append pts-tn (reverse pts-bot)) 1) ents))
      (if (> maxfill 0.001)
        (setq ents (cons (urb:profile-hatch (append pts-fill (reverse pts-bot)) 3) ents)))
      (setq ents (cons (urb:profile-hatch (append pts-ras (reverse pts-sub)) 5) ents))
      ;; lineas
      (setq ents (cons (urb:profile-pline pts-bot 1 nil) ents)
            ents (cons (urb:profile-pline pts-sub 8 nil) ents)
            ents (cons (urb:profile-pline pts-tn 32 nil) ents)
            ents (cons (urb:profile-pline pts-ras 5 nil) ents))
      ;; 5.7.2 pozos y cotas de referencia de la rasante (pedido del
      ;; usuario: "que me muestre dibujado el pozo y su elevacion... y si la
      ;; cota inicial es con respecto a una via que aparezca la cota de la
      ;; via"). Linea vertical + circulo en la cota + rotulo vertical.
      (foreach m (vl-catch-all-apply 'urb:road-profile-marks (list road data len))
        (if (and (listp m) (numberp (car m)) (numberp (cadr m)))
          (progn
            (setq s (max 0.0 (min len (car m)))
                  z (cadr m)
                  color (cond ((= (nth 2 m) "POZO") 6) ((= (nth 2 m) "VIA") 5) (T 2))
                  txt (cond
                        ((= (nth 2 m) "POZO")
                          (strcat "POZO " (urb:safe-string (nth 3 m) "") "  cota " (rtos z 2 2)))
                        ((= (nth 2 m) "VIA")
                          (strcat (urb:safe-string (nth 3 m) "VIA") "  rasante " (rtos z 2 2)))
                        (T (strcat "Cota " (rtos z 2 2)))))
            (setq ents (cons (urb:profile-pline
                               (list (list (+ x0 s) (urb:pf-y zbase)) (list (+ x0 s) (urb:pf-y ztop)))
                               color nil) ents)
                  ents (cons (urb:profile-circle (list (+ x0 s) (urb:pf-y z)) (* th 0.45) color) ents)
                  ents (cons (urb:profile-text-rot (list (- (+ x0 s) (* th 0.5)) (- (urb:pf-y ztop) (* th 0.3)))
                               (* th 0.75) txt color 2 (* 0.5 pi)) ents)))))
      ;; abscisas de la guitarra
      ;; abscisas REDONDAS (0+020, 0+040...) mas el inicio y el final;
      ;; se omite la redonda que quede pegada a un extremo
      (setq step (cond ((<= len 120.0) 10.0) ((<= len 400.0) 20.0) (T 50.0))
            s (- (* step (1+ (fix (/ (+ s0 0.001) step)))) s0)
            stations (list 0.0))
      (if (< s (* 0.45 step)) (setq s (+ s step)))
      (while (< s (- len (* 0.45 step)))
        (setq stations (cons s stations) s (+ s step)))
      (setq stations (reverse (cons len stations)))
      ;; guitarra: 6 filas
      (setq labels '("Abscisa" "Cota TN" "Rasante" "Subrasante" "h excavacion" "h lleno"))
      (setq k 0)
      (repeat 7
        (setq ents (cons (urb:profile-pline
                           (list (list (- x0 (* th 15.0)) (+ y0 (* k rh)))
                                 (list (+ x0 len (* th 3.0)) (+ y0 (* k rh)))) 8 nil) ents)
              k (1+ k)))
      (setq k 0)
      (foreach txt labels
        (setq y (+ y0 (* (- 5 k) rh) (* 0.5 rh))
              ents (cons (urb:profile-text (list (- x0 (* th 14.5)) y) th txt 7 0) ents)
              k (1+ k)))
      (foreach s stations
        (setq tn (urb:profile-interp rows (+ d0 s) 1)
              ras (urb:profile-interp rows (+ d0 s) 2)
              sub (urb:profile-interp rows (+ d0 s) 3)
              delta (- tn sub) exc (max delta h) fil (max 0.0 (- h delta))
              vals (list (urb:format-station (+ s0 s)) (rtos tn 2 2) (rtos ras 2 2)
                         (rtos sub 2 2) (rtos exc 2 2) (rtos fil 2 2))
              k 0)
        ;; linea vertical de la abscisa, solo en la reticula (no tacha los
        ;; numeros de la guitarra)
        (setq ents (cons (urb:profile-pline
                           (list (list (+ x0 s) (urb:pf-y zbase)) (list (+ x0 s) (urb:pf-y ztop))) 8 nil) ents))
        (foreach txt vals
          (setq y (+ y0 (* (- 5 k) rh) (* 0.5 rh))
                color (cond ((and (= k 4) (> exc (+ h 0.001))) 1)
                            ((and (= k 5) (> fil 0.0)) 3)
                            (T 7))
                ents (cons (urb:profile-text (list (+ x0 s) y) (* th 0.8) txt color 1) ents)
                k (1+ k))))
      ;; titulo y leyenda
      (setq cut (nth 2 stored) fill (nth 3 stored))
      (setq ents (cons (urb:profile-text (list x0 (+ (urb:pf-y ztop) (* th 4.5))) (* th 1.3)
                         (strcat "PERFIL LONGITUDINAL - " name) 7 0) ents)
            ents (cons (urb:profile-text (list x0 (+ (urb:pf-y ztop) (* th 2.5))) (* th 0.8)
                         (strcat "Escala H 1:1  V x" (rtos vx 2 0)
                                 " | cajon " (rtos depth 2 2) " m | sobreexcavacion "
                                 (rtos h 2 2) " m | excavacion "
                                 (if (numberp cut) (rtos cut 2 2) "-") " m3 | lleno "
                                 (if (numberp fill) (rtos fill 2 2) "-") " m3") 7 0) ents)
            ents (cons (urb:profile-text (list x0 (+ (urb:pf-y ztop) (* th 1.0))) (* th 0.8)
                         "Cafe: terreno natural | Azul: rasante y cajon | Rojo: excavacion | Verde: lleno | Magenta: pozos" 8 0) ents))
      (setq ents (vl-remove nil ents))
      ;; bloque propio para poder moverlo como una pieza
      (setq bname (strcat "URB_PERFIL_" handle "_" (itoa (getvar "MILLISECS")))
            bdef (vla-Add (vla-get-Blocks (urb:doc)) (vlax-3d-point base) bname))
      (if (vl-catch-all-error-p
            (vl-catch-all-apply 'vla-CopyObjects
              (list (urb:doc)
                    (urb:object-array-variant (mapcar 'vlax-ename->vla-object ents))
                    bdef)))
        (progn
          ;; sin bloque: se dejan sueltas pero etiquetadas
          (foreach e ents (urb:set-xdata-strings e "URB_VIA_PERFIL" (list handle name)))
          (prompt "\nAVISO: el perfil quedo en piezas sueltas (no se pudo agrupar en bloque).")
          (length ents))
        (progn
          (foreach e ents (entdel e))
          (setq ins (vla-InsertBlock (urb:space) (vlax-3d-point base) bname 1.0 1.0 1.0 0.0))
          (urb:ensure-layer (urb:profile-layer-name name) 4 T)
          (vla-put-Layer ins (urb:profile-layer-name name))
          (urb:set-xdata-strings (vlax-vla-object->ename ins) "URB_VIA_PERFIL" (list handle name))
          (prompt (strcat "\nPerfil de " name ": " (itoa (length stations))
                          " abscisas, " (itoa (length rows)) " secciones."))
          1)))))

(defun urb:set-road-profile-visibility
  (road show / data handle stored axis n old-busy ents ins pt had-table)
  (setq data (urb:get-xdata-strings road "URB_VIA")
        handle (cdr (assoc 5 (entget road))))
  (if (and data handle)
    (progn
      ;; recordar donde estaba (si el usuario lo movio) y borrarlo
      (setq ents (urb:road-profile-entities handle))
      (foreach ins ents (urb:profile-remove-insert ins road))
      (if show
        (progn
          (urb:delete-orphan-road-profiles)
          (setq stored (urb:road-audit-stored road))
          ;; misma regla que MEMORIAS: calcular aqui solo si es 100% seguro
          (if (null stored)
            (progn
              (setq axis (urb:road-axis-recover road data
                           (if (> (length data) 22) (nth 22 data) "")))
              (if (and axis
                       (urb:road-design-grade-records road data)
                       (urb:surface-available-p (if (> (length data) 6) (nth 6 data) "")))
                (progn
                  (prompt "\nCalculando la verificacion por primera vez...")
                  (setq had-table (urb:road-memory-table-visible-p handle)
                        *urb-road-audit-point* nil)
                  (vl-catch-all-apply 'urb:try-road-earthworks (list road axis))
                  (if (not had-table) (urb:delete-road-audit-tables handle))
                  (setq stored (urb:road-audit-stored road))))))
          (if stored
            (setq n (vl-catch-all-apply 'urb:draw-road-profile (list road data stored)))
            (alert
              (strcat "No se puede dibujar el perfil de "
                      (urb:safe-string (nth 1 data) "la via") ":\n"
                      "la via no tiene guardada su verificacion de movimiento de tierras"
                      (cond
                        ((null axis) " y no se encontro su EJE.")
                        ((null (urb:road-design-grade-records road data))
                          " y no tiene RASANTE guardada.")
                        ((not (urb:surface-available-p (if (> (length data) 6) (nth 6 data) "")))
                          (strcat " y la superficie '" (urb:safe-string (nth 6 data) "")
                                  "' no esta en el dibujo."))
                        (T "."))
                      "\n\nCorra una vez EDITAR (o Verificacion) sobre la via y vuelva a pedir el perfil.")))
          (if (vl-catch-all-error-p n)
            (progn
              (alert (strcat "ERROR al dibujar el perfil: " (vl-catch-all-error-message n)))
              (setq n nil)))))
      (setq old-busy *urb-memory-reactor-busy* *urb-memory-reactor-busy* T)
      (if (/= (strcase (urb:safe-string
                (cdr (assoc "PERFIL" (urb:block-attribute-values road))) ""))
              (if (and show n) "MOSTRAR" "OCULTAR"))
        (vl-catch-all-apply 'mp:setatt-one
          (list road "PERFIL" (if (and show n) "MOSTRAR" "OCULTAR"))))
      (setq *urb-memory-reactor-busy* old-busy)
      (if show (if n T nil) T))
    nil))

;; 5.7.1: clic derecho "Mostrar/ocultar perfil" (lo agrega la cinta .NET,
;; igual que el de memorias). Toggle sobre las VIAS de la seleccion.
(defun c:QPERFILSEL (/ ss i road h done shown hidden failed *urb-profile-ask-point*)
  ;; desde el clic derecho SI se puede pedir el punto la primera vez
  (setq *urb-profile-ask-point* T)
  (setq ss (ssget "_I"))
  (if (null ss)
    (progn (prompt "\nSeleccione vias: ") (setq ss (ssget))))
  (if ss
    (progn
      (setq i 0 shown 0 hidden 0 failed 0)
      (repeat (sslength ss)
        (setq road (urb:road-parent-from-entity (ssname ss i)))
        (if (and road (not (member road done)))
          (progn
            (setq done (cons road done)
                  h (cdr (assoc 5 (entget road))))
            (if (urb:road-profile-visible-p h)
              (progn (urb:set-road-profile-visibility road nil)
                     (setq hidden (1+ hidden)))
              (if (urb:set-road-profile-visibility road T)
                (setq shown (1+ shown))
                (setq failed (1+ failed))))))
        (setq i (1+ i)))
      (sssetfirst nil nil)
      (prompt (strcat "\nPerfil: " (itoa shown) " mostrado(s), " (itoa hidden)
                      " oculto(s)" (if (> failed 0) (strcat ", " (itoa failed) " sin datos") "")
                      "."))
      (if (and (= (length done) 0))
        (prompt "\nLa seleccion no tiene vias creadas por el programa.")))
    (prompt "\nNada seleccionado."))
  (princ))

;; 2026-08-13: toggle sobre la SELECCION ACTUAL, sin preguntar nada --
;; lo dispara el menu contextual de clic derecho ("Mostrar/ocultar
;; memorias") que agrega la cinta .NET. Acepta vias y tramos mezclados.
(defun c:QMEMORIASEL (/ ss i en road base atts done shown hidden)
  (setq ss (ssget "_I"))
  (if (null ss)
    (progn
      (prompt "\nSeleccione vias o tramos: ")
      (setq ss (ssget))))
  (if ss
    (progn
      (setq i 0 shown 0 hidden 0)
      (repeat (sslength ss)
        (setq en (ssname ss i) done nil)
        ;; via del programa?
        (setq road (urb:road-parent-from-entity en))
        (if road
          (progn
            (setq done T)
            (if (urb:road-memory-table-visible-p
                  (cdr (assoc 5 (entget road))))
              (progn
                (urb:set-road-memory-visibility road nil)
                (setq hidden (1+ hidden)))
              (if (urb:set-road-memory-visibility road T)
                (setq shown (1+ shown))))))
        ;; tramo de red?
        (if (not done)
          (progn
            (setq atts
              (vl-catch-all-apply 'mp:att-alist (list en)))
            (if (vl-catch-all-error-p atts) (setq atts nil))
            (setq base
              (vl-catch-all-apply 'mp:infer-base
                (list (cdr (assoc 2 (entget en))) atts)))
            (if (vl-catch-all-error-p base) (setq base nil))
            (if (and base (mp:base-is-tramo base))
              (progn
                (setq done T)
                (if (mp:tramo-memory-table-visible-p
                      (cdr (assoc 5 (entget en))))
                  (progn
                    (mp:set-tramo-memory-visibility en nil)
                    (setq hidden (1+ hidden)))
                  (if (mp:set-tramo-memory-visibility en T)
                    (setq shown (1+ shown))))))))
        (setq i (1+ i)))
      (sssetfirst nil nil)
      (prompt
        (strcat "\nMemorias: " (itoa shown) " mostrada(s), "
                (itoa hidden) " oculta(s).")))
    (prompt "\nNada seleccionado."))
  (princ))

(defun mp:delete-tramo-memory-tables (parent-handle / ss i en data count)
  (setq count 0
        ss (ssget "_X" '((0 . "ACAD_TABLE") (-3 ("MP_TRAMO_TABLA"))))
        i 0)
  (if ss
    (repeat (sslength ss)
      (setq en (ssname ss i)
            data (urb:get-xdata-strings en "MP_TRAMO_TABLA"))
      (if (and data (= (car data) parent-handle))
        (if (urb:safe-delete (vlax-ename->vla-object en))
          (setq count (1+ count))))
      (setq i (1+ i))))
  count)

(defun mp:create-tramo-memory-summary
  (tramo vals / rows point-table textheight rowheight colwidth table
   row item handle)
  (setq rows
    (list
      (list "Red" (mp:getval "RED" vals (mp:getval "TIPO_RED" vals "")))
      (list "Tramo"
        (strcat (mp:getval "POZO_INI" vals "?") " - "
          (mp:getval "POZO_FIN" vals "?")))
      (list "Longitud" (strcat (mp:getval "LONGITUD" vals "0") " m"))
      (list "Metodo" (mp:getval "METODO_CANTIDADES" vals "SIN CALCULAR"))
      (list "Excavacion" (strcat (mp:getval "EXCAVACION_M3" vals "0") " m3"))
      (list "Cama" (strcat (mp:getval "CAMA_M3" vals "0") " m3"))
      (list "Volumen elemento"
        (strcat (mp:getval "VOLUMEN_ELEMENTO_M3" vals "0") " m3"))
      (list "Relleno" (strcat (mp:getval "RELLENO_M3" vals "0") " m3"))
      (list "Cimentacion triturado"
        (strcat (mp:getval "TRITURADO_M3" vals "-") " m3"))
      (list "Relleno recebo" (strcat (mp:getval "RECEBO_M3" vals "-") " m3"))
      (list "Entibado <=3m"
        (strcat (mp:getval "ENTIBADO_LE3_M2" vals "-") " m2"))
      (list "Entibado >3m"
        (strcat (mp:getval "ENTIBADO_GT3_M2" vals "-") " m2"))
      (list "Sobrante" (strcat (mp:getval "SOBRANTE_M3" vals "0") " m3"))
      (list "Reposicion" (strcat (mp:getval "REPOSICION_M2" vals "0") " m2"))))
  (setq point-table (urb:road-memory-table-point tramo)
        textheight (* 0.60 (max 0.20 (getvar "TEXTSIZE")))
        rowheight (* textheight 2.20)
        colwidth (* textheight 18.0)
        table
          (vla-AddTable (urb:space) (vlax-3d-point point-table)
            (1+ (length rows)) 2 rowheight colwidth))
  (urb:ensure-layer "PPTO-TABLAS-MEMORIA" 4 T)
  (vla-put-Layer table "PPTO-TABLAS-MEMORIA")
  (vl-catch-all-apply 'vla-put-RegenerateTableSuppressed
    (list table :vlax-true))
  (vl-catch-all-apply 'vla-MergeCells (list table 0 0 0 1))
  (urb:set-table-text-safe table 0 0 "MEMORIA DE CANTIDADES DEL TRAMO")
  (setq row 1)
  (foreach item rows
    (urb:set-table-text-safe table row 0 (car item))
    (urb:set-table-text-safe table row 1 (cadr item))
    (setq row (1+ row)))
  (vl-catch-all-apply 'vla-put-RegenerateTableSuppressed
    (list table :vlax-false))
  (vl-catch-all-apply 'vla-RecomputeTableBlock (list table :vlax-true))
  (setq handle (cdr (assoc 5 (entget tramo))))
  (urb:set-xdata-strings (vlax-vla-object->ename table)
    "MP_TRAMO_TABLA" (list handle))
  table)

(defun mp:create-tramo-memory-table
  (tramo / obj vals base cached length-value diameter bedding width sample
   frac tn key bottom depth area distance-value previous-distance prev-area
   ds volume cumulative rows row table point-table textheight rowheight
   colwidth columns item col row-index handle)
  (setq obj (vlax-ename->vla-object tramo)
        vals (mp:att-alist tramo)
        base (mp:infer-base (vla-get-EffectiveName obj) vals)
        cached (mp:read-tramo-memory-samples tramo))
  ;; Tramos creados/editados desde 4.23.4 conservan el perfil que ya se
  ;; uso para calcular cantidades. Mostrar la tabla solo lo lee: no vuelve
  ;; a consultar SUP_TN y no congela Civil 3D. Los tramos anteriores usan
  ;; una memoria resumen honesta con sus cantidades guardadas.
  (if (or (not (mp:gravity-tramo-p base)) (null cached))
    (mp:create-tramo-memory-summary tramo vals)
    (progn
      (setq length-value
              (mp:number-or (mp:getval "LONGITUD" vals "0") 0.0)
            diameter (* 0.0254
              (mp:number-or (mp:getval "DIAMETRO" vals "0") 0.0))
            bedding (mp:number-or (mp:getval "ESPESOR_CAMA" vals "0.10") 0.10)
            width (mp:number-or (mp:getval "ANCHO_ZANJA" vals "0") 0.0)
            cumulative 0.0)
      (foreach sample cached
        (setq frac (nth 0 sample)
              tn (nth 1 sample)
              key (nth 2 sample)
              depth (max 0.0 (nth 3 sample))
              bottom (- key diameter bedding)
              area (* width depth)
              distance-value (* frac length-value)
              volume 0.0)
        (if (and prev-area previous-distance)
          (setq ds (- distance-value previous-distance)
                volume (* 0.5 (+ prev-area area) ds)
                cumulative (+ cumulative volume)))
        (setq rows
          (append rows
            (list (list distance-value tn key bottom depth area
                    volume cumulative))))
        (setq prev-area area previous-distance distance-value))
      (setq point-table (urb:road-memory-table-point tramo)
            textheight (* 0.60 (max 0.20 (getvar "TEXTSIZE")))
            rowheight (* textheight 2.20)
            colwidth (* textheight 11.0)
            table
              (vla-AddTable (urb:space) (vlax-3d-point point-table)
                (+ (length rows) 3) 8 rowheight colwidth))
      (urb:ensure-layer "PPTO-TABLAS-MEMORIA" 4 T)
      (vla-put-Layer table "PPTO-TABLAS-MEMORIA")
      (vl-catch-all-apply 'vla-put-RegenerateTableSuppressed
        (list table :vlax-true))
      (vl-catch-all-apply 'vla-MergeCells (list table 0 0 0 7))
      (urb:set-table-text-safe table 0 0
        (strcat "MEMORIA MOVIMIENTO DE TIERRAS - "
          (mp:getval "POZO_INI" vals "?") " - "
          (mp:getval "POZO_FIN" vals "?")))
      (setq columns
        '("Distancia" "TN/ref." "Cota clave" "Fondo zanja"
          "Profundidad" "Area exc." "Vol. tramo" "Vol. acum."))
      (setq col 0)
      (foreach item columns
        (urb:set-table-text-safe table 1 col item)
        (setq col (1+ col)))
      (setq row-index 2)
      (foreach row rows
        (setq col 0)
        (foreach item row
          (urb:set-table-text-safe table row-index col (rtos item 2 3))
          (setq col (1+ col)))
        (setq row-index (1+ row-index)))
      (urb:set-table-text-safe table row-index 0 "TOTAL EXCAVACION")
      (urb:set-table-text-safe table row-index 7 (rtos cumulative 2 3))
      (vl-catch-all-apply 'vla-put-RegenerateTableSuppressed
        (list table :vlax-false))
      (vl-catch-all-apply 'vla-RecomputeTableBlock (list table :vlax-true))
      (setq handle (cdr (assoc 5 (entget tramo))))
      (urb:set-xdata-strings (vlax-vla-object->ename table)
        "MP_TRAMO_TABLA" (list handle))
      table)))

(defun mp:tramo-memory-table-visible-p (parent-handle / ss i en data found)
  (setq ss (ssget "_X" '((0 . "ACAD_TABLE") (-3 ("MP_TRAMO_TABLA"))))
        i 0)
  (if ss
    (repeat (sslength ss)
      (setq en (ssname ss i)
            data (urb:get-xdata-strings en "MP_TRAMO_TABLA"))
      (if (and data (= (car data) parent-handle)) (setq found T))
      (setq i (1+ i))))
  found)

(defun mp:set-tramo-memory-visibility
  (tramo show / handle table created visible old-busy)
  (setq handle (cdr (assoc 5 (entget tramo))))
  (if handle
    (if show
      (if (mp:tramo-memory-table-visible-p handle)
        T
        (progn
        (setq table (mp:create-tramo-memory-table tramo)
              created (if table T nil))
        (setq visible (mp:tramo-memory-table-visible-p handle))
        (setq old-busy *urb-memory-reactor-busy*
              *urb-memory-reactor-busy* T)
        (if (/=
              (strcase (urb:safe-string
                (cdr (assoc "MEMORIAS" (urb:block-attribute-values tramo))) ""))
              (if visible "MOSTRAR" "OCULTAR"))
          (mp:setatt-one tramo "MEMORIAS" (if visible "MOSTRAR" "OCULTAR")))
        (setq *urb-memory-reactor-busy* old-busy)
        (if (mp:tramo-memory-table-visible-p
              (cdr (assoc 5 (entget tramo)))) T nil)))
      (progn
        (mp:delete-tramo-memory-tables handle)
        (setq old-busy *urb-memory-reactor-busy*
              *urb-memory-reactor-busy* T)
        (mp:setatt-one tramo "MEMORIAS" "OCULTAR")
        (setq *urb-memory-reactor-busy* old-busy)
        T))
    nil))

(defun mp:toggle-tramo-memory-command (/ pick tramo obj vals base handle visible)
  (setq pick (entsel "\nSeleccione el tramo para mostrar/ocultar sus memorias: ")
        tramo (if pick (car pick) nil))
  (if tramo
    (progn
      (setq obj (vlax-ename->vla-object tramo)
            vals (mp:att-alist tramo)
            base (mp:infer-base (vla-get-EffectiveName obj) vals))
      (if (mp:base-is-tramo base)
        (progn
          (setq handle (cdr (assoc 5 (entget tramo)))
                visible (mp:tramo-memory-table-visible-p handle))
          (if visible
            (progn
              (mp:set-tramo-memory-visibility tramo nil)
              (prompt "\nMemorias del tramo ocultas."))
            (progn
              (if (mp:set-tramo-memory-visibility tramo T)
                (prompt "\nMemorias del tramo desplegadas.")))))
        (prompt "\nEl objeto seleccionado no es un tramo de red."))))
  (princ))

(defun c:QMEMORIATRAMO () (mp:toggle-tramo-memory-command))

;; AutoCAD no permite crear un combo personalizado dentro de la paleta
;; Properties desde AutoLISP. Este reactor convierte el atributo editable
;; MEMORIAS en un control funcional: al escribir MOSTRAR/VISIBLE genera la
;; tabla y al escribir OCULTAR/OCULTAS la retira. SendCommand solo difiere
;; el trabajo; nunca se modifica la base de datos dentro de :vlr-modified.
(defun urb:memory-request-value (value / upper)
  (setq upper (strcase (vl-string-trim " " (mp:safe-str value))))
  (cond
    ((member upper '("MOSTRAR" "MOSTRARLAS" "VISIBLE" "VISIBLES" "SI" "S")) 1)
    ((member upper '("OCULTAR" "OCULTARLAS" "OCULTA" "OCULTAS" "NO" "N")) 0)
    (T nil)))

(defun urb:queue-memory-command (/ result)
  (if (and *urb-memory-pending* (not *urb-memory-command-scheduled*))
    (progn
      (setq *urb-memory-command-scheduled* T
            result
              (vl-catch-all-apply
                'vla-SendCommand
                (list (urb:doc) "ACTUALIZARMEMORIAS ")))
      (if (vl-catch-all-error-p result)
        (setq *urb-memory-command-scheduled* nil))))
  (princ))

(defun urb:on-memory-attribute-modified
  (notifier reactor parameters / data value request entry)
  (if (not *urb-memory-reactor-busy*)
    (progn
      (setq data (vlr-data reactor)
            value (vl-catch-all-apply 'vla-get-TextString (list notifier)))
      (if (not (vl-catch-all-error-p value))
        (progn
          (setq request (urb:memory-request-value value))
          (if (numberp request)
            (progn
              (setq entry (list (car data) (cadr data) request))
              (setq *urb-memory-pending*
                (cons entry
                  (vl-remove-if
                    '(lambda (item)
                       (and (= (car item) (car data))
                            (= (cadr item) (cadr data))))
                    *urb-memory-pending*)))
              (urb:queue-memory-command)))))))
  (princ))

(defun urb:process-memory-requests
  (/ pending entry ename shown hidden failed result visible requested-show)
  (setq pending *urb-memory-pending*
        *urb-memory-pending* nil
        *urb-memory-command-scheduled* nil)
  (if pending
    (progn
      (setq *urb-memory-reactor-busy* T)
      (foreach entry pending
        (setq ename (handent (cadr entry)))
        (if ename
          (progn
            (setq requested-show (= (caddr entry) 1)
                  visible
                    (cond
                      ((= (car entry) "VIA")
                        (urb:road-memory-table-visible-p (cadr entry)))
                      ((= (car entry) "PERFIL")
                        (urb:road-profile-visible-p (cadr entry)))
                      (T (mp:tramo-memory-table-visible-p (cadr entry)))))
            ;; Un segundo evento con el mismo estado no vuelve a construir
            ;; ni borrar la tabla. Esto corta reentradas de Properties/.NET.
            (setq result
              (if (eq requested-show (if visible T nil))
                T
                (vl-catch-all-apply
                  (cond
                    ((= (car entry) "VIA") 'urb:set-road-memory-visibility)
                    ((= (car entry) "PERFIL") 'urb:set-road-profile-visibility)
                    (T 'mp:set-tramo-memory-visibility))
                  (list ename requested-show))))
            (if (or (vl-catch-all-error-p result) (not result))
              (setq failed (1+ (if failed failed 0)))
              (if (= (caddr entry) 1)
                (setq shown (1+ (if shown shown 0)))
                (setq hidden (1+ (if hidden hidden 0))))))))
      (setq *urb-memory-reactor-busy* nil)
      (if (or shown hidden failed)
        (prompt
          (strcat "\nMemorias actualizadas: "
            (itoa (if shown shown 0)) " visibles, "
            (itoa (if hidden hidden 0)) " ocultas"
            (if failed (strcat ", " (itoa failed) " sin datos suficientes") "")
            ".")))))
  (princ))

(defun urb:on-memory-command-finished (reactor command-data)
  (if (and *urb-memory-pending* (not *urb-memory-reactor-busy*))
    (urb:process-memory-requests))
  (princ))

(defun urb:attach-memory-reactor-to-block
  (ename / obj attrs attribute kind base handle reactor result bname callbacks)
  (if (and ename (= (cdr (assoc 0 (entget ename))) "INSERT"))
    (progn
      (setq obj (vlax-ename->vla-object ename)
            handle (cdr (assoc 5 (entget ename))))
      (if (urb:get-xdata-strings ename "URB_VIA")
        (setq kind "VIA")
        (progn
          (setq result
            (vl-catch-all-apply 'vla-get-EffectiveName (list obj)))
          (if (not (vl-catch-all-error-p result))
            (progn
              (setq bname result
                    base (mp:infer-base bname (mp:att-alist ename)))
              (if (mp:base-is-tramo base) (setq kind "TRAMO"))))))
      (if (and kind handle (= (vla-get-HasAttributes obj) :vlax-true))
        (progn
          (setq result
            (vl-catch-all-apply 'vlax-invoke (list obj 'GetAttributes)))
          (if (not (vl-catch-all-error-p result))
            (progn
              (setq attrs result
                    callbacks
                      (list
                        (cons :vlr-modified
                          'urb:on-memory-attribute-modified)))
              (foreach attribute attrs
                ;; 5.7.0: PERFIL (solo vias) usa el mismo reactor con su
                ;; propio tipo de pedido
                (if (or (= (strcase (vla-get-TagString attribute)) "MEMORIAS")
                        (and (= kind "VIA")
                             (= (strcase (vla-get-TagString attribute)) "PERFIL")))
                  (progn
                    (setq result
                      (vl-catch-all-apply
                        'vlr-object-reactor
                        (list (list attribute)
                              (list (if (= (strcase (vla-get-TagString attribute)) "PERFIL")
                                      "PERFIL" kind)
                                    handle)
                              callbacks)))
                    (if (not (vl-catch-all-error-p result))
                      (progn
                        (setq reactor result)
                        (setq *urb-memory-attribute-reactors*
                          (cons reactor *urb-memory-attribute-reactors*))))))))))))
  reactor))

(defun urb:insert-has-memory-tag-p (ename / e d found)
  (setq e (entnext ename))
  (while (and e (not found)
              (setq d (entget e))
              (= (cdr (assoc 0 d)) "ATTRIB"))
    (if (member (strcase (cdr (assoc 2 d))) '("MEMORIAS" "PERFIL"))
      (setq found T))
    (setq e (entnext e)))
  found)

(defun urb:install-memory-property-reactors (/ reactor ss i)
  (if (and (boundp '*urb-memory-attribute-reactors*)
           *urb-memory-attribute-reactors*)
    (foreach reactor *urb-memory-attribute-reactors*
      (vl-catch-all-apply 'vlr-remove (list reactor))))
  (if (and (boundp '*urb-memory-command-reactor*)
           *urb-memory-command-reactor*)
    (vl-catch-all-apply 'vlr-remove (list *urb-memory-command-reactor*)))
  (setq *urb-memory-attribute-reactors* nil
        *urb-memory-pending* nil
        *urb-memory-command-scheduled* nil
        ss (ssget "_X" '((0 . "INSERT") (66 . 1)))
        i 0)
  ;; 5.7.2 (medido en el maestro: 10,4 s por apertura): antes se pedia el
  ;; nombre efectivo, se inferia la base y se leian por ActiveX los
  ;; atributos de CADA bloque con atributos (644). Ahora un recorrido
  ;; barato por entnext descarta los que no tienen MEMORIAS/PERFIL.
  (if ss
    (repeat (sslength ss)
      (if (urb:insert-has-memory-tag-p (ssname ss i))
        (vl-catch-all-apply 'urb:attach-memory-reactor-to-block
          (list (ssname ss i))))
      (setq i (1+ i))))
  (setq *urb-memory-command-reactor*
    (vlr-command-reactor
      nil
      '((:vlr-commandEnded . urb:on-memory-command-finished)
        (:vlr-commandCancelled . urb:on-memory-command-finished)
        (:vlr-commandFailed . urb:on-memory-command-finished))))
  (length *urb-memory-attribute-reactors*))

(defun c:ACTUALIZARMEMORIAS (/ t0 n f)
  ;; telemetria (2026-08-13): el usuario reporto congelamiento al dar
  ;; MOSTRAR en vivo; el cronometro headless dio 31 ms, asi que cada
  ;; corrida real deja su tiempo en el mismo log de la cinta para
  ;; ubicar donde se pierde el tiempo en la sesion viva.
  (setq t0 (getvar "MILLISECS")
        n (length *urb-memory-pending*))
  (urb:process-memory-requests)
  (setq f
    (vl-catch-all-apply 'open
      (list (strcat (urb:safe-string (getenv "TEMP") ".")
                    "\\urbcant_ribbon.log") "a")))
  (if (and f (not (vl-catch-all-error-p f)))
    (progn
      (write-line
        (strcat "LISP ACTUALIZARMEMORIAS: " (itoa n) " pedido(s) en "
                (itoa (- (getvar "MILLISECS") t0)) " ms") f)
      (close f)))
  (princ))

;; 2026-08-11 v2: las tablas de verificacion viejas NO estan sueltas en el
;; dibujo -- quedaron EMPACADAS dentro del bloque de cada via
;; (urb:package-road recoge todo lo etiquetado URB_VIA_GEN, tabla
;; incluida), por eso un ssget de primer nivel no las ve y la migracion
;; inicial no borro nada (reporte del usuario). Esta funcion las purga de
;; las DEFINICIONES de los bloques URB_VIA_*: dentro de esos bloques la
;; unica ACAD_TABLE posible es la de verificacion.
(defun urb:purge-road-block-tables (/ blocks bdef bname victims obj count)
  (setq blocks (vla-get-Blocks (urb:doc)) count 0)
  (vlax-for bdef blocks
    (setq bname (strcase (vla-get-Name bdef)))
    (if (and (urb:starts-with bname "URB_VIA_")
             (= (vla-get-IsLayout bdef) :vlax-false)
             (= (vla-get-IsXRef bdef) :vlax-false))
      (progn
        (setq victims nil)
        (vlax-for obj bdef
          (if (= (vla-get-ObjectName obj) "AcDbTable")
            (setq victims (cons obj victims))))
        (foreach obj victims
          (if (urb:safe-delete obj) (setq count (1+ count)))))))
  count)

;; 2026-08-11: tabla de verificacion BAJO DEMANDA (menu Cantidades). La
;; tabla ya no se crea sola al crear/editar la via (aparecia lejos del
;; contorno): aqui el usuario selecciona la via Y el punto donde quiere la
;; tabla. Recalcula el movimiento de tierras con los datos guardados de la
;; via (mismo camino que EDITAR) y borra la tabla anterior de esa via para
;; no duplicar.
(defun urb:road-audit-table-command
  (/ selected road data axis-handle via-id axis point *error*)
  (defun *error* (message)
    (setq *urb-road-audit-point* nil)
    (if (and message
             (not (member message '("Function cancelled" "quit / exit abort"))))
      (prompt (strcat "\nError en tabla de verificacion: " message)))
    (princ))
  (setq selected (entsel "\nSeleccione la via: "))
  (if selected (setq road (urb:road-parent-from-entity (car selected))))
  (if (and road (setq data (urb:get-xdata-strings road "URB_VIA")))
    (progn
      (setq via-id (if (> (length data) 22) (nth 22 data) ""))
      ;; 2026-08-13: eje resuelto SOLO (handle -> cache -> enlazado ->
      ;; copia dentro del bloque); seleccionar a mano queda de ultimo
      ;; recurso -- antes siempre lo pedia en vias con eje perdido
      (setq axis (urb:road-axis-recover road data via-id))
      (if (not axis) (setq axis (urb:select-or-draw-road-axis "Existente")))
      (setq point (getpoint "\nPunto de insercion de la tabla de verificacion: "))
      (if (and axis point)
        (progn
          (urb:delete-road-audit-tables (cdr (assoc 5 (entget road))))
          (setq *urb-road-audit-point* point)
          (urb:try-road-earthworks road axis)
          (setq *urb-road-audit-point* nil))
        (prompt "\nComando cancelado.")))
    (prompt "\nEl objeto seleccionado no es una via cuantificable."))
  (princ))

(defun urb:road-earthwork-width (area span nominal left right / calzada)
  ;; AREA de URB_VIA es calzada, no huella de tierras (ver package-road).
  ;; Sigue siendo un ancho MEDIO: no reemplaza integrar el contorno real.
  (setq calzada (if (> span 0.01) (/ area span) 0.0))
  (+ (if (> calzada 0.01) calzada nominal) left right))

(defun urb:point-line-distance (p a b / dx dy den)
  (setq dx (- (car b) (car a)) dy (- (cadr b) (cadr a))
        den (sqrt (+ (* dx dx) (* dy dy))))
  (if (< den 1e-12) (distance p a)
    (/ (abs (- (* dx (- (cadr p) (cadr a)))
                 (* dy (- (car p) (car a))))) den)))

(defun urb:curve-end-tangent-intersection (curve at-start a b / param p d q hit)
  (setq param (if at-start
                (vlax-curve-getStartParam curve)
                (vlax-curve-getEndParam curve))
        p (vlax-curve-getPointAtParam curve param)
        d (vlax-curve-getFirstDeriv curve param))
  (if (and p d)
    (progn
      (setq q (list (+ (car p) (car d)) (+ (cadr p) (cadr d))))
      (setq hit (inters p q a b nil))))
  (if hit (list (car hit) (cadr hit)) nil))

(defun urb:road-clip-offset-chain (curve cap1 cap2 / vb pts bulges p0 pn first-cap last-cap hit)
  ;; OFFSET desplaza tambien los extremos longitudinalmente cuando el
  ;; costado es oblicuo. Recortarlos contra las rectas de los bordes
  ;; inicial/final mantiene exactamente la huella dentro de sus tapas.
  (setq vb (urb:lwpoly-vertex-bulges curve) pts (car vb) bulges (cadr vb)
        p0 (car pts) pn (last pts))
  (if (<= (urb:point-line-distance p0 (car cap1) (cadr cap1))
          (urb:point-line-distance p0 (car cap2) (cadr cap2)))
    (setq first-cap cap1 last-cap cap2)
    (setq first-cap cap2 last-cap cap1))
  (setq hit (urb:curve-end-tangent-intersection curve T (car first-cap) (cadr first-cap)))
  (if hit (setq pts (cons hit (cdr pts))))
  (setq hit (urb:curve-end-tangent-intersection curve nil (car last-cap) (cadr last-cap)))
  (if hit (setq pts (reverse (cons hit (cdr (reverse pts))))))
  (list pts bulges))

(defun urb:road-earthwork-footprint (boundary axis left right direction / ends chains pl p near raw ang side width off pts all ring result failed gap test vb basepts cap1 cap2 result-area base-area self-cross bounded)
  ;; Huella REAL: desplazar solo los costados, nunca promediar sus anchos.
  ;; Izquierda/derecha relativas al sentido de abscisado. Tapas sin prolongar.
  (setq *urb-last-road-footprint-diagnostic* nil)
  (if (and (<= left 1e-9) (<= right 1e-9))
    (urb:as-ename (vla-Copy (vlax-ename->vla-object boundary)))
    (progn
      (setq ends (urb:road-end-edges boundary) ring (urb:lwpoly-points-with-arcs-fine boundary)
            gap (getvar "OFFSETGAPTYPE"))
      (if ends
        (progn
          (setq vb (urb:lwpoly-vertex-bulges boundary) basepts (car vb)
                cap1 (list (nth (car ends) basepts)
                  (nth (rem (1+ (car ends)) (length basepts)) basepts))
                cap2 (list (nth (cadr ends) basepts)
                  (nth (rem (1+ (cadr ends)) (length basepts)) basepts)))))
      (setvar "OFFSETGAPTYPE" 1)
      (if ends (setq chains (urb:road-side-chains boundary (car ends) (cadr ends))))
      (foreach pl chains
        (setq p (urb:curve-pt pl (* 0.5 (urb:curve-length pl)))
              near (vlax-curve-getClosestPointTo axis p)
              raw (vlax-curve-getDistAtPoint axis near)
              ang (urb:curve-tangent axis raw)
              side (+ (* (- (car p) (car near)) (- (sin ang)))
                      (* (- (cadr p) (cadr near)) (cos ang))))
        (if (urb:string-equal-p direction "Final") (setq side (- side)))
        (setq width (if (> side 0.0) left right))
        (setq off (if (<= width 1e-9) (urb:as-ename (vla-Copy (vlax-ename->vla-object pl)))
                    (urb:anden-offset-safe pl width)))
        (if (and off (> width 1e-9))
          (progn
            (setq test (urb:curve-pt off (* 0.5 (urb:curve-length off))))
            (if (urb:point-in-poly-p test ring)
              (progn (entdel off) (setq off (urb:anden-offset-safe pl (- width)))))))
        (if off
          (progn
            (setq pts (urb:road-clip-offset-chain off cap1 cap2))
            (setq all (append all (mapcar '(lambda (p b) (list (car p) (cadr p) b)) (car pts) (cadr pts))))
            (entdel off))
          (setq failed T))
        (entdel pl))
      (setvar "OFFSETGAPTYPE" gap)
      (if (and (= (length chains) 2) (not failed))
        (progn
          (setq result (urb:poly-chain-polyline all))
          (vla-put-Closed (vlax-ename->vla-object result) :vlax-true)
          (setq result-area (vla-get-Area (vlax-ename->vla-object result))
                base-area (vla-get-Area (vlax-ename->vla-object boundary))
                self-cross (urb:polygon-self-intersects-p (urb:lwpoly-points-with-arcs result))
                ;; En el encuentro de un costado oblicuo con la tapa, el
                ;; miter queda a width/cos(angulo), ligeramente mayor que
                ;; width aunque el desplazamiento perpendicular sea exacto.
                ;; Admitir hasta 1.5x (angulo <=48 grados); picos agudos o
                ;; offsets descontrolados siguen rechazados.
                bounded (urb:anden-overwidth-bounded-p boundary result
                  (+ 0.001 (* 1.5 (max left right))))
                *urb-last-road-footprint-diagnostic*
                  (list result-area base-area self-cross bounded (length all)))
          (if (or (< result-area base-area) self-cross (not bounded))
            (progn (entdel result) (setq result nil)))))
      (if (null *urb-last-road-footprint-diagnostic*)
        (setq *urb-last-road-footprint-diagnostic*
          (list "NO_RESULT" (if chains (length chains) 0) failed (length all))))
      ;; En sobreanchos simetricos, reutilizar el constructor exhaustivo de
      ;; andenes cuando el offset dirigido arma un lazo o un pico. Prueba
      ;; las cuatro combinaciones de signo y conserva solo una huella mayor,
      ;; no autointersectada y acotada al ancho real. Las tapas no se
      ;; prolongan, por lo que sigue siendo una huella vial exacta.
      (if (and (null result) (> left 1e-9) (equal left right 1e-9))
        (progn
          (setq result (urb:anden-overwidth-contour boundary left))
          (if result
            (setq *urb-last-road-footprint-diagnostic*
              (list "FALLBACK_SIMETRICO_OK"
                (vla-get-Area (vlax-ename->vla-object result))
                (vla-get-Area (vlax-ename->vla-object boundary)))))))
      result)))

(defun urb:road-plan-integral (points surface axis raw-grade axis-start span direction depth step bin-size / cells sample p w near raw st tn finish cf cut fill covered total missing bins key old row rows ds)
  (setq cells (urb:earthwork-scanline-samples points step)
        cut 0.0 fill 0.0 covered 0.0 total 0.0 missing 0)
  (foreach sample cells
    (setq p (car sample) w (cadr sample) total (+ total w)
          near (vlax-curve-getClosestPointTo axis p)
          raw (vlax-curve-getDistAtPoint axis near)
          st (if (urb:string-equal-p direction "Final") (- (+ axis-start span) raw) (- raw axis-start))
          tn (urb:surface-elevation surface (car p) (cadr p))
          finish (urb:cota-at-axis-distance raw raw-grade))
    (if (and (numberp tn) (numberp finish) (>= st -0.05) (<= st (+ span 0.05)))
      (progn
        (setq finish (- finish (* (distance (list (car p) (cadr p)) (list (car near) (cadr near))) *urb-road-crossfall*))
              cf (urb:cut-fill-at (- tn (- finish depth)))
              cut (+ cut (* w (car cf))) fill (+ fill (* w (cadr cf))) covered (+ covered w)
              key (min (fix (/ (max 0.0 st) bin-size)) (max 0 (1- (fix (+ 0.999999 (/ span bin-size))))))
              old (assoc key bins))
        (if (null old) (setq old (list key 0.0 0.0 0.0 0.0 0.0)))
        (setq row (list key (+ (nth 1 old) w) (+ (nth 2 old) (* w tn)) (+ (nth 3 old) (* w finish))
                     (+ (nth 4 old) (* w (car cf))) (+ (nth 5 old) (* w (cadr cf)))))
        (if (assoc key bins) (setq bins (subst row (assoc key bins) bins)) (setq bins (cons row bins))))
      (setq missing (1+ missing))))
  (foreach row (vl-sort bins '(lambda (a b) (< (car a) (car b))))
    (setq ds (min bin-size (- span (* (car row) bin-size)))
          tn (/ (nth 2 row) (nth 1 row)) finish (/ (nth 3 row) (nth 1 row)))
    (setq rows (cons (list (min span (* (1+ (car row)) bin-size)) tn finish (- finish depth)
      (- tn (- finish depth)) (/ (nth 4 row) ds) (/ (nth 5 row) ds) (nth 4 row) (nth 5 row)) rows)))
  (list cut fill missing total (length cells) (reverse rows)))

(defun urb:road-grade-sanity (samples depth / item station tn grade delta maximum worst total count)
  ;; Guardarrail previo a la integracion pesada. Una cota tomada de otra via
  ;; o un pozo intermedio tratado por error como extremo puede poner la rasante
  ;; decenas de metros bajo SUP_TN y fabricar miles de m3 plausibles en forma,
  ;; pero imposibles en proyecto. No se guarda ni se integra esa rasante.
  (setq maximum 0.0 total 0.0 count 0)
  (foreach item samples
    (setq station (nth 0 item) tn (nth 1 item) grade (nth 2 item))
    (if (and (numberp tn) (numberp grade))
      (progn
        (setq delta (- tn (- grade depth))
              total (+ total (abs delta))
              count (1+ count))
        (if (> (abs delta) maximum)
          (setq maximum (abs delta)
                worst (list station tn grade delta))))))
  (setq *urb-last-road-grade-diagnostic*
    (list (or (<= *urb-road-max-earthwork-depth* 0.0)
              (<= maximum *urb-road-max-earthwork-depth*)) maximum
      (if (> count 0) (/ total count) 0.0) worst count
      *urb-road-max-earthwork-depth*))
  *urb-last-road-grade-diagnostic*)

(defun urb:road-plan-converged (footprint surface axis raw-grade axis-start span direction depth bin-size / points area steps step prev current delta ok history reason)
  (setq *urb-last-road-plan-diagnostic* nil)
  ;; 2.0/1.0 m suele converger en vias largas y evita arrancar con cientos
  ;; de miles de llamadas COM. Solo baja a 0.5 m si la diferencia supera 0.5%.
  (setq points (urb:anden-earthwork-raw-points footprint)
        area (vla-get-Area (vlax-ename->vla-object footprint))
        steps '(2.0 1.0 0.5))
  (while (and (not ok) steps)
    (setq step (car steps) steps (cdr steps))
    (setq current (urb:road-plan-integral points surface axis raw-grade axis-start span direction depth step bin-size))
    (setq history (cons (list step (nth 0 current) (nth 1 current)
      (nth 2 current) (nth 3 current) area (nth 4 current)) history))
    (if (or (> (nth 2 current) 0) (<= (nth 3 current) 1e-9)
            (> (abs (- area (nth 3 current))) (max 0.001 (* area 0.0001))))
      (setq reason
        (cond ((> (nth 2 current) 0) "MUESTRAS_FUERA_DE_TN_O_RASANTE")
              ((<= (nth 3 current) 1e-9) "AREA_MUESTREADA_CERO")
              (T "AREA_MUESTREADA_NO_COINCIDE"))
            steps nil)
      (progn
        (if prev
          (setq ok (and (<= (abs (- (car current) (car prev))) (max 0.02 (* 0.005 (abs (car current)))))
                        (<= (abs (- (cadr current) (cadr prev))) (max 0.02 (* 0.005 (abs (cadr current))))))))
        (if (not ok) (setq prev current)))))
  (if (and (not ok) (null reason)) (setq reason "SIN_CONVERGENCIA_0.5%"))
  (setq *urb-last-road-plan-diagnostic*
    (list (if ok "OK" reason) (reverse history)))
  (if ok (append current (list step area)) nil))

(defun urb:compute-road-earthworks
  (boundary data axis / surface depth area axis-length axis-start nominal
   left right width-total design-width geometry-width interval sample-interval direction texts radius span stations raw-stations
   station-start-number coverage
   samples old-mov old-cota0 old-cota-final grade-result totals metodo
   cota0 cota-final cut fill skipped audit-result
   cov-min cov-max cov-it guard-records footprint plan-result raw-grade audit-rows
   grade-sanity)
  (setq *urb-earthwork-stage* "inicio del calculo")
  (setq old-mov (urb:road-movement-data boundary))
  (setq old-cota0
    (if (and old-mov (> (length old-mov) 7) (/= (nth 7 old-mov) ""))
      (atof (nth 7 old-mov))
      nil))
  (setq old-cota-final
    (if (and old-mov (> (length old-mov) 8) (/= (nth 8 old-mov) ""))
      (atof (nth 8 old-mov))
      nil))
  (if (and (null old-cota0) (> (length data) 30)
           (/= (urb:safe-string (nth 30 data) "") ""))
    (setq old-cota0 (atof (nth 30 data))))
  (if (and (null old-cota-final) (> (length data) 31)
           (/= (urb:safe-string (nth 31 data) "") ""))
    (setq old-cota-final (atof (nth 31 data))))
  ;; cotas seleccionadas en el flujo Pendiente (una por costado): tienen
  ;; prioridad como par inicial/final para la pendiente lineal
  (if *urb-road-picked-cotas*
    (setq old-cota0 (car *urb-road-picked-cotas*)
          old-cota-final (cadr *urb-road-picked-cotas*)))
  (setq surface (urb:select-surface-object (nth 6 data)))
  (setq depth (urb:road-profile-depth (nth 4 data)))
  (cond
    ((not axis)
      (prompt "\nMovimiento de tierras: la via no tiene un eje valido.")
      nil)
    ((not surface)
      (prompt "\nMovimiento de tierras: sin superficie topografica.")
      nil)
    ((<= depth 0.001)
      (prompt
        (strcat
          "\nMovimiento de tierras: el perfil "
          (urb:safe-string (nth 4 data) "")
          " no tiene capas volumetricas."))
      nil)
    (T
      (setq area (atof (nth 17 data)))
      (setq axis-length (atof (urb:safe-string (nth 18 data) "0")))
      (setq axis-start (atof (urb:safe-string (nth 21 data) "0")))
      (setq nominal (atof (nth 16 data)))
      (setq left (atof (nth 14 data)))
      (setq right (atof (nth 15 data)))
      (setq design-width (+ nominal left right)
            geometry-width
              (if (> axis-length 0.01) (/ area axis-length) 0.0))
      ;; El area guardada corresponde a CALZADA. Los sobreanchos se suman
      ;; una vez, igual que en VIA_AREA_SOBREANCHO_M2. El ancho medio no
      ;; representa la distribucion local de anchos variables.
      (setq width-total
        (urb:road-earthwork-width area axis-length nominal left right))
      (if (and (> design-width 0.01) (> geometry-width 0.01)
               (> (/ (abs (- width-total design-width)) design-width) 0.02))
        (prompt
          (strcat
            "\nControl de ancho: calzada + sobreanchos " (rtos width-total 2 2)
            " m vs. diseno " (rtos design-width 2 2)
            " m. El movimiento usa el ancho medio mas los sobreanchos.")))
      (setq interval (atof (nth 11 data)))
      (if (<= interval 0.01) (setq interval 10.0))
      (setq sample-interval
        (min interval (max 0.25 *urb-road-earthwork-interval*)))
      (setq direction (urb:safe-string (nth 12 data) "Inicio"))
      (setq station-start-number
        (urb:station-number (urb:safe-string (nth 10 data) "0+000")))
      (if (<= width-total 0.01)
        (progn
          (prompt "\nMovimiento de tierras: ancho de via indeterminado.")
          nil)
        (progn
          (setq *urb-earthwork-stage* "lectura de textos de cota")
          (setq texts (urb:collect-cota-texts (nth 8 data)))
          ;; Distancia TRANSVERSAL: antes se admitian 15 m y entraban
          ;; decenas de etiquetas ajenas o posiciones proxy. Se limita a
          ;; la franja de la propia via; el anclaje COGO correcto queda
          ;; normalmente sobre el eje.
          (setq radius (max 1.50 (min 4.00 (* width-total 0.45))))
          (setq span axis-length)
          (setq *urb-earthwork-stage* "proyeccion de cotas sobre el eje")
          ;; Se incluyen dos estaciones de margen en cada extremo. Un solo
          ;; intervalo no alcanzaba la cota 0+060 cuando el tramo terminaba
          ;; en 0+054.12, y la rasante quedaba plana desde 0+050.
          (setq raw-stations
            (urb:cota-stations-on-axis axis texts
              (- axis-start (* 2.0 interval))
              (+ span (* 4.0 interval)) radius))
          (setq stations (urb:cota-best-per-source raw-stations))
          (setq stations
            (urb:cota-snap-to-project-grid stations axis-start span
              station-start-number interval direction))
          (setq stations (urb:cota-deduplicate-stations stations 0.20))
          (setq coverage
            (urb:cota-stations-cover-p
              stations axis-start (+ axis-start span) interval))
          ;; 2026-08-11: cotas seleccionadas UNA A UNA en modo Pendiente
          ;; (3 o mas, p.ej. pozos sobre la via): reemplazan cualquier
          ;; texto detectado y definen la rasante por tramos completa.
          (if (and (boundp '*urb-road-picked-stations*)
                   *urb-road-picked-stations*)
            (progn
              (setq stations *urb-road-picked-stations*)
              (setq coverage T)))
          ;; 2026-08-25: CERO candidatos con miles de textos leidos =
          ;; desfase de posicion de las etiquetas COGO (medido 121-229 m
          ;; en el master real; la calibracion por clic del flujo de
          ;; crear vivia solo en la sesion y podia elegir el punto
          ;; equivocado entre valores repetidos). Un clic recalibra con
          ;; validacion contra el eje y queda PERSISTIDO en el dibujo.
          (if (and (null raw-stations) texts (not coverage))
            (progn
              (setq *urb-earthwork-stage* "recalibracion de cotas")
              (if (urb:recalibrate-cota-interactive
                    (urb:safe-string (nth 8 data) "")
                    axis axis-start span radius interval)
                (progn
                  (setq texts
                    (urb:collect-cota-texts
                      (urb:safe-string (nth 8 data) "")))
                  (setq raw-stations
                    (urb:cota-stations-on-axis axis texts
                      (- axis-start (* 2.0 interval))
                      (+ span (* 4.0 interval)) radius))
                  (setq stations
                    (urb:cota-best-per-source raw-stations))
                  (setq stations
                    (urb:cota-snap-to-project-grid stations axis-start
                      span station-start-number interval direction))
                  (setq stations
                    (urb:cota-deduplicate-stations stations 0.20))
                  (setq coverage
                    (urb:cota-stations-cover-p
                      stations axis-start (+ axis-start span)
                      interval))))))
          ;; 2026-08-13: si la capa de textos no cubre el tramo pero la
          ;; via YA tiene su rasante guardada (records del calculo
          ;; anterior), esa rasante es la fuente -- las vias existentes
          ;; no deben pedir cotas de nuevo ni cancelar la verificacion
          ;; (reporte del usuario: 7785 textos leidos, 0 cercanos,
          ;; "Function cancelled" en la construccion de la rasante).
          ;; 2026-08-25: si hay estaciones pero la cobertura fallo,
          ;; DECIR el hueco real de cada borde (el mensaje generico "No
          ;; hay suficientes cotas" escondia que habia 22 estaciones
          ;; buenas descartadas por 9.84 m sin cota en el extremo).
          (if (and (not coverage) (>= (length stations) 2))
            (progn
              (setq cov-min nil cov-max nil)
              (foreach cov-it stations
                (if (or (null cov-min) (< (car cov-it) cov-min))
                  (setq cov-min (car cov-it)))
                (if (or (null cov-max) (> (car cov-it) cov-max))
                  (setq cov-max (car cov-it))))
              ;; 2026-08-26 (pedido del usuario): con 3+ estaciones que
              ;; cubran un tramo minimamente representativo (3 intervalos
              ;; o el 20% de la via, lo que sea mayor), la rasante se
              ;; ACEPTA y los extremos sin cota se EXTRAPOLAN con la
              ;; pendiente del tramo de borde (urb:cota-at-axis-distance
              ;; ya lo hace). Se avisa cuanto se extrapola por lado --
              ;; el usuario decide si le sirve o re-etiqueta. Con menos
              ;; de eso sigue el flujo manual de siempre.
              (if (and (>= (length stations) 3)
                       (>= (- cov-max cov-min)
                           (max (* 3.0 interval) (* 0.20 span))))
                (progn
                  (setq coverage T)
                  (prompt
                    (strcat
                      "\nRasante con EXTRAPOLACION: "
                      (itoa (length stations)) " cotas cubren "
                      (rtos (- cov-max cov-min) 2 1)
                      " m; se extrapola con la pendiente del borde "
                      (rtos (max 0.0 (- cov-min axis-start)) 2 1)
                      " m al inicio y "
                      (rtos (max 0.0 (- (+ axis-start span) cov-max)) 2 1)
                      " m al final.")))
                (prompt
                  (strcat
                    "\nCobertura de cotas insuficiente: "
                    (itoa (length stations)) " estaciones detectadas,"
                    " hueco al inicio "
                    (rtos (max 0.0 (- cov-min axis-start)) 2 2)
                    " m y al final "
                    (rtos (max 0.0 (- (+ axis-start span) cov-max)) 2 2)
                    " m (tolerancia "
                    (rtos (* 2.0 interval) 2 2) " m).")))))
          (if (not coverage)
            (progn
              (setq *urb-earthwork-stage* "rasante guardada")
              ;; 2026-08-25: variable PROPIA -- antes esta rama pisaba
              ;; raw-stations y el mensaje de abajo mentia "candidatos
              ;; cercanos: 0" aunque la proyeccion si habia encontrado
              (setq guard-records
                (urb:road-design-grade-records boundary data))
              (if guard-records
                (progn
                  ;; records en coordenada LOCAL (0..span) -> distancia
                  ;; RAW sobre el eje, respetando el sentido
                  (setq stations
                    (mapcar
                      '(lambda (r)
                         (list
                           (if (urb:string-equal-p direction "Final")
                             (- (+ axis-start span) (car r))
                             (+ axis-start (car r)))
                           (cadr r)))
                      guard-records))
                  (setq coverage T)
                  (prompt
                    (strcat
                      "\nRasante tomada de la guardada en la via ("
                      (itoa (length stations)) " puntos)."))))))
          ;; 2026-08-25 (pedido del usuario: via con 20 estaciones REALES
          ;; descartadas por un hueco de 29.84 m en un solo extremo -- el
          ;; fallback de abajo tiraba las 20 estaciones buenas y pedia
          ;; una linea recta manual para TODA la via, de punta a punta).
          ;; Si sigue sin cobertura ni rasante guardada pero SI hay
          ;; estaciones reales, se usan automaticamente extrapolando
          ;; PLANO (valor del borde mas cercano) solo el tramo sin cota
          ;; -- urb:cota-at-axis-distance ya hace esa extrapolacion,
          ;; aqui solo se decide usarla en vez de descartar datos reales.
          ;; Sin pregunta (pedido del usuario, v4.57.5): usar 20 cotas
          ;; reales + extrapolacion del borde SIEMPRE es mejor que
          ;; fabricar una recta ficticia de punta a punta con "No".
          (if (and (not coverage) (>= (length stations) 2))
            (progn
              (setq coverage T)
              (prompt
                "\nCotas insuficientes en un extremo: se usan las estaciones detectadas y se extrapola PLANO (valor del borde mas cercano) el tramo sin cota -- revise esa zona.")))
          (if texts
            (prompt
              (strcat
                "\nTextos de cota leidos: " (itoa (length texts))
                " | candidatos cercanos: " (itoa (length raw-stations))
                " | cotas unicas usadas: " (itoa (length stations)) ".")))
          (if (and *urb-last-cota-projection-failures*
                   (> *urb-last-cota-projection-failures* 0))
            (prompt
              (strcat
                "\nCandidatos proxy descartados por geometria invalida: "
                (itoa *urb-last-cota-projection-failures*)
                (if *urb-last-cota-projection-error*
                  (strcat " | ultimo: " *urb-last-cota-projection-error*)
                  "") ".")))
          (if (and (null stations) *urb-last-cota-min-offset*)
            (prompt
              (strcat
                "\nDiagnostico de cotas: distancia minima texto-eje = "
                (rtos *urb-last-cota-min-offset* 2 3) " m"
                " | radio admitido = " (rtos radius 2 3) " m.")))
          (setq *urb-earthwork-stage* "muestreo de la superficie")
          (setq samples
            (urb:road-section-samples
              surface axis axis-start span sample-interval direction width-total
              stations coverage station-start-number))
          (setq *urb-earthwork-stage* "construccion de la rasante")
          (setq grade-result
            (urb:road-resolve-grade
              samples coverage (length stations) old-cota0 old-cota-final
              span data))
          (if (null grade-result)
            (progn
              (prompt "\nMovimiento de tierras omitido en esta via.")
              nil)
            (progn
              (setq samples (nth 0 grade-result))
              (setq metodo
                (strcat "AREAS_EXTREMAS_7_ORDENADAS_BOMBEO_"
                  (rtos (* 100.0 *urb-road-crossfall*) 2 2) "% - "
                  (urb:safe-string (nth 1 grade-result) "rasante")))
              (setq cota0 (nth 2 grade-result))
              (setq cota-final (nth 3 grade-result))
              (setq grade-sanity (urb:road-grade-sanity samples depth))
              (if (not (car grade-sanity))
                (progn
                  (urb:invalidate-road-movement boundary nil
                    "PENDIENTE: RASANTE INCONSISTENTE CON SUP_TN")
                  (prompt
                    (strcat
                      "\nTierras PENDIENTES: la rasante difiere hasta "
                      (rtos (nth 1 grade-sanity) 2 2)
                      " m del terreno natural (limite de control "
                      (rtos *urb-road-max-earthwork-depth* 2 1)
                      " m; 0 lo desactiva). Revise las cotas y los pozos; no se calcula ni"
                      " se guarda un volumen absurdo."))
                  nil)
                (progn
              (setq *urb-earthwork-stage* "integracion de corte y relleno")
              (setq raw-grade (mapcar '(lambda (s)
                (list (if (urb:string-equal-p direction "Final") (- (+ axis-start span) (car s)) (+ axis-start (car s))) (nth 2 s))) samples))
              (setq footprint (urb:road-earthwork-footprint boundary axis left right direction))
              (setq plan-result (if footprint (urb:road-plan-converged footprint surface axis raw-grade axis-start span direction depth interval)))
              (if footprint (entdel footprint))
              (setq totals (if plan-result (list (car plan-result) (cadr plan-result) 0) (list 0.0 0.0 1)))
              (if plan-result
                (setq metodo (strcat "HUELLA_REAL_CONVERGENCIA_0.5%_PASO_" (rtos (nth 6 plan-result) 2 3) "m")
                      audit-rows (nth 5 plan-result)))
              (setq cut (nth 0 totals))
              (setq fill (nth 1 totals))
              (setq skipped (nth 2 totals))
              (if (> skipped 0)
                (progn
                  (urb:invalidate-road-movement boundary nil "PENDIENTE: REVISAR HUELLA/TN/CONVERGENCIA")
                  (prompt
                    (strcat
                      "\nTierras PENDIENTES: "
                      (if footprint
                        (vl-princ-to-string *urb-last-road-plan-diagnostic*)
                        (strcat "huella invalida "
                          (vl-princ-to-string *urb-last-road-footprint-diagnostic*)))
                      ". No se conserva un volumen parcial ni por ancho promedio."))
                  nil)
                (progn
              ;; Estado y movimiento se escriben juntos dentro de URB_VIA;
              ;; asi el bloque no depende de una segunda aplicacion XDATA.
              (urb:set-road-movement-data boundary
                (list
                  (rtos cut 2 2)
                  (rtos fill 2 2)
                  metodo
                  (itoa (length samples))
                  (itoa skipped)
                  (rtos width-total 2 2)
                  (rtos depth 2 2)
                  (if cota0 (rtos cota0 2 4) "")
                  (if cota-final (rtos cota-final 2 4) "")
                  (urb:serialize-lisp
                    (urb:compact-road-grade-samples samples))))
              ;; Perfil completo en diccionario: no perder quiebres por el
              ;; limite de 255 caracteres de la copia compatible XDATA.
              (vlax-ldata-put boundary "URB_VIA_RASANTE_FULL"
                (mapcar '(lambda (s) (list (car s) (nth 2 s))) samples))
              (vlax-ldata-put boundary "URB_VIA_HUELLA" (list (nth 7 plan-result) (nth 6 plan-result) (nth 4 plan-result)))
              ;; 2026-08-13: las FILAS de la tabla de verificacion se
              ;; persisten en TODO calculo (ldata URB_VIA_AUDIT), se
              ;; dibuje o no la tabla -- asi el clic derecho
              ;; (Mostrar/ocultar memorias) funciona apenas la via tiene
              ;; movimiento calculado, sin pasar por Verificacion.
              (setq *urb-earthwork-stage* "guardado de filas de verificacion")
              (vl-catch-all-apply 'vlax-ldata-put
                (list boundary "URB_VIA_AUDIT"
                  (list
                    audit-rows
                    metodo cut fill)))
              ;; 2026-08-11: la tabla de verificacion YA NO se crea sola al
              ;; crear/editar la via (aparecia lejos del contorno y estorbaba).
              ;; Solo se crea cuando se pide desde Cantidades
              ;; (urb:road-audit-table-command), que deja el punto de
              ;; insercion elegido por el usuario en *urb-road-audit-point*.
              (if (and (boundp '*urb-road-audit-point*) *urb-road-audit-point*)
                (progn
                  (setq *urb-earthwork-stage* "creacion de tabla de verificacion")
                  (setq audit-result
                    (vl-catch-all-apply
                    'urb:draw-road-audit-table
                      (list boundary axis audit-rows data cut fill metodo)))
                  (if (vl-catch-all-error-p audit-result)
                    (prompt
                      (strcat
                        "\nAviso: no se pudo crear la tabla de verificacion: "
                        (vl-catch-all-error-message audit-result))))))
              (prompt
                (strcat
                  "\nMovimiento de tierras (" metodo "): corte "
                  (rtos cut 2 2) " m3 | relleno "
                  (rtos fill 2 2) " m3."))
              (setq *urb-earthwork-stage* "calculo finalizado")
              (list cut fill))))))))))))

;; Se llama solo desde crear/editar via; nunca interrumpe el flujo.
;; Recibe el eje ya resuelto (no lo vuelve a buscar con handent, que no
;; funciona si el eje vive en un xref).
(defun urb:try-road-earthworks (boundary axis / data result)
  (setq data (urb:get-xdata-strings boundary "URB_VIA"))
  (if (and data
           (not (urb:string-equal-p (nth 6 data) "NO SELECCIONADA")))
    (progn
      (setq result
        (vl-catch-all-apply
          'urb:compute-road-earthworks
          (list boundary data axis)))
      (if (vl-catch-all-error-p result)
        (progn
          (prompt
            (strcat
              "\nERROR al calcular cortes y rellenos: "
              (vl-catch-all-error-message result)
              " | etapa: "
              (urb:safe-string *urb-earthwork-stage* "desconocida")))
          nil)
        result))
    nil)
)

(defun urb:ramp-local-point (base axis-angle side-sign u v)
  ;; u corre a lo largo del sardinel desde el punto base; v entra
  ;; perpendicular hacia el anden (side-sign decide hacia cual lado).
  (list
    (+ (car base)
       (* u (cos axis-angle))
       (* v side-sign (- (sin axis-angle))))
    (+ (cadr base)
       (* u (sin axis-angle))
       (* v side-sign (cos axis-angle))))
)

(defun urb:ramp-quad-poly (base axis-angle side-sign u1 v1 u2 v2 layer / p1 p2 p3 p4)
  (setq p1 (urb:ramp-local-point base axis-angle side-sign u1 v1)
        p2 (urb:ramp-local-point base axis-angle side-sign u2 v1)
        p3 (urb:ramp-local-point base axis-angle side-sign u2 v2)
        p4 (urb:ramp-local-point base axis-angle side-sign u1 v2))
  (entmake
    (list (cons 0 "LWPOLYLINE") (cons 100 "AcDbEntity") (cons 100 "AcDbPolyline")
          (cons 8 layer) (cons 90 4) (cons 70 1)
          (cons 10 p1) (cons 10 p2) (cons 10 p3) (cons 10 p4)))
  (entlast)
)

(defun urb:ramp-line (base axis-angle side-sign u1 v1 u2 v2 layer color / p1 p2)
  (setq p1 (urb:ramp-local-point base axis-angle side-sign u1 v1)
        p2 (urb:ramp-local-point base axis-angle side-sign u2 v2))
  (entmake
    (list (cons 0 "LINE") (cons 8 layer) (cons 62 color)
          (cons 10 (list (car p1) (cadr p1) 0.0))
          (cons 11 (list (car p2) (cadr p2) 0.0))))
  (entlast)
)

;; ---------- ventana previa de RAMPA (2026-08-21, pedido del usuario:
;; "no me sale ninguna ventana ni siquiera para elegir etapa o
;; subetapa") -- etapa, subetapa, ancho de banda central y fondo ----------
(setq *urb-rampa-tipos*
  '(("RAMPA-PEATONAL" "Rampa peatonal" "RAMPA-PEATONAL")
    ("RAMPA-VEHICULAR" "Rampa vehicular" "RAMPA-VEHICULAR")
    ("PASO-PEATONAL" "Paso peatonal seguro" "PASO-PEATONAL")))

(defun urb:rampa-red (tipo / entry)
  (setq entry (assoc (strcase (urb:safe-string tipo "RAMPA-PEATONAL"))
                     *urb-rampa-tipos*))
  (if entry (nth 2 entry) "RAMPA-PEATONAL"))

(defun urb:rampa-write-dcl ()
  (urb:write-dialog-dcl
    "urb_rampa"
    '*urb-rampa-dcl-ok*
    (list
      ;; 2026-09-02 (pedido del usuario, 2 rondas): ni FONDO ni ANCHO se
      ;; digitan aqui -- el ancho se define dibujando (clic HASTA DONDE va
      ;; la rampa sobre el borde, o digitando la longitud) y el fondo lo
      ;; define el clic final sobre el bordillo.
      "urb_rampa : dialog { label = \"Rampas y pasos peatonales\";"
      ": popup_list { label = \"Tipologia\"; key = \"tipo\"; }"
      ": popup_list { label = \"Etapa\"; key = \"etapa\"; }"
      ": popup_list { label = \"Subetapa\"; key = \"subetapa\"; }"
      ": text { label = \"Peatonal: inicio, fin sobre el borde y fondo.\"; }"
      ": text { label = \"Vehicular / paso: Tres puntos o Dibujar contorno.\"; }"
      ": text { label = \"Sin contorno previo. Admite longitud libre y arcos.\"; }"
      "ok_cancel; }")))

(defun urb:rampa-fill-sub (idx)
  (start_list "subetapa")
  (foreach s (urb:subetapas-for (nth idx *urb-etapa-list*)) (add_list s))
  (end_list)
  (set_tile "subetapa" "0"))

;; devuelve (tipo etapa subetapa ancho fondo) o nil si cancela
(defun urb:rampa-dialog (/ dclfile dcl done tipo etapa subs fondo width entry)
  (setq dclfile (urb:rampa-write-dcl))
  (if (null dclfile)
    (progn
      (alert "No se pudo preparar la ventana de rampa (revise permisos de la carpeta temporal de Windows).")
      nil)
    (progn
      (setq dcl (load_dialog dclfile))
      (if (and dcl (> dcl 0) (new_dialog "urb_rampa" dcl))
        (progn
          (start_list "tipo")
          (foreach entry *urb-rampa-tipos* (add_list (nth 1 entry)))
          (end_list)
          (set_tile "tipo" "0")
          (start_list "etapa")
          (foreach e *urb-etapa-list* (add_list e))
          (end_list)
          (set_tile "etapa" "0")
          (urb:rampa-fill-sub 0)
          (action_tile "etapa" "(urb:rampa-fill-sub (atoi $value))")
          ;; seleccion capturada DENTRO del accept (regla de oro DCL v4.41)
          (action_tile "accept"
            (strcat
              "(setq *urb-rampa-sel* (list (get_tile \"tipo\")"
              " (get_tile \"etapa\")"
              " (get_tile \"subetapa\")))"
              " (done_dialog 1)"))
          (setq done (start_dialog))))
      (if (and dcl (> dcl 0)) (unload_dialog dcl))
      (if (= done 1)
        (progn
          (setq tipo
            (nth 0 (nth (atoi (nth 0 *urb-rampa-sel*)) *urb-rampa-tipos*)))
          (setq etapa
            (urb:safe-string
              (nth (atoi (nth 1 *urb-rampa-sel*)) *urb-etapa-list*) "1"))
          (setq subs (urb:subetapas-for etapa))
          ;; ancho: placeholder -- se define dibujando (clic hasta donde va
          ;; o longitud digitada); fondo: default, el clic final lo redefine
          (setq width 2.00)
          (setq fondo *urb-anden-default-width*)
          (list tipo etapa
            (urb:safe-string
              (nth (atoi (nth 2 *urb-rampa-sel*)) subs) "1")
            width fondo))
        nil))))

;; 2026-09-01 (pedido del usuario: "que pasa si anteriormente habia
;; dibujado un sardinel... hay forma de que se corte"): recorta los
;; prefabricados (sardinel/bordillo/canuela) que corren bajo el frente de
;; la rampa. Cada prefabricado afectado se parte: se extrae su polilinea
;; de referencia (misma tuberia probada de EDITAR), se quita el rango que
;; la rampa ocupa y se reconstruyen las piezas restantes como bloques
;; nuevos; el original se borra. Devuelve cuantos prefabricados corto.
(defun urb:trim-prefabs-for-ramp (base-pt axis-angle span
   / p2 ss i en data prefab pwidth mode etapa sub extd ref sp len d pt
   destino dmin dmax cnt piece res bb1 bb2 minx miny maxx maxy tol)
  (setq p2 (list (+ (car base-pt) (* span (cos axis-angle)))
                 (+ (cadr base-pt) (* span (sin axis-angle)))))
  (setq minx (- (min (car base-pt) (car p2)) 1.5)
        maxx (+ (max (car base-pt) (car p2)) 1.5)
        miny (- (min (cadr base-pt) (cadr p2)) 1.5)
        maxy (+ (max (cadr base-pt) (cadr p2)) 1.5)
        tol 0.35 cnt 0)
  (setq ss (ssget "_X" '((0 . "INSERT") (-3 ("URB_PREFAB_BLOCK")))) i 0)
  (if ss
    (while (< i (sslength ss))
      (setq en (ssname ss i))
      ;; prefiltro barato por bbox del insert
      (setq res (vl-catch-all-apply 'vla-GetBoundingBox
        (list (vlax-ename->vla-object en) 'bb1 'bb2)))
      (if (and (not (vl-catch-all-error-p res))
               (progn
                 (setq bb1 (vlax-safearray->list bb1)
                       bb2 (vlax-safearray->list bb2))
                 (and (< (car bb1) maxx) (> (car bb2) minx)
                      (< (cadr bb1) maxy) (> (cadr bb2) miny))))
        (progn
          (setq data (urb:prefab-data en)
                prefab (urb:safe-string (nth 0 data) "Bordillo")
                etapa (urb:safe-string (nth 1 data) "1")
                sub (urb:safe-string (nth 2 data) "1")
                pwidth (atof (urb:safe-string (nth 3 data) "0.20"))
                mode (urb:safe-string (nth 5 data) "Interior")
                destino (urb:safe-string (nth 7 data)
                  (urb:prefab-destino-default prefab)))
          (setq extd (urb:extract-prefab-reference en prefab mode))
          (if extd
            (progn
              (setq ref (nth 0 extd) sp (nth 1 extd))
              (setq len (vlax-curve-getDistAtParam ref
                          (vlax-curve-getEndParam ref)))
              ;; rango de la referencia ocupado por el frente de la rampa.
              ;; 2026-09-02 v2 (foto del usuario: quedaban HUECOS a lado y
              ;; lado): el criterio por distancia al segmento recortaba de
              ;; mas en las esquinas (radio tol alrededor del extremo). Se
              ;; decide por PROYECCION exacta sobre el eje de la rampa:
              ;; dentro del modulo = proyeccion en [0, span] y distancia
              ;; perpendicular < 0.60 -- el sardinel llega JUSTO al borde.
              (setq dmin nil dmax nil d 0.0)
              (while (<= d len)
                (setq pt (vlax-curve-getPointAtDist ref d))
                (if pt
                  (progn
                    (setq res
                      (list
                        (+ (* (- (car pt) (car base-pt)) (cos axis-angle))
                           (* (- (cadr pt) (cadr base-pt)) (sin axis-angle)))
                        (abs
                          (+ (* (- (car pt) (car base-pt))
                                (- (sin axis-angle)))
                             (* (- (cadr pt) (cadr base-pt))
                                (cos axis-angle))))))
                    (if (and (>= (car res) -0.01) (<= (car res) (+ span 0.01))
                             (< (cadr res) 0.60))
                      (progn
                        (if (null dmin) (setq dmin d))
                        (setq dmax d)))))
                (setq d (+ d 0.05)))
              (if (null dmin)
                ;; no lo toca: descartar la referencia, insert queda intacto
                (if (entget ref) (entdel ref))
                (progn
                  ;; piezas restantes fuera del frente de la rampa
                  (foreach seg (list (list 0.0 dmin) (list dmax len))
                    (if (> (- (cadr seg) (car seg)) 0.15)
                      (progn
                        (setq piece
                          (urb:chain-subpoly ref (car seg) (cadr seg)))
                        (if piece
                          (urb:build-prefab-from-reference
                            piece sp prefab pwidth etapa sub mode destino)))))
                  (if (entget ref) (entdel ref))
                  (entdel en)
                  (setq cnt (1+ cnt))))))))
      (setq i (1+ i))))
  cnt)

;; distancia punto-segmento 2D (devuelve (dist)) -- version local segura
(defun cr:pt-seg-safe (px py x1 y1 x2 y2 / dx dy len2 t0 cx cy)
  (setq dx (- x2 x1) dy (- y2 y1))
  (setq len2 (+ (* dx dx) (* dy dy)))
  (if (< len2 1e-12)
    (list (distance (list px py) (list x1 y1)))
    (progn
      (setq t0 (/ (+ (* (- px x1) dx) (* (- py y1) dy)) len2))
      (if (< t0 0.0) (setq t0 0.0))
      (if (> t0 1.0) (setq t0 1.0))
      (setq cx (+ x1 (* t0 dx)) cy (+ y1 (* t0 dy)))
      (list (distance (list px py) (list cx cy))))))

(defun urb:ramp-frame-at (boundary i / p q a mid points sign probe)
  ;; Marco de un remate a partir del INDICE de su segmento en el contorno.
  (setq p (vlax-curve-getPointAtParam boundary i)
        q (vlax-curve-getPointAtParam boundary (1+ i)))
  (if (and p q (> (distance p q) 0.01))
    (progn
      (setq a (angle p q) mid (mapcar '(lambda(x y) (/ (+ x y) 2.0)) p q)
            points (urb:lwpoly-points-with-arcs-fine boundary)
            probe (polar mid (+ a (/ pi 2.0)) 0.01)
            sign (if (urb:point-in-poly-2d probe points) 1.0 -1.0))
      (list p a sign (distance p q) i))))

(defun urb:ramp-end-frame (boundary picked / cp par)
  ;; Marco del remate mas cercano a un punto marcado por el usuario.
  ;; Se conserva como respaldo: el flujo normal ya no pregunta.
  (setq cp (vlax-curve-getClosestPointTo boundary (trans picked 1 0))
        par (vlax-curve-getParamAtPoint boundary cp))
  (urb:ramp-frame-at boundary (fix par)))

;; 2026-09-08 (reporte del usuario: "no entiendo porque me pide remates
;; transversales"): los dos remates son las TAPAS del contorno, o sea los
;; dos segmentos que quedan en los extremos del eje largo. Es el mismo
;; problema que ya resuelve urb:costado-tip-segments para los costados del
;; anden, asi que se reutiliza tal cual y el comando deja de preguntar.
;; Devuelve (f1 f2) o nil si el contorno no permite decidirlo solo (ahi si
;; se le pregunta al usuario, como antes).
(defun urb:ramp-auto-frames (boundary / pts tips f1 f2)
  (setq pts (urb:lwpoly-points boundary))
  (if (< (length pts) 4)
    nil
    (progn
      (setq tips
        (vl-catch-all-apply 'urb:costado-tip-segments
          (list pts (urb:anden-axis-angle pts))))
      (if (or (vl-catch-all-error-p tips) (null tips))
        nil
        (progn
          (setq f1 (urb:ramp-frame-at boundary (car tips))
                f2 (urb:ramp-frame-at boundary (cadr tips)))
          (if (and f1 f2 (/= (nth 4 f1) (nth 4 f2))) (list f1 f2)))))))


(defun urb:ramp-terminal-region (region frame depth / en cutter piece result)
  (setq en (urb:ramp-quad-poly (car frame) (cadr frame) (caddr frame)
             0.0 0.0 (nth 3 frame) depth "URB-RAMPA")
        cutter (urb:add-region-from-object (urb:as-vla-object en)))
  (entdel en)
  (setq piece (vla-Copy region)
        result (vl-catch-all-apply 'vla-Boolean (list piece 1 cutter)))
  (urb:safe-delete cutter)
  (if (and (not (vl-catch-all-error-p result)) (urb:region-usable-p piece))
    piece (progn (urb:safe-delete piece) nil)))

;; Desarrollo del extremo de rampa (2026-09-08, pedido del usuario:
;; "quiero el desarrollo completo de la rampa con las aletas laterales").
;; En cada extremo de un paso peatonal LARGO se dibuja el desarrollo real
;; del modulo U-201 -- no solo la cuna A81 de v4.83:
;;   ALETA LATERAL de 0.60 m a cada lado = toperol 0.20 (gris con domos)
;;     + bordillo 0.10 + prefabricado A81 0.30 con su diagonal,
;;   BANDA CENTRAL de rampa entre las dos aletas, con la textura del
;;     material del paso,
;;   BORDILLO TRANSVERSAL de 0.20 que cierra el desarrollo contra el
;;     cuerpo del paso.
;; Las medidas son las del modulo parametrico que el usuario ya da por
;; bueno (urb:build-ramp): aleta 0.60, desarrollo de rampa 1.30, cierre
;; 0.20. Devuelve (objetos a81-und toperol-ml bordillo-ml area-rampa-m2).
(setq *urb-rampa-aleta* 0.60)
(setq *urb-rampa-desarrollo* 1.30)
(setq *urb-rampa-cierre* 0.20)
;; v4.95: fila de tableta de ALERTA a todo el ancho al pie del desarrollo
;; (B-Rampa modulo tipo c del plano: banda de cierre y luego la alerta)
(setq *urb-rampa-alerta* 0.20)

;; fondo total que ocupa el extremo del paso peatonal
(defun urb:paso-end-depth ()
  (+ *urb-rampa-desarrollo* *urb-rampa-cierre* *urb-rampa-alerta*))

;; Medidas minimas del extremo. 2026-09-10: dependen del TIPO, porque el
;; acceso vehicular usa las del plano de detalles (aleta 2,369 y 1,70 de
;; rampa mas 0,20 de tableta) y el paso peatonal las del modulo U-201.
(defun urb:ramp-end-min-width (tipo)
  (if (= tipo "RAMPA-VEHICULAR")
    (urb:rampav-min-width)
    (+ (* 2.0 *urb-rampa-aleta*) 0.50)))

(defun urb:ramp-end-min-length (tipo)
  (if (= tipo "RAMPA-VEHICULAR")
    (+ (* 2.0 (+ *urb-rampav-fondo* *urb-rampav-tableta*)) 0.50)
    (+ (* 2.0 (urb:paso-end-depth)) 0.50)))

;; v4.95 (2026-09-11, "sigue con el paso peatonal"): el extremo se rehizo
;; contra el plano (B-Rampa modulo tipo c, leido de su definicion) y la
;; foto 5 del usuario:
;;   - la SUPERFICIE de rampa ya no es una banda lisa: lleva la MISMA
;;     textura por bandas del cuerpo, de corrido. Aqui solo se devuelve su
;;     contorno; el llamador la une al cuerpo antes de modular las bandas.
;;   - la bajada se marca con un tono translucido, flecha y "BAJA" hacia
;;     la tapa (v = 0), como el acceso vehicular.
;;   - toperol y bordillo laterales bajan hasta la banda de cierre (antes
;;     quedaba un hueco en la esquina de 0,30 x 0,20).
;;   - fila de tableta de ALERTA a todo el ancho al pie del desarrollo.
;;   - el punteado del toperol va por patron (un hatch), no un circulo por
;;     domo.
;; Devuelve (objetos a81-und toperol-ml bordillo-ml area-rampa-m2
;;           ename-contorno-superficie toperol-m2).
(defun urb:ramp-end-objects
  (frame material / base axis sign L dev total alert objects obj hatch ent
   tramos tu1 tu2 bu1 bu2 au1 au2 du1 du2 a81 top-ml top-m2 bor-ml
   surface origin txt mid)
  (setq base (car frame) axis (cadr frame) sign (caddr frame) L (nth 3 frame))
  (setq dev *urb-rampa-desarrollo*
        total (+ *urb-rampa-desarrollo* *urb-rampa-cierre*)
        alert *urb-rampa-alerta*)
  (setq objects nil a81 0 top-ml 0.0 top-m2 0.0 bor-ml 0.0)
  (urb:ensure-layer "URB-RAMPA-A81" 8 T)
  (urb:ensure-layer "URB-RAMPA-BAJADA" 8 T)
  (urb:ensure-layer "URB-ANDEN-LOSETA-TOPEROL-20X20" 2 T)
  (urb:ensure-layer "URB-BORDILLO" 9 T)
  (if (not (tblsearch "APPID" "URB_ANDEN_GEN")) (regapp "URB_ANDEN_GEN"))
  ;; ---- las dos aletas laterales ----
  (setq tramos
    (list
      (list 0.0 0.20 0.20 0.30 0.30 *urb-rampa-aleta* 0.30 *urb-rampa-aleta*)
      (list (- L 0.20) L (- L 0.30) (- L 0.20)
            (- L *urb-rampa-aleta*) (- L 0.30)
            (- L 0.30) (- L *urb-rampa-aleta*))))
  (foreach tr tramos
    (setq tu1 (nth 0 tr) tu2 (nth 1 tr)
          bu1 (nth 2 tr) bu2 (nth 3 tr)
          au1 (nth 4 tr) au2 (nth 5 tr)
          du1 (nth 6 tr) du2 (nth 7 tr))
    ;; toperol de la aleta, hasta la banda de cierre
    (setq objects
      (append (reverse (urb:paso-toperol-quad base axis sign tu1 0.0 tu2 total))
              objects))
    (setq top-ml (+ top-ml total) top-m2 (+ top-m2 (* 0.20 total)))
    ;; bordillo de confinamiento de la aleta, tambien hasta el cierre
    (setq obj
      (urb:as-vla-object
        (urb:ramp-quad-poly base axis sign bu1 0.0 bu2 total "URB-BORDILLO")))
    (setq objects (cons obj objects))
    (setq hatch (vl-catch-all-apply 'urb:add-solid-hatch (list obj "URB-BORDILLO" 9)))
    (if (not (vl-catch-all-error-p hatch)) (setq objects (cons hatch objects)))
    (setq bor-ml (+ bor-ml total))
    ;; prefabricado A81: rectangulo CON DIAGONAL (la cuna inclinada)
    (setq obj
      (urb:as-vla-object
        (urb:ramp-quad-poly base axis sign au1 0.0 au2 dev "URB-RAMPA-A81")))
    (setq objects (cons obj objects))
    (setq hatch (vl-catch-all-apply 'urb:add-solid-hatch (list obj "URB-RAMPA-A81" 8)))
    (if (not (vl-catch-all-error-p hatch)) (setq objects (cons hatch objects)))
    (setq ent
      (urb:ramp-line base axis sign du1 0.0 du2 dev "URB-RAMPA-A81" 7))
    (if ent (setq objects (cons (urb:as-vla-object ent) objects)))
    (setq a81 (1+ a81)))
  ;; ---- superficie de la rampa, entre las dos aletas: su contorno va al
  ;;      llamador (textura de bandas de corrido con el cuerpo) ----
  (setq surface
    (urb:ramp-quad-poly base axis sign
      *urb-rampa-aleta* 0.0 (- L *urb-rampa-aleta*) dev "URB-RAMPA"))
  ;; ---- LA BAJADA: tono translucido + flecha "BAJA" hacia la tapa ----
  (setq obj
    (urb:as-vla-object
      (urb:ramp-quad-poly base axis sign
        *urb-rampa-aleta* 0.0 (- L *urb-rampa-aleta*) dev "URB-RAMPA-BAJADA")))
  (setq objects (cons obj objects))
  (setq hatch (vl-catch-all-apply 'urb:add-solid-hatch (list obj "URB-RAMPA-BAJADA" 8)))
  (if (not (vl-catch-all-error-p hatch))
    (progn
      (if (vlax-property-available-p hatch 'EntityTransparency T)
        (vl-catch-all-apply 'vlax-put-property
          (list hatch 'EntityTransparency "60")))
      (setq objects (cons hatch objects))))
  (setq mid (* 0.5 L))
  (foreach seg (list (list mid (- dev 0.20) mid 0.20)
                     (list (- mid 0.12) 0.40 mid 0.20)
                     (list (+ mid 0.12) 0.40 mid 0.20))
    (setq ent (urb:ramp-line base axis sign (nth 0 seg) (nth 1 seg)
                (nth 2 seg) (nth 3 seg) "URB-RAMPA-BAJADA" 7))
    (if ent (setq objects (cons (urb:as-vla-object ent) objects))))
  (setq origin (urb:ramp-local-point base axis sign (+ mid 0.22) (* 0.5 dev)))
  (setq txt (vl-catch-all-apply 'vla-AddText
    (list (urb:space) "BAJA" (vlax-3d-point (list (car origin) (cadr origin) 0.0)) 0.15)))
  (if (not (vl-catch-all-error-p txt))
    (progn
      (vla-put-Layer txt "URB-RAMPA-BAJADA")
      (vla-put-Rotation txt (+ axis (if (< sign 0) (- (/ pi 2.0)) (/ pi 2.0))))
      (setq objects (cons txt objects))))
  ;; ---- bordillo transversal que cierra el desarrollo ----
  (setq obj
    (urb:as-vla-object
      (urb:ramp-quad-poly base axis sign 0.30 dev (- L 0.30) total
        "URB-BORDILLO")))
  (setq objects (cons obj objects))
  (setq hatch (vl-catch-all-apply 'urb:add-solid-hatch (list obj "URB-BORDILLO" 9)))
  (if (not (vl-catch-all-error-p hatch)) (setq objects (cons hatch objects)))
  (setq bor-ml (+ bor-ml (- L 0.60)))
  ;; ---- fila de tableta de ALERTA a todo el ancho ----
  (setq objects
    (append (reverse (urb:paso-toperol-quad base axis sign 0.0 total L (+ total alert)))
            objects))
  (setq top-ml (+ top-ml L) top-m2 (+ top-m2 (* alert L)))
  (list (reverse objects) a81 top-ml bor-ml
    (* (- L (* 2.0 *urb-rampa-aleta*)) dev) surface top-m2)
)

;; Franja de toperol (tableta de alerta) en coordenadas locales: contorno,
;; relleno y punteado por patron (con respaldo de circulos si el patron no
;; esta disponible en este dibujo). Devuelve la lista de objetos.
(defun urb:paso-toperol-quad (base axis sign u1 v1 u2 v2 / obj hatch out lu lv uvh ent)
  (setq obj
    (urb:as-vla-object
      (urb:ramp-quad-poly base axis sign u1 v1 u2 v2 "URB-ANDEN-LOSETA-TOPEROL-20X20")))
  (setq out (list obj))
  (setq hatch
    (vl-catch-all-apply 'urb:add-solid-hatch
      (list obj "URB-ANDEN-LOSETA-TOPEROL-20X20" (urb:tactile-fill-color "TOPEROL" T))))
  (if (not (vl-catch-all-error-p hatch)) (setq out (cons hatch out)))
  (setq hatch (urb:toperol-texture obj "TOPEROL" "URB-ANDEN-LOSETA-TOPEROL-20X20" axis ""))
  (if hatch
    (setq out (cons hatch out))
    (progn
      (setq lu (+ (min u1 u2) 0.025))
      (while (<= lu (- (max u1 u2) 0.025 (- 1e-6)))
        (setq lv (+ (min v1 v2) 0.025))
        (while (<= lv (- (max v1 v2) 0.025 (- 1e-6)))
          (setq uvh (urb:ramp-frame-uv base axis sign lu lv))
          (setq ent
            (urb:add-circle-symbol (car uvh) (cadr uvh) *urb-toperol-radio*
              axis "URB-ANDEN-LOSETA-TOPEROL-20X20" ""
              (urb:tactile-symbol-color "TOPEROL" T)))
          (if ent (setq out (cons (urb:as-vla-object ent) out)))
          (setq lv (+ lv 0.05)))
        (setq lu (+ lu 0.05)))))
  (reverse out)
)

;; Eje del paso: punto medio entre sus dos costados, del remate 1 al 2.
;; Los costados son los tramos del contorno entre las dos tapas (las mismas
;; que eligio urb:ramp-auto-frames), asi que sigue un paso quebrado o curvo
;; (foto 5 del usuario) y no solo uno recto.
(defun urb:paso-centerline (boundary frames / pts n i1 i2 k side-a side-b la lb
   nseg res j ta pa pb)
  (setq pts (mapcar '(lambda (p) (list (car p) (cadr p))) (urb:lwpoly-points boundary))
        n (length pts)
        i1 (nth 4 (car frames)) i2 (nth 4 (cadr frames)))
  (setq k (rem (1+ i1) n) side-a (list (nth k pts)))
  (while (/= k i2) (setq k (rem (1+ k) n) side-a (cons (nth k pts) side-a)))
  (setq side-a (reverse side-a))
  (setq k (rem (1+ i2) n) side-b (list (nth k pts)))
  (while (/= k i1) (setq k (rem (1+ k) n) side-b (cons (nth k pts) side-b)))
  ;; side-b queda armado al reves: ya corre del remate 1 al 2
  (setq la (urb:chain-total-length side-a) lb (urb:chain-total-length side-b))
  (cond
    ((or (< la 1e-6) (< lb 1e-6)) nil)
    ;; los dos costados con los mismos vertices (lo normal al dibujar un
    ;; paso quebrado): vertice con vertice, asi el quiebre del eje queda en
    ;; su sitio exacto y las cunas de las bandas empatan sin traslape
    ((and (= (length side-a) (length side-b)) (<= (length side-a) 60))
      (mapcar '(lambda (pa pb)
                 (list (* 0.5 (+ (car pa) (car pb))) (* 0.5 (+ (cadr pa) (cadr pb)))))
              side-a side-b))
    (T
    (progn
      (setq nseg (max 2 (fix (+ 0.999 (/ (max la lb) 0.25)))) j 0 res nil)
      (repeat (1+ nseg)
        (setq ta (/ (float j) nseg)
              pa (urb:chain-point-at side-a (* ta la))
              pb (urb:chain-point-at side-b (* ta lb)))
        (setq res (cons (list (* 0.5 (+ (car pa) (car pb)))
                              (* 0.5 (+ (cadr pa) (cadr pb)))) res)
              j (1+ j)))
      (reverse res))))
)

;; punto a una distancia d sobre una cadena abierta de puntos
(defun urb:chain-point-at (chain d / rest p q seg found)
  (setq rest chain found nil)
  (while (and (cadr rest) (not found))
    (setq p (car rest) q (cadr rest) seg (distance p q))
    (if (or (<= d seg) (null (cddr rest)))
      (setq found
        (if (> seg 1e-9)
          (polar p (angle p q) (min d seg))
          p))
      (setq d (- d seg)))
    (setq rest (cdr rest)))
  (if found found (car chain))
)

;; Guia podotactil por el eje del cuerpo del paso: franja de 0,40 (dos
;; tabletas de 0,20) entre las dos filas de alerta. Devuelve
;; (objetos region-de-la-guia largo-ml area-m2) o nil. La region queda en
;; los objetos; el llamador la resta del cuerpo para que las bandas no la
;; pisen.
(defun urb:paso-guide-strip (centerline body trim / cl len sub c1 c2 strip res
   objects d ln hatch area)
  (setq cl (urb:open-poly-from-points centerline 0.0))
  (setq len (urb:curve-length cl))
  (if (> len (+ (* 2.0 trim) 0.40))
    (setq sub (vl-catch-all-apply 'urb:chain-subpoly (list cl trim (- len trim)))))
  (if (and cl (entget cl)) (entdel cl))
  (if (or (null sub) (vl-catch-all-error-p sub))
    nil
    (progn
      (setq c1 (urb:offset-poly sub 0.20) c2 (urb:offset-poly sub -0.20))
      (setq strip (if (and c1 c2) (urb:strip-band-region c1 c2 0.0)))
      (if c1 (entdel c1))
      (if c2 (entdel c2))
      (if strip
        (progn
          ;; que no se salga del cuerpo (paso que se angosta)
          (setq res (vl-catch-all-apply 'vla-Boolean
                      (list strip 1 (vla-Copy body))))
          (if (or (vl-catch-all-error-p res) (not (urb:region-usable-p strip)))
            (progn (urb:safe-delete strip) (setq strip nil)))))
      (if (null strip)
        (progn (entdel sub) nil)
        (progn
          (urb:ensure-layer "URB-ANDEN-LOSETA-GUIA-20X20" 8 T)
          (vla-put-Layer strip "URB-ANDEN-LOSETA-GUIA-20X20")
          (setq objects (list strip))
          (setq hatch (vl-catch-all-apply 'urb:add-solid-hatch
                        (list strip "URB-ANDEN-LOSETA-GUIA-20X20"
                              (urb:tactile-fill-color "GUIA" T))))
          (if (not (vl-catch-all-error-p hatch)) (setq objects (cons hatch objects)))
          ;; las barras de la tableta guia siguen el eje (tambien en curva)
          (foreach d '(0.15 0.05 -0.05 -0.15)
            (setq ln (urb:offset-poly sub d))
            (if ln
              (progn
                (vla-put-Layer (urb:as-vla-object ln) "URB-ANDEN-LOSETA-GUIA-20X20")
                (vla-put-Color (urb:as-vla-object ln) 7)
                (setq objects (cons (urb:as-vla-object ln) objects)))))
          (setq area (vla-get-Area strip))
          (setq len (urb:curve-length sub))
          (entdel sub)
          (list (reverse objects) strip len area)))))
)

;;; ---------------------------------------------------------------------
;; 2026-09-10 (decision del usuario sobre el paso peatonal largo: "textura
;; de anden, bandas gris/blanco"): el cuerpo del paso deja de ser un
;; relleno plano y toma la MISMA modelacion por bandas del anden -- fase
;; 0.80/1.00, gris = loseta 20x20 (solido gris + reticula 0.20 doble),
;; blanco = adoquin (solido blanco + juntas 0.10 al eje y 0.20
;; perpendicular). Es el mismo criterio que ya usa urb:build-ramp para el
;; modulo parametrico, aqui extraido para poder reutilizarlo.
;; Devuelve la lista de objetos creados, o nil si no pudo (el llamador
;; vuelve entonces al relleno plano de siempre).
(defun urb:decorate-region-anden-bands
  (region axis layer / pts bounds umin umax vmin vmax phase gray primera
   bw s e piece objects hatch origin iter)
  (setq pts (urb:region-outline-points region))
  (if (null pts) (setq pts (urb:object-box-points region)))
  (if (null pts)
    nil
    (progn
      (setq bounds (urb:project-bounds pts axis)
            umin (nth 0 bounds) umax (nth 1 bounds)
            vmin (- (nth 2 bounds) 0.5) vmax (+ (nth 3 bounds) 0.5))
      (setq phase (urb:composite-phase-state umin))
      (setq gray (car phase) primera T s umin objects nil iter 0)
      (while (and (< s (- umax 1e-6)) (< iter 20000))
        (setq iter (1+ iter))
        (setq bw (if primera (cdr phase) (if gray 0.80 1.00)))
        (if (< bw 0.001) (setq bw 0.001))
        (setq e (min umax (+ s bw)))
        (setq piece (urb:clip-stripe region s e vmin vmax axis))
        (if piece
          (progn
            (setq origin (urb:local-to-world s vmin axis))
            (setq objects
              (append (reverse (urb:band-piece-objects piece gray layer axis origin))
                      objects))))
        (setq s e gray (not gray) primera nil))
      (reverse objects))))

;; Relleno + juntas de UNA banda. Si la banda quedo partida en varias caras
;; (la corta la guia o un bordillo) el HATCH la rechaza entera: v4.95 la
;; decora cara por cara con el mismo origen (mismo arreglo que v4.94 hizo
;; en el anden) en vez de dejarla sin relleno.
(defun urb:band-piece-objects (piece gray layer axis origin / out hatch faces)
  (vla-put-Layer piece layer)
  (vla-put-Color piece (if gray 8 7))
  (setq hatch (vl-catch-all-apply 'urb:add-solid-hatch
                (list piece layer (if gray 8 7))))
  (if (and (vl-catch-all-error-p hatch)
           (setq faces (urb:region-split-faces piece)))
    (progn
      (urb:safe-delete piece)
      (foreach f faces
        (setq out (append out (urb:band-piece-objects f gray layer axis origin))))
      out)
    (progn
      (setq out (list piece))
      (if (not (vl-catch-all-error-p hatch)) (setq out (append out (list hatch))))
      (foreach h
        (if gray
          (list (vl-catch-all-apply 'urb:add-user-hatch
                  (list piece layer 0.20 axis T 9 origin)))
          (list (vl-catch-all-apply 'urb:add-user-hatch
                  (list piece layer 0.10 axis nil 8 origin))
                (vl-catch-all-apply 'urb:add-user-hatch
                  (list piece layer 0.20 (+ axis (/ pi 2.0)) nil 8 origin))))
        (if (not (vl-catch-all-error-p h)) (setq out (append out (list h)))))
      out))
)

;; v4.95: bandas del paso peatonal que SIGUEN EL EJE (paso quebrado o curvo,
;; como el de la foto 5). Cada tramo del eje recorta su cuna entre
;; bisectrices (la misma junta a inglete del anden segmentado) y la modula
;; con su propio angulo. La fase se ancla al EJE -- una banda gris de 0,80
;; centrada en el eje, donde va la guia, y 1,00 / 0,80 hacia los lados --,
;; asi en el quiebre las bandas de los dos tramos empatan a la misma
;; distancia del eje. Devuelve la lista de objetos.
(defun urb:paso-bands-along (region centerline layer / pts n edges bis span
   objects i slice th axis uc)
  (setq pts (urb:simplify-chain centerline (/ pi 90.0)) n (length pts))
  (if (< n 2)
    nil
    (progn
      ;; se alarga 1,00 m por cada punta: con una tapa oblicua la superficie
      ;; de rampa no puede quedar por fuera de la primera / ultima cuna
      (setq pts
        (append
          (list (polar (car pts) (angle (cadr pts) (car pts)) 1.0))
          (cdr (reverse (cdr (reverse pts))))
          (list (polar (last pts) (angle (nth (- n 2) pts) (last pts)) 1.0))))
      (setq edges (urb:open-chain-edges pts)
            bis (urb:chain-edge-bisectors edges)
            span (urb:points-span pts)
            i 0)
      (foreach e edges
        (setq slice (urb:clip-edge-wedge region (nth 0 e) (nth 1 e)
                      (car (nth i bis)) (cadr (nth i bis)) span))
        (if slice
          (progn
            (setq th (angle (nth 0 e) (nth 1 e)) axis (+ th (* 0.5 pi)))
            (setq uc (+ (* (car (nth 0 e)) (cos axis)) (* (cadr (nth 0 e)) (sin axis))))
            (setq objects (append objects
                            (urb:decorate-bands-anchored slice axis layer uc)))
            (urb:safe-delete slice)))
        (setq i (1+ i)))
      objects))
)

;; quita los vertices intermedios donde la cadena casi no gira
(defun urb:simplify-chain (pts tol / out prev a1 a2 k)
  (if (< (length pts) 3)
    pts
    (progn
      (setq out (list (car pts)) k 1)
      (while (< k (1- (length pts)))
        (setq a1 (angle (car out) (nth k pts))
              a2 (angle (nth k pts) (nth (1+ k) pts)))
        (if (and (> (distance (car out) (nth k pts)) 1e-6)
                 (> (abs (urb:turning-angle a1 a2)) tol))
          (setq out (cons (nth k pts) out)))
        (setq k (1+ k)))
      (reverse (cons (last pts) out))))
)

;; bandas 0,80 gris / 1,00 blanco sobre u = proyeccion en "axis", con la
;; fase anclada en uc: gris de (uc - 0,40) a (uc + 0,40)
(defun urb:decorate-bands-anchored (region axis layer uc / pts bounds umin umax
   vmin vmax s e gray piece objects origin iter)
  (setq pts (urb:region-outline-points region))
  (if (null pts) (setq pts (urb:object-box-points region)))
  (if pts
    (progn
      (setq bounds (urb:project-bounds pts axis)
            umin (nth 0 bounds) umax (nth 1 bounds)
            vmin (- (nth 2 bounds) 0.5) vmax (+ (nth 3 bounds) 0.5))
      (setq s (- uc 0.40) iter 0)
      (while (> s umin) (setq s (- s 1.80)))
      (setq gray T)
      (while (and (< s (- umax 1e-6)) (< iter 20000))
        (setq iter (1+ iter) e (+ s (if gray 0.80 1.00)))
        (if (> e (+ umin 1e-6))
          (progn
            (setq piece (urb:clip-stripe region (max s umin) (min e umax) vmin vmax axis))
            (if piece
              (progn
                (setq origin (urb:local-to-world s vmin axis))
                (setq objects
                  (append objects
                    (urb:band-piece-objects piece gray layer axis origin)))))))
        (setq s e gray (not gray)))))
  objects
)

;; areas de loseta (bandas grises) y adoquin (blancas) de una lista de
;; objetos de bandas: (gris blanco)
(defun urb:band-areas (objects / g b a)
  (setq g 0.0 b 0.0)
  (foreach o objects
    (if (and (= (type o) 'VLA-OBJECT)
             (= (vla-get-ObjectName o) "AcDbRegion"))
      (progn
        (setq a (vl-catch-all-apply 'vla-get-Area (list o)))
        (if (numberp a)
          (if (= (vla-get-Color o) 8) (setq g (+ g a)) (setq b (+ b a)))))))
  (list g b)
)

;;; RAMPA VEHICULAR segun el plano de detalles (2026-09-10, reporte del
;;; usuario: "la rampa vehicular no se parece en nada a como tiene que
;;; quedar"). Las medidas NO son estimadas: salen de leer el bloque
;;; B-RAMPA VEHICULAR de Detalles_Rampas.dwg con AutoCAD headless
;;; (evidencia en work/claude_20260910_detalles/vertices.txt). Modulo del
;;; plano: 10,00 m de frente.
;;;
;;;   aleta TRAPEZOIDAL a cada lado: (0,0) (2.369,1.70) (2.156,1.70) (0,0.20)
;;;     -- no es un rectangulo con diagonal, que es lo que se dibujaba
;;;   cara de rampa entre las dos aletas, a 1,70 m de fondo
;;;   banda de fondo de 0,20 m (v 1.50 -> 1.70) = bordillo A-80
;;;   fila de tableta podotactil de ALERTA a lo ancho del fondo (27
;;;     tabletas de 0,20 en el modulo de 10 m) y 8 tabletas bajando por
;;;     cada costado
;;;   4 bolardos, a 2,20 y 3,00 m de fondo
;;; ---------------------------------------------------------------------
;;; 2026-09-11 (foto acotada del usuario): el modulo mide 10,00 m en la
;;; LONGITUD MAYOR (el frente, sobre el bordillo de la via) y 5,80 m en la
;;; LONGITUD MENOR (la banda del fondo, entre las dos aletas). De ahi salen
;;; la aleta (10,00 - 5,80) / 2 = 2,10 y el arranque de la banda en la
;;; misma abscisa que el final del arco.
(setq *urb-rampav-mayor* 10.00)     ; referencia: longitud mayor del plano
(setq *urb-rampav-menor* 5.80)      ; referencia: longitud menor del plano
(setq *urb-rampav-aleta* 2.10)      ; ancho de la aleta sobre el bordillo
(setq *urb-rampav-aleta-int* 2.10)  ; su borde interior, ya al fondo
(setq *urb-rampav-fondo* 1.70)      ; profundidad de la rampa
(setq *urb-rampav-banda* 0.20)      ; banda de fondo (bordillo A-80)
(setq *urb-rampav-tableta* 0.20)    ; tableta podotactil 20 x 20
(setq *urb-rampav-lateral* 1.60)    ; 8 tabletas bajando por cada costado
(setq *urb-rampav-bolardo-v* '(2.20 3.00))
(setq *urb-rampav-bolardo-r* 0.075)

;; ancho minimo para que quepan las dos aletas y algo de cara de rampa
(defun urb:rampav-min-width ()
  (+ (* 2.0 *urb-rampav-aleta*) 1.00))

;; ancho real de aleta para un modulo de L metros: la del plano si cabe;
;; si el acceso es mas angosto se reparte lo que haya dejando 1,00 m de
;; cara de rampa, y nunca baja de 0,30.
(defun urb:rampav-aleta (L / a)
  (setq a (if (>= L (urb:rampav-min-width))
            *urb-rampav-aleta*
            (/ (- L 1.00) 2.0)))
  (max 0.30 a))

;;; ---------------------------------------------------------------------
;;; RAMPA VEHICULAR v2 (2026-09-11). Se rehizo despues de RENDERIZAR el
;;; plano (diagnosticos/detalles4920/r_vehicular.png) y de leer los arcos
;;; con su bulge (bulges.txt). Lo que muestra el plano y que v4.91 no hacia:
;;;
;;;  * el acceso NO reemplaza el anden: el patron de bandas del anden sigue
;;;    de corrido por debajo. El modulo es una SUPERPOSICION.
;;;  * las aletas son BORDILLOS CURVOS de 0,20: arco desde la esquina del
;;;    bordillo de la via hasta la cara de rampa, bulge 0,32172 (~71 grados).
;;;    v4.91 los dibujo como trapecios porque solo se habian leido los
;;;    vertices, no el bulge.
;;;  * al fondo de la bajada, una banda de bordillo A-80 de 0,20.
;;;  * la rampa va SOLO del lado de la via (una cara), no en los dos extremos.
;;;
;;; Pedido del usuario al ver el plano: "que se vea bien que parte es en
;;; bajada" y "que la franja de adoquines y losetas no quede por encima de
;;; los bordillos". Por eso las dos aletas y la banda se construyen como
;;; PREFABRICADOS de bordillo de verdad: el motor ya los usa como cortadores,
;;; asi que el patron del anden se recorta debajo de ellos, y ya salen en el
;;; presupuesto como bordillo prefabricado A-80. La bajada se marca con un
;;; tono translucido, las lineas en V del plano y una flecha "BAJA".
;;; ---------------------------------------------------------------------
(setq *urb-rampav-bulge* 0.32172)   ; arco de la aleta (del plano)
;; 2026-09-11: la banda del fondo arranca donde termina el arco, para que
;; su longitud sea exactamente la LONGITUD MENOR (10,00 - 2 x 2,10 = 5,80).
(setq *urb-rampav-banda-ini* 0.0)

;; Polilinea en coordenadas LOCALES de la rampa con arcos: verts = (u v
;; bulge). El marco local puede ser un reflejo (side-sign = -1) y en ese
;; caso el sentido de los arcos se invierte, asi que el bulge se multiplica
;; por side-sign.
(defun urb:ramp-bulge-poly (base axis sign verts closed layer / data w)
  (setq data
    (list '(0 . "LWPOLYLINE") '(100 . "AcDbEntity") '(100 . "AcDbPolyline")
          (cons 8 layer) (cons 90 (length verts)) (cons 70 (if closed 1 0))))
  (foreach v verts
    (setq w (urb:ramp-local-point base axis sign (car v) (cadr v)))
    (setq data
      (append data
        (list (cons 10 (list (car w) (cadr w)))
              (cons 42 (* (if (caddr v) (caddr v) 0.0) sign))))))
  (entmakex data))

;; Prefabricado de bordillo a lo largo de una referencia local. Devuelve la
;; referencia de bloque del prefabricado o nil.
;; 2026-09-11 (pedido del usuario: "agregame las capas correspondientes a
;; los prefabricados"): cada pieza entra con SU tipo de prefabricado, y el
;; tipo define capa, color y actividades del presupuesto. Las dos aletas
;; son la pieza de remate A-105 del plano (capa URB-REMATE-A-105) y la
;; banda del fondo es el bordillo A-80 (capa URB-BORDILLO).
(defun urb:rampav-bordillo
  (base axis sign verts side-uv etapa sub tipo destino / ref side r)
  (setq tipo (urb:safe-string tipo "Bordillo")
        destino (urb:safe-string destino "Rampa vehicular"))
  (setq ref (urb:ramp-bulge-poly base axis sign verts nil "URB-RAMPA"))
  (setq side (urb:ramp-local-point base axis sign (car side-uv) (cadr side-uv)))
  (setq r
    (vl-catch-all-apply 'urb:build-prefab-from-reference
      (list ref (list (car side) (cadr side) 0.0) tipo *urb-rampav-banda*
            etapa sub "Exterior" destino)))
  (if (or (null r) (vl-catch-all-error-p r))
    (progn (if (and ref (entget ref)) (entdel ref)) nil)
    r))

;; ML reales de un prefabricado ya creado (los guarda su atributo, y en un
;; arco no son la distancia entre extremos).
(defun urb:prefab-longitud-de (ref)
  (atof (urb:safe-string
          (cdr (assoc "LONGITUD_M" (urb:block-attribute-values ref))) "0")))

(defun urb:ramp-tactile-clear-prefabs (poly prefabs / region cutter result prefab)
  ;; Recorte real del encuentro tactil/aleta; no dibujar domos encima
  ;; del bordillo ni contabilizar esa superficie como loseta.
  (setq region (urb:add-region-from-object poly))
  (foreach prefab prefabs
    (if (urb:objects-bbox-overlap-p region (urb:as-vla-object prefab) 0.001)
      (progn
        (setq cutter (urb:block-footprint-region prefab))
        (if cutter
          (progn
            (urb:region-align-elevation cutter region)
            (setq result (vl-catch-all-apply 'vla-Boolean (list region 2 cutter)))
            (urb:safe-delete cutter)
            (if (vl-catch-all-error-p result)
              (vl-exit-with-error "No se pudo recortar la loseta contra el prefabricado.")))))))
  (vla-put-Layer region (vla-get-Layer poly))
  (urb:safe-delete poly)
  region)

(defun urb:ramp-input-data (tipo p1 p2 p3 / spec)
  (setq spec (urb:ramp-three-point-data p1 p2 p3))
  (if (and spec (= tipo "RAMPA-VEHICULAR"))
    (list (car spec) (cadr spec) (caddr spec) *urb-rampav-mayor* (nth 4 spec))
    spec))

(defun urb:ramp-vehicular-objects
  (frame etapa sub depth / base axis sign L a f b bi objects obj hatch ent
   u1 u2 lu lv tab-ml bol origin prefabs r fan-area vx txt a105 a80ml a85ml a86ml v)
  (setq base (car frame) axis (cadr frame) sign (caddr frame) L (nth 3 frame))
  (setq a (urb:rampav-aleta L)
        f *urb-rampav-fondo*
        b *urb-rampav-banda*
        bi (max 0.0 (- a *urb-rampav-banda-ini*)))
  ;; El frente seleccionado es el LIMITE via/anden. Reservar el espesor
  ;; real del sardinel hacia el tercer punto; tambien las curvas quedan
  ;; al interior. Conservar el fondo absoluto seleccionado por el usuario.
  (setq base (urb:ramp-local-point base axis sign 0.0 b)
        depth (- depth b))
  (setq objects nil prefabs nil tab-ml 0.0 bol 0 a105 0 a80ml 0.0 a85ml 0.0 a86ml 0.0)
  (urb:ensure-layer "URB-RAMPA" 4 T)
  (urb:ensure-layer "URB-RAMPA-BAJADA" 8 T)
  (urb:ensure-layer "URB-RAMPA-REMATE" 4 T)
  (urb:ensure-layer "URB-ANDEN-LOSETA-TOPEROL-20X20" 2 T)
  ;; 2026-09-11 (pedido del usuario): cada elemento prefabricado en SU capa
  ;; -- el bolardo alto M-63 del ppto ya no comparte capa con el remate.
  (urb:ensure-layer "URB-BOLARDO-M-63" 1 T)
  (if (not (tblsearch "APPID" "URB_ANDEN_GEN")) (regapp "URB_ANDEN_GEN"))

  ;; ---- LA BAJADA: abanico entre las dos aletas, del bordillo de la via
  ;;      (v = 0) a la banda del fondo. Tono translucido: el patron del
  ;;      anden se sigue viendo por debajo, como en el plano. ----
  (setq obj
    (urb:as-vla-object
      (urb:ramp-bulge-poly base axis sign
        (list (list 0.0 0.0 *urb-rampav-bulge*)
              (list a f 0.0)
              (list (- L a) f *urb-rampav-bulge*)
              (list L 0.0 0.0))
        T "URB-RAMPA-BAJADA")))
  (setq objects (cons obj objects))
  (setq fan-area (vl-catch-all-apply 'vla-get-Area (list obj)))
  (if (not (numberp fan-area)) (setq fan-area (* (- L a) f)))
  (setq hatch (vl-catch-all-apply 'urb:add-solid-hatch
                (list obj "URB-RAMPA-BAJADA" 8)))
  (if (not (vl-catch-all-error-p hatch))
    (progn
      (if (vlax-property-available-p hatch 'EntityTransparency T)
        (vl-catch-all-apply 'vlax-put-property
          (list hatch 'EntityTransparency "60")))
      (setq objects (cons hatch objects))))
  ;; lineas en V de la pendiente (plano: (0.98,0.2) (5.14,1.5) (9.02,0.2))
  (setq vx (* 0.4137 a))
  (setq ent (urb:ramp-line base axis sign vx 0.20 (* 0.5 L) (- f b) "URB-RAMPA-BAJADA" 8))
  (if ent (setq objects (cons (urb:as-vla-object ent) objects)))
  (setq ent (urb:ramp-line base axis sign (* 0.5 L) (- f b) (- L vx) 0.20 "URB-RAMPA-BAJADA" 8))
  (if ent (setq objects (cons (urb:as-vla-object ent) objects)))
  ;; flecha de pendiente: baja hacia la via (v = 0)
  (setq ent (urb:ramp-line base axis sign (* 0.5 L) (- f b 0.20) (* 0.5 L) 0.30 "URB-RAMPA-BAJADA" 7))
  (if ent (setq objects (cons (urb:as-vla-object ent) objects)))
  (setq ent (urb:ramp-line base axis sign (- (* 0.5 L) 0.15) 0.55 (* 0.5 L) 0.30 "URB-RAMPA-BAJADA" 7))
  (if ent (setq objects (cons (urb:as-vla-object ent) objects)))
  (setq ent (urb:ramp-line base axis sign (+ (* 0.5 L) 0.15) 0.55 (* 0.5 L) 0.30 "URB-RAMPA-BAJADA" 7))
  (if ent (setq objects (cons (urb:as-vla-object ent) objects)))
  (setq origin (urb:ramp-local-point base axis sign (+ (* 0.5 L) 0.25) (* 0.5 (- f b))))
  (setq txt (vl-catch-all-apply 'vla-AddText
    (list (urb:space) "BAJA" (vlax-3d-point (list (car origin) (cadr origin) 0.0)) 0.18)))
  (if (not (vl-catch-all-error-p txt))
    (progn
      (vla-put-Layer txt "URB-RAMPA-BAJADA")
      (vla-put-Rotation txt (+ axis (if (< sign 0) (- (/ pi 2.0)) (/ pi 2.0))))
      (setq objects (cons txt objects))))

  ;; ---- ALETAS = bordillos A-80 CURVOS de 0,20 (PREFABRICADOS) ----
  ;; 2026-09-11 (foto acotada del usuario): "el bordillo A-80 va en las
  ;; curvas y en la longitud menor". El largo del arco se mide de verdad
  ;; sobre la polilinea del prefabricado, no en linea recta.
  (setq r (urb:rampav-bordillo base axis sign
            (list (list 0.0 0.0 *urb-rampav-bulge*) (list a f 0.0))
            (list -1.0 (* 0.5 f)) etapa sub "Bordillo" "Rampa vehicular"))
  (if r (setq prefabs (cons r prefabs) a80ml (+ a80ml (urb:prefab-longitud-de r))))
  (setq r (urb:rampav-bordillo base axis sign
            (list (list L 0.0 (- *urb-rampav-bulge*)) (list (- L a) f 0.0))
            (list (+ L 1.0) (* 0.5 f)) etapa sub "Bordillo" "Rampa vehicular"))
  (if r (setq prefabs (cons r prefabs) a80ml (+ a80ml (urb:prefab-longitud-de r))))
  ;; ---- LONGITUD MENOR (5,80 en el modulo de 10) = sardinel bajo A-85 ----
  (setq r (urb:rampav-bordillo base axis sign
            (list (list bi (- f b) 0.0) (list (- L bi) (- f b) 0.0))
            (list (* 0.5 L) (+ f 1.0)) etapa sub "Sardinel A-85" "Rampa vehicular"))
  (if r (setq prefabs (cons r prefabs) a85ml (+ a85ml (- L (* 2.0 bi)))))
  ;; ---- LONGITUD MAYOR (10,00) = sardinel ALTO A-86 ----
  (setq r (urb:rampav-bordillo base axis sign
            (list (list 0.0 0.0 0.0) (list L 0.0 0.0))
            (list (* 0.5 L) -1.0) etapa sub "Sardinel A-86" "Rampa vehicular"))
  (if r (setq prefabs (cons r prefabs) a86ml (+ a86ml L)))

  ;; ---- tableta podotactil de ALERTA: fila al fondo y bajando por los
  ;;      costados (del bloque del plano) ----
  (setq u1 (+ a 0.03) u2 (- L a 0.03))
  (if (> (- u2 u1) *urb-rampav-tableta*)
    (progn
      (setq obj
        (urb:as-vla-object
          (urb:ramp-quad-poly base axis sign u1 f u2 (+ f *urb-rampav-tableta*)
            "URB-ANDEN-LOSETA-TOPEROL-20X20")))
      (setq obj (urb:ramp-tactile-clear-prefabs obj prefabs))
      (setq objects (cons obj objects))
      (setq hatch (vl-catch-all-apply 'urb:add-solid-hatch
                    (list obj "URB-ANDEN-LOSETA-TOPEROL-20X20"
                          (urb:tactile-fill-color "TOPEROL" T))))
      (if (not (vl-catch-all-error-p hatch)) (setq objects (cons hatch objects)))
      (setq hatch (urb:toperol-texture obj "TOPEROL" "URB-ANDEN-LOSETA-TOPEROL-20X20" axis ""))
      (if hatch (setq objects (cons hatch objects)))
      (setq tab-ml (+ tab-ml (/ (vla-get-Area obj) *urb-rampav-tableta*)))))
  ;; Alerta a TODO el fondo en los dos costados EXTERIORES del modulo.
  (foreach lu (list (list 0.0 *urb-rampav-tableta*)
                    (list (- L *urb-rampav-tableta*) L))
    (if (> depth 0.0)
      (progn
        (setq obj
          (urb:as-vla-object
            (urb:ramp-quad-poly base axis sign (car lu) 0.0
              (cadr lu)
              depth
              "URB-ANDEN-LOSETA-TOPEROL-20X20")))
        (setq obj (urb:ramp-tactile-clear-prefabs obj prefabs))
        (setq objects (cons obj objects))
        (setq hatch (vl-catch-all-apply 'urb:add-solid-hatch
                      (list obj "URB-ANDEN-LOSETA-TOPEROL-20X20"
                            (urb:tactile-fill-color "TOPEROL" T))))
        (if (not (vl-catch-all-error-p hatch)) (setq objects (cons hatch objects)))
        (setq hatch (urb:toperol-texture obj "TOPEROL" "URB-ANDEN-LOSETA-TOPEROL-20X20" axis ""))
        (if hatch (setq objects (cons hatch objects)))
        (setq tab-ml (+ tab-ml (/ (vla-get-Area obj) *urb-rampav-tableta*))))))

  ;; ---- borde del acceso hacia el predio (arcos de cuarto de circulo del
  ;;      plano) y los 4 bolardos, solo lo que quepa en el fondo dibujado --
  (if (and (>= L 5.5) (>= depth 2.5))
    (foreach v (list (list (list 0.0 0.0 0.41421) (list 2.5 2.5 0.0)
                           (list 2.5 (min depth 3.3) 0.0))
                     (list (list L 0.0 -0.41421) (list (- L 2.5) 2.5 0.0)
                           (list (- L 2.5) (min depth 3.3) 0.0)))
      (setq ent (urb:ramp-bulge-poly base axis sign v nil "URB-RAMPA-REMATE"))
      (if ent (setq objects (cons (urb:as-vla-object ent) objects)))))
  (foreach lu (list u1 u2)
    (foreach lv *urb-rampav-bolardo-v*
      (if (< lv depth)
        (progn
          (setq origin (urb:ramp-local-point base axis sign lu lv))
          (setq ent
            (entmakex
              (list '(0 . "CIRCLE") '(100 . "AcDbEntity")
                    '(8 . "URB-BOLARDO-M-63") '(62 . 256) '(100 . "AcDbCircle")
                    (cons 10 (list (car origin) (cadr origin) 0.0))
                    (cons 40 *urb-rampav-bolardo-r*))))
          (if ent
            (progn (setq objects (cons (urb:as-vla-object ent) objects))
                   (setq bol (1+ bol))))))))

  ;; (objetos area-de-bajada tableta-ML bordillo-ML-en-el-bloque bolardos
  ;;  prefabricados piezas-A105 bordillo-A80-ML sardinel-A85-ML) -- los
  ;;  bordillos y el sardinel se cobran como PREFABRICADOS; los ML aqui van
  ;;  solo de informe (atributos del bloque)
  (list (reverse objects) fan-area tab-ml 0.0 bol (reverse prefabs) a105 a80ml
        a85ml a86ml)
)

;; T si el paso da para llevar el desarrollo completo en los dos extremos
;; ("cuando son tramos largos", condicion del usuario).
;; punto medio de la tapa de un remate: es el que mide de verdad el largo
;; del modulo (los vertices de arranque son esquinas opuestas y en un paso
;; corto y ancho darian una diagonal enganosamente larga).
(defun urb:ramp-frame-mid (frame / p a L)
  (setq p (car frame) a (cadr frame) L (nth 3 frame))
  (list (+ (car p) (* 0.5 L (cos a))) (+ (cadr p) (* 0.5 L (sin a)))))

(defun urb:ramp-ends-fit-p (frames tipo)
  (and frames (= (length frames) 2)
       (>= (nth 3 (car frames)) (urb:ramp-end-min-width tipo))
       (>= (nth 3 (cadr frames)) (urb:ramp-end-min-width tipo))
       (>= (distance (urb:ramp-frame-mid (car frames))
                     (urb:ramp-frame-mid (cadr frames)))
           (urb:ramp-end-min-length tipo)))
)

;; Que tapa del modulo es la del lado de la VIA: la mas cercana a una via
;; creada (bloques URB_VIA). En el modo Tres puntos el primer remate ya es
;; el del bordillo por construccion, asi que solo decide en el modo
;; Dibujar. Sin vias en el dibujo se queda con el primero.
(defun urb:frame-nearest-road (frames / ss i en r lo hi mid best best-d d fr)
  (setq ss (ssget "_X" '((0 . "INSERT") (-3 ("URB_VIA")))) best nil best-d nil)
  (if (null ss)
    (car frames)
    (progn
      (foreach fr frames
        (setq mid (urb:ramp-frame-mid fr) i 0)
        (repeat (sslength ss)
          (setq en (ssname ss i) i (1+ i))
          (setq r (vl-catch-all-apply
            '(lambda () (vla-GetBoundingBox (urb:as-vla-object en) 'lo 'hi)
               (list (vlax-safearray->list lo) (vlax-safearray->list hi)))))
          (if (not (vl-catch-all-error-p r))
            (progn
              ;; distancia del punto medio a la caja de la via
              (setq d (distance mid
                        (list (max (car (car r)) (min (car mid) (car (cadr r))))
                              (max (cadr (car r)) (min (cadr mid) (cadr (cadr r)))))))
              (if (or (null best-d) (< d best-d)) (setq best fr best-d d))))))
      (if best best (car frames)))))

;; Borde del ACCESO VEHICULAR que da a la via. La deteccion automatica de
;; remates (urb:ramp-auto-frames) toma las tapas del eje LARGO, que en un paso
;; peatonal son los extremos; pero un acceso vehicular es mas ANCHO que
;; profundo (el del plano: 10 x 3,3 m) y su borde contra la via es un lado
;; largo. Aqui se prueban TODOS los bordes rectos: el mas cercano a una via
;; creada; sin vias en el dibujo, el mas largo. Devuelve (frame fondo).
;; 2026-09-11: dibujado con TRES PUNTOS, el frente lo marca el usuario (el
;; tramo 1 -> 2), asi que ese borde manda sobre cualquier deteccion
;; automatica. El comando deja aqui el punto medio del frente.
(setq *urb-rampav-frente* nil)

(defun urb:vehicular-curb-frame (source / n i fr cands best pts mid p a s d fondo)
  (setq n (fix (+ 0.5 (vlax-curve-getEndParam source))) i 0 cands nil)
  (while (< i n)
    (setq fr (vl-catch-all-apply 'urb:ramp-frame-at (list source i)))
    (if (and fr (not (vl-catch-all-error-p fr)) (> (nth 3 fr) 0.50))
      (setq cands (cons fr cands)))
    (setq i (1+ i)))
  (setq cands (reverse cands))
  (if (null cands)
    nil
    (progn
      (setq best
        (cond
          ;; el frente marcado con los 3 puntos
          ((and *urb-rampav-frente*
                (progn
                  (setq best nil d nil)
                  (foreach fr cands
                    (setq mid (distance (urb:ramp-frame-mid fr) *urb-rampav-frente*))
                    (if (or (null d) (< mid d)) (setq d mid best fr)))
                  (and best d (< d 0.30))))
           best)
          ((ssget "_X" '((0 . "INSERT") (-3 ("URB_VIA"))))
           (urb:frame-nearest-road cands))
          ;; el mas largo; en empate (bordes paralelos iguales) el que se
          ;; dibujo PRIMERO, que normalmente es el del bordillo
          (T
            (setq best (car cands))
            (foreach fr (cdr cands)
              (if (> (nth 3 fr) (+ (nth 3 best) 0.01)) (setq best fr)))
            best)))
      ;; fondo = la mayor distancia de un vertice del contorno a la linea
      ;; del borde, medida hacia adentro del modulo
      (setq p (car best) a (cadr best) s (caddr best) fondo 0.0)
      (foreach q (urb:lwpoly-points source)
        (setq d (* s (+ (* (- (car q) (car p)) (- (sin a)))
                        (* (- (cadr q) (cadr p)) (cos a)))))
        (if (> d fondo) (setq fondo d)))
      (list best fondo))))

;; Recorta los andenes que queden debajo de los prefabricados nuevos: el
;; anden se reconstruye UNA vez y en ese momento aplica todos los
;; cortadores (los bordillos curvos y la banda de la rampa incluidos).
(defun urb:recut-andenes-under (refs / hechos en res n)
  (setq hechos nil n 0)
  (foreach en (urb:all-anden-blocks)
    (if (and (not (member en hechos))
             (vl-some '(lambda (r)
                         (urb:objects-bbox-overlap-p (urb:as-vla-object r)
                                                     (urb:as-vla-object en) 0.02))
                      refs))
      (progn
        (setq hechos (cons en hechos))
        (setq res (vl-catch-all-apply 'urb:recut-one-anden-for-container (list en)))
        (if (and (not (vl-catch-all-error-p res)) res) (setq n (1+ n))))))
  n)

;; ACCESO VEHICULAR como SUPERPOSICION sobre el anden (2026-09-11). Una sola
;; cara de rampa, del lado de la via. El contorno dibujado solo marca la
;; extension del modulo (linea fina); no lleva relleno propio -- el patron
;; del anden se sigue viendo, igual que en el plano de detalles.
;;; 2026-09-11 (reporte del usuario: "en la rampa vehicular no me aparece
;;; detallada toda la rampa, tiene que verse como la imagen 2"). Dibujado
;;; con TRES PUNTOS donde todavia no hay anden, el modulo se veia casi
;;; vacio: las bandas que se ven en el plano son las del ANDEN y en la
;;; superposicion (v4.94) aparecen por debajo. Ahora, si NO hay anden
;;; debajo, el propio modulo pone su pavimento -- bandas del anden (gris
;;; loseta 20x20 / blanco adoquin 20x10), franja de guia podotactil a 2,50 m
;;; del bordillo (U-201) -- y las bandas se recortan debajo de los
;;; prefabricados (aletas A-105, banda A-80) y de las tabletas de alerta.
;;; Si SI hay anden debajo se mantiene la superposicion: el anden ya trae
;;; su patron y su area.
(defun urb:anden-under-p (source / ss i obj res)
  (setq ss (ssget "_X" '((0 . "INSERT") (-3 ("URB_ANDEN_BLOCK"))))
        obj (urb:as-vla-object source) i 0 res nil)
  (if (and ss obj)
    (while (and (< i (sslength ss)) (not res))
      (if (urb:objects-bbox-overlap-p obj (urb:as-vla-object (ssname ss i)) 0.05)
        (setq res T))
      (setq i (1+ i))))
  res
)

;; franja de guia podotactil: relleno gris con las barras de la tableta
(defun urb:guia-quad-objects (quad axis / obj out hatch)
  (urb:ensure-layer "URB-ANDEN-LOSETA-GUIA-20X20" 8 T)
  (setq obj (urb:as-vla-object quad) out (list obj))
  (setq hatch (vl-catch-all-apply 'urb:add-solid-hatch
                (list obj "URB-ANDEN-LOSETA-GUIA-20X20"
                      (urb:tactile-fill-color "GUIA" T))))
  (if (not (vl-catch-all-error-p hatch)) (setq out (cons hatch out)))
  (setq hatch (vl-catch-all-apply 'urb:add-user-hatch
                (list obj "URB-ANDEN-LOSETA-GUIA-20X20" 0.05 axis nil 7 nil)))
  (if (not (vl-catch-all-error-p hatch)) (setq out (cons hatch out)))
  (reverse out)
)

;; pavimento propio del modulo. Devuelve
;; (objetos gris-m2 blanco-m2 guia-ml guia-m2 toperol-m2) o nil.
(defun urb:vehicular-surface
  (contorno frame depth objetos / region axis L base sign objects p reg
   bandas gb guia guia-ml guia-m2 top-m2 quad ok)
  (setq base (car frame) axis (cadr frame) sign (caddr frame) L (nth 3 frame))
  (setq region (vl-catch-all-apply 'urb:add-region-from-object (list contorno)))
  (if (or (null region) (vl-catch-all-error-p region))
    nil
    (progn
      ;; prefabricados y contenedores: mismo recorte que usa el anden
      (setq region (urb:apply-anden-cutouts region))
      ;; las tabletas de alerta del modulo van ENCIMA: se restan del fondo
      (setq top-m2 0.0 objects nil)
      (foreach p objetos
        (setq ok
          (vl-catch-all-apply
            '(lambda ()
               (and (= (type p) 'VLA-OBJECT)
                    (member (vla-get-ObjectName p) '("AcDbPolyline" "AcDbRegion"))
                    (= (vla-get-Layer p) "URB-ANDEN-LOSETA-TOPEROL-20X20")
                    (or (= (vla-get-ObjectName p) "AcDbRegion")
                        (= (vla-get-Closed p) :vlax-true))))))
        (if (and ok (not (vl-catch-all-error-p ok)))
          (progn
            (setq reg (if (= (vla-get-ObjectName p) "AcDbRegion")
              (vla-Copy p) (vl-catch-all-apply 'urb:add-region-from-object (list p))))
            (if (and reg (not (vl-catch-all-error-p reg)))
              (progn
                (setq top-m2 (+ top-m2 (vla-get-Area reg)))
                (vl-catch-all-apply 'urb:region-align-elevation (list reg region))
                (if (vl-catch-all-error-p
                      (vl-catch-all-apply 'vla-Boolean (list region 2 reg)))
                  (urb:safe-delete reg)))))))
      ;; franja de guia paralela al bordillo
      (setq guia-ml 0.0 guia-m2 0.0)
      (if (> depth (+ *urb-guide-offset* 0.45))
        (progn
          (setq quad (urb:ramp-quad-poly base axis sign *urb-rampav-tableta* *urb-guide-offset*
                       (- L *urb-rampav-tableta*) (+ *urb-guide-offset* 0.40)
                       "URB-ANDEN-LOSETA-GUIA-20X20"))
          (setq reg (vl-catch-all-apply 'urb:add-region-from-object
                      (list (urb:as-vla-object quad))))
          (if (and reg (not (vl-catch-all-error-p reg)))
            (progn
              (vl-catch-all-apply 'urb:region-align-elevation (list reg region))
              (if (vl-catch-all-error-p
                    (vl-catch-all-apply 'vla-Boolean (list region 2 reg)))
                (urb:safe-delete reg))))
          (setq guia (urb:guia-quad-objects quad axis))
          (setq guia-ml (- L (* 2.0 *urb-rampav-tableta*)) guia-m2 (* guia-ml 0.40))
          (setq objects (append objects guia))))
      (setq bandas (vl-catch-all-apply 'urb:decorate-region-anden-bands
                     (list region axis "URB-RAMPA")))
      (if (vl-catch-all-error-p bandas) (setq bandas nil))
      (setq gb (urb:band-areas bandas))
      (urb:safe-delete region)
      (list (append bandas objects) (car gb) (cadr gb) guia-ml guia-m2 top-m2)))
)

(defun urb:build-vehicular-access
  (source frames etapa sub / doc copy elevation frame other depth endres
   objects name definition result attrs ref origin area prefabs n-rec surf
   gris blanco guia-ml guia-m2 top-m2 top-ml area-pav)
  (setq doc (urb:doc))
  (urb:ensure-layer "URB-RAMPA" 4 T)
  ;; el borde que da a la via se busca entre TODOS los lados del contorno
  ;; (ver urb:vehicular-curb-frame); los remates que llegan son de respaldo
  (setq other (vl-catch-all-apply 'urb:vehicular-curb-frame (list source)))
  (if (and other (not (vl-catch-all-error-p other)))
    (setq frame (car other) depth (cadr other))
    (setq frame (car frames)
          depth (if (cadr frames)
                  (distance (urb:ramp-frame-mid (car frames))
                            (urb:ramp-frame-mid (cadr frames)))
                  4.0)))
  (setq copy (vla-Copy (urb:as-vla-object source))
        elevation (vla-get-Elevation copy))
  (vla-put-Elevation copy 0.0)
  (vla-put-Layer copy "URB-RAMPA")
  (vla-put-Color copy 8)
  (setq objects (list copy) origin (car frame))
  (setq endres (vl-catch-all-apply 'urb:ramp-vehicular-objects
                 (list frame etapa sub depth)))
  (if (vl-catch-all-error-p endres)
    (progn (urb:safe-delete copy)
      (vl-exit-with-error (strcat "No se pudo dibujar el acceso vehicular: "
        (vl-catch-all-error-message endres)))))
  ;; sin anden debajo, el modulo pone su propio pavimento (bandas + guia);
  ;; con anden debajo se queda como superposicion (el anden ya lo trae)
  (setq surf
    (if (urb:anden-under-p source)
      nil
      (vl-catch-all-apply 'urb:vehicular-surface
        (list copy frame depth (car endres)))))
  (if (vl-catch-all-error-p surf) (setq surf nil))
  (setq objects (append objects (if surf (car surf)) (car endres))
        area (nth 1 endres)
        prefabs (nth 5 endres)
        top-ml (nth 2 endres))
  (setq gris (if surf (nth 1 surf) 0.0)
        blanco (if surf (nth 2 surf) 0.0)
        guia-ml (if surf (nth 3 surf) 0.0)
        guia-m2 (if surf (nth 4 surf) 0.0)
        top-m2 (* top-ml *urb-rampav-tableta*))
  ;; AREA_M2 = lo pavimentado por el modulo cuando el pavimento es suyo;
  ;; en superposicion sigue siendo el area de la bajada (el anden ya cuenta
  ;; la suya y no se puede contar dos veces)
  (setq area-pav (if surf (+ gris blanco guia-m2 top-m2) 0.0))
  (if (and surf (> area-pav 0.0)) (setq area area-pav))
  (setq name (strcat "URB_RAMPA_" (vla-get-Handle copy))
        definition (vla-Add (vla-get-Blocks doc) (vlax-3d-point '(0 0 0)) name)
        result (vl-catch-all-apply 'vla-CopyObjects
          (list doc (urb:object-array-variant objects) definition)))
  (if (vl-catch-all-error-p result)
    (progn (foreach obj objects (urb:safe-delete obj)) (urb:safe-delete definition)
      (foreach r prefabs (urb:safe-delete r))
      (vl-exit-with-error (vl-catch-all-error-message result))))
  (setq attrs
    (list (cons "TIPO" "RAMPA-VEHICULAR") (cons "ETAPA" etapa) (cons "SUBETAPA" sub)
      (cons "ANCHO_RAMPA" (rtos (nth 3 frame) 2 3))
      (cons "FONDO_M" (rtos *urb-rampav-fondo* 2 3))
      (cons "AREA_M2" (rtos area 2 6))
      (cons "TOPEROL_ML" (rtos (nth 2 endres) 2 6))
      (cons "A81_UND" "0")
      (cons "A105_UND" (itoa (nth 6 endres)))
      (cons "BORDILLO_A80_ML" (rtos (nth 7 endres) 2 3))
      (cons "SARDINEL_A85_ML" (rtos (nth 8 endres) 2 3))
      (cons "SARDINEL_A86_ML" (rtos (nth 9 endres) 2 3))
      (cons "LONGITUD_MAYOR_M" (rtos (nth 3 frame) 2 3))
      (cons "LONGITUD_MENOR_M"
        (rtos (max 0.0 (- (nth 3 frame)
                          (* 2.0 (max 0.0 (- (urb:rampav-aleta (nth 3 frame))
                                             *urb-rampav-banda-ini*)))))
              2 3))
      (cons "BORDILLO_PREFAB_UND" (itoa (length prefabs)))
      (cons "BOLARDO_UND" (itoa (nth 4 endres)))
      (cons "BORDILLO_ML" "0")
      (cons "AREA_BAJADA_M2" (rtos (nth 1 endres) 2 6))
      ;; acabados del pavimento propio (0 en superposicion)
      (cons "LOSETA_LISA_M2" (rtos gris 2 3))
      (cons "LOSETA_LISA_UND" (itoa (fix (+ 0.5 (/ gris 0.04)))))
      (cons "ADOQUIN_M2" (rtos blanco 2 3))
      (cons "ADOQUIN_20X10_UND" (itoa (fix (+ 0.5 (/ blanco 0.02)))))
      (cons "LOSETA_GUIA_ML" (rtos guia-ml 2 3))
      (cons "LOSETA_GUIA_UND" (itoa (fix (+ 0.5 (/ guia-m2 0.04)))))
      (cons "LOSETA_TOPEROL_UND" (itoa (fix (+ 0.5 (/ top-m2 0.04)))))
      (cons "SBG_M3" (rtos (* area-pav 0.50) 2 3))
      (cons "ARENA_M3" (rtos (* area-pav 0.04) 2 3))
      (cons "GEOTEXTIL_M2" (rtos (* area-pav 1.15) 2 3))
      (cons "MATERIAL" "Concreto")))
  (foreach obj attrs (urb:add-invisible-attribute definition origin (car obj) (car obj) (cdr obj)))
  (setq ref (vla-InsertBlock (urb:space) (vlax-3d-point (list 0.0 0.0 elevation)) name 1.0 1.0 1.0 0.0))
  (vla-put-Layer ref "URB-RAMPA")
  (urb:set-xdata-strings (urb:as-ename ref) "URB_RAMPA_BLOCK"
    (list "RAMPA-VEHICULAR" etapa sub (rtos (nth 3 frame) 2 6) "0" (rtos area 2 6)))
  (foreach obj objects (urb:safe-delete obj))
  ;; los bordillos curvos y la banda recortan el patron del anden de abajo
  (setq n-rec (if prefabs (urb:recut-andenes-under prefabs) 0))
  (prompt (strcat "\nAcceso vehicular hacia el tercer punto, sin invadir la via: "
    (rtos (nth 7 endres) 2 2) " ml A-80 en curvas, "
    (rtos (nth 8 endres) 2 2) " ml sardinel bajo A-85 (menor), "
    (rtos (nth 9 endres) 2 2) " ml sardinel alto A-86 (mayor), "
    (itoa (nth 4 endres)) " bolardos."
    (if surf
      (strcat " Pavimento propio del modulo: " (rtos (+ gris blanco) 2 2)
        " m2 de bandas (loseta " (rtos gris 2 2) " / adoquin " (rtos blanco 2 2)
        ") y " (rtos guia-ml 2 2) " ml de guia.")
      " Superposicion sobre el anden (el anden conserva su patron y su area).")
    (if (> n-rec 0) (strcat " Anden recortado bajo los bordillos: " (itoa n-rec) ".") "")))
  ref)

;; 2026-09-11: el acceso vehicular sigue su propio camino (superposicion
;; sobre el anden, una sola cara del lado de la via, aletas como bordillos
;; curvos prefabricados). El paso peatonal conserva el de siempre.
(defun urb:build-contour-ramp (source frames tipo etapa sub material)
  (if (= tipo "RAMPA-VEHICULAR")
    (urb:build-vehicular-access source frames etapa sub)
    (urb:build-contour-ramp-cuerpo source frames tipo etapa sub material)))

(defun urb:build-contour-ramp-cuerpo
  (source frames tipo etapa sub material / doc copy region body terminals frame term
   objects hatch area total-area edge-length attrs name definition result ref obj
   depth origin axis boundary-en elevation wedge-depth wedge-layer wedge-en
   a81-count ramp-ends endres extra-top extra-bor extra-area a80-ml bolardos
   bandas top-m2 guia-ml guia-m2 paso-largo end-objs surfaces tiled guia r
   area-tot gb cl)
  ;; Nuevo modulo 2D: contorno exacto (incluye arcos), remates elegidos,
  ;; paso adoquinado/liso o acceso vehicular liso. No inventa pendientes 3D.
  (setq doc (urb:doc) objects nil terminals nil edge-length 0.0)
  (urb:ensure-layer "URB-RAMPA" 4 T)
  (urb:ensure-layer "URB-RAMPA-REMATE" 4 T)
  (setq copy (vla-Copy (urb:as-vla-object source)) elevation (vla-get-Elevation copy))
  (vla-put-Elevation copy 0.0)
  (setq region (urb:add-region-from-object copy) body (vla-Copy region)
        total-area (vla-get-Area region) objects (list copy)
        axis (cadr (car frames)) origin (car (car frames))
        ;; 2026-09-08 (pedido del usuario, confirmado en dos pasos: primero
        ;; el paso peatonal y despues "la rampa vehicular tambien con
        ;; aletas"): los DOS tipos llevan el desarrollo completo de rampa
        ;; en sus extremos siempre que el modulo de la medida. Si no da la
        ;; medida se conserva el remate simple, y se dice por que -- antes
        ;; se caia al remate simple en silencio.
        ;; 2026-09-10: la profundidad que se recorta del cuerpo tiene que
        ;; ser LA MISMA que ocupa el modulo que se dibuja despues. El
        ;; acceso vehicular usa las medidas del plano (1,70 de rampa +
        ;; 0,20 de tableta de alerta); el paso peatonal, las del U-201.
        depth (cond ((urb:ramp-ends-fit-p frames tipo)
                      (setq ramp-ends T)
                      (if (= tipo "RAMPA-VEHICULAR")
                        (+ *urb-rampav-fondo* *urb-rampav-tableta*)
                        (urb:paso-end-depth)))
                    ((= tipo "RAMPA-VEHICULAR") 0.60)
                    (T 0.20)))
  (if ramp-ends
    (prompt
      (if (= tipo "RAMPA-VEHICULAR")
        (strcat "\nRampa vehicular segun el plano de detalles: aletas de "
          (rtos *urb-rampav-aleta* 2 2) " m, "
          (rtos *urb-rampav-fondo* 2 2)
          " m de rampa, bordillo A-80 al fondo, tableta podotactil de alerta y bolardos.")
        (strcat "\nDesarrollo de rampa en los dos extremos: aletas de "
          (rtos *urb-rampa-aleta* 2 2) " m y "
          (rtos *urb-rampa-desarrollo* 2 2) " m de rampa.")))
    (prompt
      (strcat "\nSin desarrollo de rampa: hacen falta tapas de "
        (rtos (urb:ramp-end-min-width tipo) 2 2) " m o mas y "
        (rtos (urb:ramp-end-min-length tipo) 2 2)
        " m entre ellas. Se dibuja el remate simple.")))
  (foreach frame frames
    (setq term (urb:ramp-terminal-region region frame depth))
    (if (null term) (progn (foreach obj objects (urb:safe-delete obj))
      (urb:safe-delete region) (urb:safe-delete body)
      (vl-exit-with-error "No se pudo construir un remate dentro del contorno.")))
    (setq edge-length (+ edge-length (nth 3 frame)) terminals (cons term terminals))
    (vla-Boolean body 2 (vla-Copy term)))
  (if (not (urb:region-usable-p body))
    (progn (foreach obj (append objects terminals) (urb:safe-delete obj))
      (urb:safe-delete region) (urb:safe-delete body)
      (vl-exit-with-error "Los remates cubren todo el modulo; marque extremos separados.")))
  ;; Con desarrollo de rampa el area util se arma igual en los dos tipos:
  ;; cuerpo + las dos bandas centrales (extra-area, sumada mas abajo). Las
  ;; aletas se cobran por ML/UND, como en el modulo parametrico. Sin
  ;; desarrollo, el acceso vehicular conserva su area total de siempre.
  (setq area
    (if (and (= tipo "RAMPA-VEHICULAR") (not ramp-ends))
      total-area
      (vla-get-Area body)))
  ;; 2026-09-08 (reporte del usuario: "de la rampa vehicular tampoco se ve
  ;; el dibujo de la rampa"): el remate se rellenaba en BLANCO sobre un
  ;; cuerpo tambien claro, asi que el modulo quedaba como un poligono liso.
  ;; Ahora el remate va en gris, que es el tono con el que el usuario ya
  ;; lee las piezas inclinadas del modulo parametrico.
  ;; Con desarrollo de rampa el remate NO se rellena: lo ocupa el modulo
  ;; (aletas + banda de rampa + bordillo de cierre), que se dibuja abajo.
  (foreach term terminals
    (vla-put-Layer term "URB-RAMPA-REMATE")
    (if ramp-ends
      (setq objects (append objects (list term)))
      (setq hatch (urb:add-solid-hatch term "URB-RAMPA-REMATE" 8)
            objects (append objects (list term hatch)))))
  (vla-put-Layer body "URB-RAMPA")
  (setq a81-count 0 extra-top 0.0 extra-bor 0.0 extra-area 0.0
        a80-ml 0.0 bolardos 0 top-m2 0.0 guia-ml 0.0 guia-m2 0.0
        paso-largo (and ramp-ends (/= tipo "RAMPA-VEHICULAR")))
  (if paso-largo
    ;; v4.95 (2026-09-11, "sigue con el paso peatonal"; referencia: la foto
    ;; 5 del usuario y B-Rampa modulo tipo c del plano). El paso largo se
    ;; arma como UN solo pavimento:
    ;;   cuerpo + superficies de rampa de los dos extremos, unidas, con la
    ;;     textura por bandas de corrido (en el plano la rampa sigue el
    ;;     patron del anden; antes era una banda lisa),
    ;;   guia podotactil de 0,40 por el eje, entre las dos filas de alerta,
    ;;   y encima de todo el modulo de cada extremo (aletas, bordillos,
    ;;     alerta y el tono de la bajada).
    ;; Las bandas se modulan sobre ese pavimento YA descontado de bordillos,
    ;; A81, toperol y guia: ninguna franja de adoquin o loseta queda por
    ;; encima de ellos (pedido del usuario).
    (progn
      (setq end-objs nil surfaces nil)
      (foreach frame frames
        (setq endres (vl-catch-all-apply 'urb:ramp-end-objects
                       (list frame material)))
        (if (vl-catch-all-error-p endres)
          (prompt (strcat "\nAVISO: no se pudo dibujar el desarrollo de rampa: "
                    (vl-catch-all-error-message endres)))
          (setq end-objs (append end-objs (car endres))
                a81-count (+ a81-count (nth 1 endres))
                extra-top (+ extra-top (nth 2 endres))
                extra-bor (+ extra-bor (nth 3 endres))
                top-m2 (+ top-m2 (nth 6 endres))
                surfaces (cons (nth 5 endres) surfaces))))
      (setq tiled (vla-Copy body))
      (foreach s surfaces
        (setq r (vl-catch-all-apply 'urb:add-region-from-object
                  (list (urb:as-vla-object s))))
        (if (entget s) (entdel s))
        (if (and r (not (vl-catch-all-error-p r)))
          (if (vl-catch-all-error-p
                (vl-catch-all-apply 'vla-Boolean (list tiled 0 r)))
            (urb:safe-delete r))))
      (setq cl (vl-catch-all-apply 'urb:paso-centerline (list source frames)))
      (if (vl-catch-all-error-p cl) (setq cl nil))
      (setq guia
        (if cl
          (vl-catch-all-apply 'urb:paso-guide-strip
            (list cl body (urb:paso-end-depth)))))
      (if (or (null guia) (vl-catch-all-error-p guia))
        (setq guia nil)
        (progn
          (vl-catch-all-apply 'vla-Boolean (list tiled 2 (vla-Copy (nth 1 guia))))
          (setq guia-ml (nth 2 guia) guia-m2 (nth 3 guia))))
      (setq area (vla-get-Area tiled))
      ;; bandas que siguen el eje (paso quebrado); sin eje, las de siempre
      (setq bandas
        (if cl
          (vl-catch-all-apply 'urb:paso-bands-along (list tiled cl "URB-RAMPA"))))
      (if (or (null bandas) (vl-catch-all-error-p bandas))
        (setq bandas (vl-catch-all-apply 'urb:decorate-region-anden-bands
                       (list tiled axis "URB-RAMPA"))))
      (urb:safe-delete tiled)
      (if (vl-catch-all-error-p bandas) (setq bandas nil))
      ;; AREA_M2 = todo lo pavimentado: bandas + guia + toperol (como el
      ;; AREA_M2 del anden, que tambien incluye sus franjas tactiles)
      (setq area (+ area guia-m2 top-m2))
      (setq objects (append objects (list body) bandas
                      (if guia (car guia)) end-objs)))
   (progn
  ;; 2026-09-10 (decision del usuario): el cuerpo del PASO PEATONAL lleva
  ;; la textura por bandas del anden -- por eso en el plano se ve oscuro y
  ;; texturizado y no como un relleno plano. El acceso vehicular conserva
  ;; su superficie lisa, que es como esta en el plano de detalles.
  (setq bandas
    (if (= tipo "PASO-PEATONAL")
      (vl-catch-all-apply 'urb:decorate-region-anden-bands
        (list body axis "URB-RAMPA"))))
  (if (and bandas (not (vl-catch-all-error-p bandas)))
    (setq objects (append objects (list body) bandas))
    (progn
      (setq bandas nil)
      (setq hatch (urb:add-solid-hatch body "URB-RAMPA"
                    (if (= material "Adoquin") 7 9))
            objects (append objects (list body hatch)))
      (if (= material "Adoquin")
        (setq objects (append objects (list
          (urb:add-user-hatch body "URB-RAMPA" 0.10 axis nil 8 origin)
          (urb:add-user-hatch body "URB-RAMPA" 0.20 (+ axis (/ pi 2.0)) nil 8 origin)))))))))
  ;; 2026-09-08 (pedido del usuario, foto 4: "en los extremos del paso
  ;; peatonal, cuando son tramos largos, me aparezca esa parte de la
  ;; rampa" -> confirmado despues: "quiero el DESARROLLO COMPLETO de la
  ;; rampa con las aletas laterales"). En un paso peatonal que da la
  ;; medida, cada extremo lleva el modulo real de U-201
  ;; (urb:ramp-end-objects): aleta lateral de 0.60 m a cada lado --
  ;; toperol 0.20 + bordillo 0.10 + A81 0.30 con su diagonal --, banda
  ;; central de rampa y bordillo transversal de cierre. Si no da la
  ;; medida, o en el acceso vehicular, se conserva la cuna simple:
  ;; rectangulo con diagonal. (v4.95: el paso largo ya se armo arriba.)
  (if (and ramp-ends (= tipo "RAMPA-VEHICULAR"))
    ;; 2026-09-10: el acceso vehicular deja de usar el modulo peatonal y
    ;; pasa a dibujarse como el plano de detalles -- aletas TRAPEZOIDALES,
    ;; banda de fondo con bordillo A-80, tableta podotactil de alerta al
    ;; fondo y por los dos costados, y 4 bolardos.
    (foreach frame frames
      (setq endres (vl-catch-all-apply 'urb:ramp-vehicular-objects (list frame)))
      (if (vl-catch-all-error-p endres)
        (prompt (strcat "\nAVISO: no se pudo dibujar la rampa vehicular: "
                  (vl-catch-all-error-message endres)))
        (setq objects (append objects (car endres))
              extra-area (+ extra-area (nth 1 endres))
              extra-top (+ extra-top (nth 2 endres))
              a80-ml (+ a80-ml (nth 3 endres))
              bolardos (+ bolardos (nth 4 endres))))))
  (progn
    ;; sin desarrollo de rampa: la cuna simple de siempre
    (if ramp-ends nil
     (progn
      (setq wedge-depth
        (cond
          ((= tipo "RAMPA-VEHICULAR") depth)
          ((and (= (length frames) 2)
                (>= (distance (car (car frames)) (car (cadr frames))) 2.0))
            0.30)
          (T nil)))
      (if wedge-depth
        (progn
          (if (/= tipo "RAMPA-VEHICULAR") (urb:ensure-layer "URB-RAMPA-A81" 8 T))
          (setq wedge-layer
            (if (= tipo "RAMPA-VEHICULAR") "URB-RAMPA-REMATE" "URB-RAMPA-A81"))
          (foreach frame frames
            ;; contorno de la cuna (solo en el paso: en el vehicular el
            ;; remate ya esta dibujado como region)
            (if (/= tipo "RAMPA-VEHICULAR")
              (progn
                (setq wedge-en
                  (urb:ramp-quad-poly (car frame) (cadr frame) (caddr frame)
                    0.0 0.0 (nth 3 frame) wedge-depth wedge-layer))
                (setq obj (urb:as-vla-object wedge-en))
                (setq hatch (vl-catch-all-apply 'urb:add-solid-hatch
                              (list obj wedge-layer 8)))
                (setq objects (append objects (list obj)))
                (if (not (vl-catch-all-error-p hatch))
                  (setq objects (append objects (list hatch))))
                (setq a81-count (1+ a81-count))))
            ;; la DIAGONAL: es lo que hace que se lea como rampa y no como
            ;; un poligono liso
            (setq boundary-en
              (urb:ramp-line (car frame) (cadr frame) (caddr frame)
                0.0 0.0 (nth 3 frame) wedge-depth wedge-layer 8))
            (setq objects
              (append objects (list (urb:as-vla-object boundary-en))))))))))
  (urb:safe-delete region)
  (setq name (strcat "URB_RAMPA_" (vla-get-Handle copy))
        definition (vla-Add (vla-get-Blocks doc) (vlax-3d-point '(0 0 0)) name)
        result (vl-catch-all-apply 'vla-CopyObjects
          (list doc (urb:object-array-variant objects) definition)))
  (if (vl-catch-all-error-p result)
    (progn (foreach obj objects (urb:safe-delete obj)) (urb:safe-delete definition)
      (vl-exit-with-error (vl-catch-all-error-message result))))
  (setq attrs (list (cons "TIPO" tipo) (cons "ETAPA" etapa) (cons "SUBETAPA" sub)
    (cons "ANCHO_RAMPA" (rtos (/ edge-length 2.0) 2 3))
    (cons "FONDO_M" "0") (cons "AREA_M2" (rtos (+ area extra-area) 2 6))
    (cons "TOPEROL_ML" (rtos extra-top 2 3)) (cons "A81_UND" (itoa a81-count))
    (cons "BORDILLO_A80_ML" (rtos a80-ml 2 3))
    (cons "BOLARDO_UND" (itoa bolardos))
    (cons "BORDILLO_ML"
      (if (= tipo "PASO-PEATONAL")
        (rtos (+ edge-length extra-bor) 2 6)
        (rtos extra-bor 2 6)))
    (cons "MATERIAL" material)))
  ;; v4.95: cantidades de acabado y de estructura en propiedades (pedido del
  ;; usuario: "que en propiedades quede de una vez lo de prefabricados,
  ;; losetas, adoquin, y los rellenos, que son iguales que los del anden").
  ;; Loseta = bandas grises (20x20, 25 und/m2); adoquin = bandas blancas
  ;; (20x10, 50 und/m2); estructura con los mismos espesores del anden.
  (if (/= tipo "RAMPA-VEHICULAR")
    (progn
      (setq area-tot (+ area extra-area)
            gb (cond (bandas (urb:band-areas bandas))
                     ((= material "Adoquin") (list 0.0 area-tot))
                     (T (list 0.0 0.0))))
      (setq attrs
        (append attrs
          (list
            (cons "LOSETA_LISA_M2" (rtos (car gb) 2 3))
            (cons "LOSETA_LISA_UND" (itoa (fix (+ 0.5 (/ (car gb) 0.04)))))
            (cons "ADOQUIN_M2" (rtos (cadr gb) 2 3))
            (cons "ADOQUIN_20X10_UND" (itoa (fix (+ 0.5 (/ (cadr gb) 0.02)))))
            (cons "LOSETA_GUIA_ML" (rtos guia-ml 2 3))
            (cons "LOSETA_GUIA_UND" (itoa (fix (+ 0.5 (/ guia-m2 0.04)))))
            (cons "LOSETA_TOPEROL_UND" (itoa (fix (+ 0.5 (/ top-m2 0.04)))))
            (cons "SBG_M3" (rtos (* area-tot 0.50) 2 3))
            (cons "ARENA_M3" (rtos (* area-tot 0.04) 2 3))
            (cons "GEOTEXTIL_M2" (rtos (* area-tot 1.15) 2 3)))))))
  (foreach obj attrs (urb:add-invisible-attribute definition origin (car obj) (car obj) (cdr obj)))
  (setq ref (vla-InsertBlock (urb:space) (vlax-3d-point (list 0.0 0.0 elevation)) name 1.0 1.0 1.0 0.0))
  (vla-put-Layer ref "URB-RAMPA")
  (urb:set-xdata-strings (urb:as-ename ref) "URB_RAMPA_BLOCK"
    (list tipo etapa sub (rtos (/ edge-length 2.0) 2 6) "0" (rtos area 2 6)))
  (foreach obj objects (urb:safe-delete obj))
  ref)

(defun urb:ramp-three-point-data (p1 p2 p3 / a width v depth sign)
  ;; Puntos WCS. El segundo fija eje y ancho; el tercero sentido y fondo.
  (setq width (distance (list (car p1) (cadr p1)) (list (car p2) (cadr p2))))
  (if (> width 0.01)
    (progn
      (setq a (angle p1 p2)
            v (+ (* (- (car p3) (car p1)) (- (sin a)))
                 (* (- (cadr p3) (cadr p1)) (cos a)))
            depth (abs v) sign (if (< v 0.0) -1.0 1.0))
      (if (> depth 0.01) (list p1 a sign width depth)))))

(defun urb:create-contour-ramp-command
  (selection / *error* doc source p1 p2 p3 f1 f2 material result undo-open
   mode previous oldwidth spec axis sign width depth endp autof kw recorte)
  (setq doc (urb:doc))
  (defun *error* (msg)
    (if oldwidth (setvar "PLINEWID" oldwidth))
    (if (and source (entget source) (not result)) (entdel source))
    (if undo-open (vla-EndUndoMark doc))
    (if msg (prompt (strcat "\nRAMPA: " msg))) (princ))
  (initget "Tres Dibujar")
  (setq mode (getkword "\nModelar con [Tres puntos/Dibujar contorno] <Tres>: "))
  (setq *urb-rampav-frente* nil)
  (vla-StartUndoMark doc) (setq undo-open T)
  (urb:ensure-layer "URB-RAMPA" 4 T)
  (if (= mode "Dibujar")
    (progn
      (prompt "\nDibuje el contorno; use Arco si necesita curva y Cerrar para terminar.")
      (setq previous (entlast) oldwidth (getvar "PLINEWID"))
      (setvar "PLINEWID" 0.0)
      (urb:draw-polyline-interactive oldwidth)
      (setvar "PLINEWID" oldwidth) (setq oldwidth nil)
      (if (and (not (eq previous (entlast)))
               (= (cdr (assoc 0 (entget (entlast)))) "LWPOLYLINE")
               (>= (cdr (assoc 90 (entget (entlast)))) 3))
        (progn
          (setq source (entlast))
          (vla-put-Closed (urb:as-vla-object source) :vlax-true))))
    (progn
      (setq p1 (getpoint "\n1. Punto INICIAL: "))
      (if p1 (setq p2 (getpoint p1
        (if (= (car selection) "RAMPA-VEHICULAR")
          "\n2. Direccion del EJE (frente fijo de 10.00 m): "
          "\n2. EJE y ancho: marque hasta donde llega el frente: "))))
      (if p2 (setq p3 (getpoint p1 "\n3. SENTIDO y FONDO: marque hacia donde llega: ")))
      (if p3
        (progn
          (setq spec (urb:ramp-input-data (car selection) (trans p1 1 0) (trans p2 1 0) (trans p3 1 0)))
          (if spec
            (progn
              (setq axis (cadr spec) sign (caddr spec) width (nth 3 spec) depth (nth 4 spec))
              (if (> depth (if (= (car selection) "RAMPA-VEHICULAR")
                            (+ *urb-rampav-fondo* *urb-rampav-banda* *urb-rampav-tableta*) 0.40))
                (progn
                  (setq source (urb:ramp-quad-poly (car spec) axis sign 0.0 0.0 width depth "URB-RAMPA"))
                  (vla-put-Elevation (urb:as-vla-object source) (caddr (car spec)))
                  (setq p1 (trans (urb:ramp-local-point (car spec) axis sign (/ width 2.0) 0.0) 0 1)
                        p2 (trans (urb:ramp-local-point (car spec) axis sign (/ width 2.0) depth) 0 1))
                  ;; el frente (1 -> 2) es el borde de la via del acceso
                  ;; vehicular, aunque no sea el lado mas largo del modulo
                  (setq endp (urb:ramp-local-point (car spec) axis sign (/ width 2.0) 0.0)
                        *urb-rampav-frente* (list (car endp) (cadr endp))))
                (prompt "\nFondo insuficiente para los remates; no se ha creado el modulo."))))))))
  (if (and source (= (cdr (assoc 0 (entget source))) "LWPOLYLINE")
           (= 1 (logand 1 (cdr (assoc 70 (entget source))))))
    (progn
      ;; 2026-09-08 (reporte del usuario: "no entiendo porque me pide
      ;; remates transversales"): los remates son las dos TAPAS del
      ;; contorno -- los segmentos de los extremos del eje largo -- y el
      ;; programa ya sabe encontrarlas solo (urb:ramp-auto-frames, el
      ;; mismo criterio que usan los costados del anden). Solo se
      ;; pregunta si el contorno no permite decidirlo.
      (if (= mode "Dibujar")
        (progn
          (setq autof (urb:ramp-auto-frames source))
          (if autof
            (progn
              (setq f1 (car autof) f2 (cadr autof))
              (prompt
                (strcat "\nRemates transversales detectados solos: "
                  (rtos (nth 3 f1) 2 2) " m y " (rtos (nth 3 f2) 2 2) " m.")))
            (progn
              (prompt "\nNo se pudieron identificar las dos tapas del contorno.")
              (setq p1 (getpoint "\nMarque el PRIMER remate transversal del contorno: "))
              (if p1 (setq p2 (getpoint "\nMarque el SEGUNDO remate transversal: ")))))))
      (if (and (null f1) p1 p2)
        (setq f1 (urb:ramp-end-frame source p1) f2 (urb:ramp-end-frame source p2)))
      (if (and f1 f2)
        (progn
          (if (and f1 f2 (/= (nth 4 f1) (nth 4 f2)))
            (progn
              (setq material "Concreto")
              (if (= (car selection) "PASO-PEATONAL")
                (progn (initget "Adoquin Concreto")
                  (setq material (getkword "\nAcabado del paso [Adoquin/Concreto] <Adoquin>: "))
                  (if (null material) (setq material "Adoquin"))))
              (prompt (if (= (car selection) "PASO-PEATONAL")
                "\nConfinamientos transversales de 0.20 m; longitud libre segun contorno."
                "\nAcceso liso con remates de 0.60 m en los extremos."))
              (setq result (urb:build-contour-ramp source (list f1 f2)
                (car selection) (cadr selection) (caddr selection) material))
              ;; 2026-09-10 (pedido del usuario): antes esto avisaba "no se
              ;; recortan objetos vecinos". Ahora se ofrece recortar lo que
              ;; queda DEBAJO del modulo -- andenes, zonas verdes y
              ;; prefabricados -- para que el area no quede contada dos
              ;; veces. Por defecto SI: es el caso normal.
              ;; 2026-09-11: el acceso vehicular no preguntaba (superposicion,
              ;; solo recortaba el anden bajo sus bordillos). 5.6.2 (pedido
              ;; del usuario: "rampas peatonales, vehiculares y pasos
              ;; peatonales sobre un anden o zona verde: que se corte el anden
              ;; y se recalcule el movimiento de tierras y el resto de
              ;; cantidades"): ahora tambien pregunta.
              (if result
                (progn
                  (initget "Si No")
                  (setq kw (getkword
                    "\nRecortar lo que quedo debajo del modulo (andenes, zonas verdes, prefabricados)? [Si/No] <Si>: "))
                  (if (= kw "No")
                    (prompt "\nModulo creado; no se recortaron los objetos vecinos.")
                    (progn
                      (setq recorte
                        (vl-catch-all-apply 'urb:recut-vecinos-bajo
                          (list (urb:as-ename result))))
                      (if (vl-catch-all-error-p recorte)
                        (prompt (strcat "\nModulo creado, pero el recorte fallo: "
                          (vl-catch-all-error-message recorte)))
                        (prompt (strcat "\nModulo creado. Recortados: "
                          (itoa (car recorte)) " anden(es) y "
                          (itoa (cadr recorte)) " zona(s) verde(s)."))))))))
            (prompt "\nSeleccione dos remates distintos del contorno.")))))
    (prompt "\nNo se ha completado una geometria valida."))
  (if (and source (entget source)) (entdel source))
  (if undo-open (vla-EndUndoMark doc))
  (princ))

(defun urb:create-ramp-command (/ selection)
  (setq selection (urb:rampa-dialog))
  (if selection
    (if (= (car selection) "RAMPA-PEATONAL")
      (urb:create-pedestrian-ramp-command selection)
      (urb:create-contour-ramp-command selection)))
  (princ))

(defun urb:create-pedestrian-ramp-command
  (selection / *error* doc undo-open undo-result base-pt dir-pt side-pt width kw
   depth tipo etapa subetapa axis-angle side-sign block-ref center-pt total-half done
   ext ext-pt ext-sel ext-cp vproj dlg ncut picks mov pe u v pts recorte)
  ;; Rampa peatonal parametrica sobre el borde de la via, segun los
  ;; modulos de U-201: banda central lisa (2.00 o 3.00 m) + 2 aletas
  ;; laterales de 0.65 m con adoquin 20x10, fondo = ancho del anden
  ;; (3.50 / 4.00 / otro). Queda empaquetada en su propio bloque
  ;; URB_RAMPA_* con atributos y xdata para cantidades y para el cambio de
  ;; etapa/subetapa en lote.
  (setq doc (urb:doc))
  (defun *error* (message)
    (if undo-open
      (progn (vl-catch-all-apply 'vla-EndUndoMark (list doc)) (setq undo-open nil)))
    (if (and message
             (not (member message '("Function cancelled" "quit / exit abort"))))
      (prompt (strcat "\nERROR EN RAMPA: " message)))
    (princ))
  (setq undo-result (vl-catch-all-apply 'vla-StartUndoMark (list doc)))
  (setq undo-open (not (vl-catch-all-error-p undo-result)))
  ;; Flujo a pedido del usuario: punto inicial + eje + ancho + un CLICK
  ;; del lado hacia donde va la rampa (igual que el lado del toperol).
  ;; El fondo (3.50 default) es opcion del mismo prompt del ancho.
  ;; Etapa/subetapa arrancan en 1/1 (cambiables en lote).
  (setq depth *urb-anden-default-width*
        side-sign 1.0 width 2.00 tipo "RAMPA-PEATONAL"
        etapa "1" subetapa "1" ext 0.0)
  ;; 2026-08-21 v4.48.1 (pedido del usuario): VENTANA previa con etapa,
  ;; subetapa, ancho de banda y fondo -- el ancho por getkword de la
  ;; linea de comandos desaparece; el resto del flujo (punto inicial,
  ;; direccion, clic al bordillo) queda igual.
  (setq dlg selection)
  (if dlg
    (setq tipo (nth 0 dlg) etapa (nth 1 dlg) subetapa (nth 2 dlg)
          width (nth 3 dlg) depth (nth 4 dlg)))
  (setq base-pt
    (if dlg
      (getpoint "\nPunto INICIAL de la rampa sobre el borde de la via: ")))
  ;; 2026-09-02 v2 (pedido del usuario): el ancho NO va en la ventana --
  ;; el MISMO clic sobre el borde define la direccion Y HASTA DONDE va la
  ;; rampa (modulo total a lo largo del borde = clic; banda central =
  ;; total - 1.20 de las dos aletas). Con la opcion Longitud se digita el
  ;; total y luego solo se marca la direccion.
  (if base-pt
    (progn
      (setq done nil)
      (while (not done)
        (initget "Longitud")
        (setq dir-pt
          (getpoint base-pt
            "\nClic HASTA DONDE va la rampa sobre el borde o [Longitud]: "))
        (cond
          ((and dir-pt (= (type dir-pt) 'STR) (= dir-pt "Longitud"))
            (initget 6)
            (setq kw (getreal "\nLongitud TOTAL de la rampa sobre el borde m: "))
            (if kw
              (progn
                (setq dir-pt
                  (getpoint base-pt "\nDireccion del borde (un clic): "))
                (if dir-pt
                  (progn
                    (setq width (max 0.50 (- kw 1.20)))
                    (setq done T))))))
          (dir-pt
            (setq width (max 0.50 (- (distance base-pt dir-pt) 1.20)))
            (setq done T))
          (T (setq done T))))))
  (if (and dir-pt (/= (type dir-pt) 'STR))
    (setq axis-angle (angle base-pt dir-pt)))
  (if axis-angle
    (prompt (strcat "\nRampa: modulo total " (rtos (+ width 1.2) 2 2)
      " m sobre el borde (banda central " (rtos width 2 2) " m).")))
  (if (and base-pt dir-pt axis-angle)
    (progn
      ;; 2026-08-12 v7 (pedido del usuario): el MISMO clic define el lado
      ;; del anden Y hasta donde llega el FONDO. Se clickea SOBRE el
      ;; BORDILLO donde termina la rampa (con osnap Nearest cae exacto);
      ;; la distancia perpendicular del clic al eje es el fondo. Sin
      ;; seleccionar entidades: solo el punto, asi funciona igual con
      ;; bordillos en bloques, xrefs o lineas sueltas. Un clic muy cerca
      ;; del eje (<0.5 m) solo define el lado y el fondo queda el
      ;; configurado (3.50 o el digitado con la opcion Fondo).
      (setq side-pt
        (getpoint base-pt
          (strcat "\nClic sobre el BORDILLO donde termina el fondo"
                  " (lado del anden; clic pegado al eje = fondo "
                  (rtos depth 2 2) " m): ")))
      (if side-pt
        (progn
          (setq vproj
            (+ (* (- (car side-pt) (car base-pt)) (- (sin axis-angle)))
               (* (- (cadr side-pt) (cadr base-pt)) (cos axis-angle))))
          (setq side-sign (if (>= vproj 0.0) 1.0 -1.0))
          (if (>= (abs vproj) 0.5)
            (progn
              (setq depth (abs vproj))
              (prompt
                (strcat "\nFondo tomado del clic sobre el bordillo: "
                        (rtos depth 2 2) " m."))))))
      ;; extension hasta el bordillo (2026-08-11, pedido del usuario): si el
      ;; punto inicial se marco sobre el borde del anden pero el bordillo de
      ;; la via queda mas alla, un click sobre ese borde extiende TODO el
      ;; modulo (rampa, A81, toperoles y bordillos verticales) hasta el
      ;; bordillo. Enter = sin extension (comportamiento anterior).
      ;; base-pt es el INICIO del modulo (u=0) SOBRE EL BORDILLO; el
      ;; modulo mide W+1.20 a lo largo del bordillo y crece hacia el anden
      (setq block-ref
        (urb:build-ramp base-pt axis-angle side-sign width depth etapa subetapa ext tipo))
      (if block-ref
        (progn
          ;; 2026-09-01: cortar el sardinel/bordillo existente bajo la rampa
          (initget "Si No")
          (setq kw (getkword
            "\nCortar sardinel/bordillo existente bajo la rampa? [Si/No] <Si>: "))
          (if (/= kw "No")
            (progn
              (setq ncut (urb:trim-prefabs-for-ramp
                base-pt axis-angle (+ width 1.2)))
              (if (> ncut 0)
                (prompt (strcat "\nPrefabricados cortados bajo la rampa: "
                  (itoa ncut) "."))
                (prompt "\nNo habia sardinel/bordillo bajo la rampa."))))
          ;; 5.6.2 (pedido del usuario): la rampa peatonal tambien recorta
          ;; el anden y la zona verde que quedan DEBAJO del modulo -- antes
          ;; solo cortaba los prefabricados y el area se contaba dos veces.
          ;; Mismo motor de la rampa por contorno y del paso peatonal; el
          ;; anden/zona recortado recalcula su movimiento de tierras.
          (initget "Si No")
          (setq kw (getkword
            "\nRecortar anden/zona verde debajo de la rampa? [Si/No] <Si>: "))
          (if (/= kw "No")
            (progn
              (setq recorte
                (vl-catch-all-apply 'urb:recut-vecinos-bajo
                  (list (urb:as-ename block-ref))))
              (if (vl-catch-all-error-p recorte)
                (prompt (strcat "\nEl recorte fallo: " (vl-catch-all-error-message recorte)))
                (prompt (strcat "\nRecortados bajo la rampa: "
                  (itoa (car recorte)) " anden(es) y "
                  (itoa (cadr recorte)) " zona(s) verde(s).")))))
          ;; 2026-09-01: corte/relleno opcional de la rampa (mismo motor de
          ;; zona verde: cotas de diseno intuitivas + malla contra SUP_TN)
          (initget "Si No")
          (setq kw (getkword
            "\nCalcular CORTE/RELLENO de la rampa? [Si/No] <No>: "))
          (if (= kw "Si")
            (progn
              (setq picks (urb:pick-design-cotas))
              (if (and picks (>= (length picks) 1))
                (progn
                  ;; rectangulo del modulo en el marco local de la rampa
                  (setq pts nil)
                  (foreach uv (list (list 0.0 0.0)
                                    (list (+ width 1.2) 0.0)
                                    (list (+ width 1.2) depth)
                                    (list 0.0 depth))
                    (setq u (car uv) v (* side-sign (cadr uv)))
                    (setq pts (cons
                      (list (+ (car base-pt)
                               (* u (cos axis-angle))
                               (* v (- (sin axis-angle))))
                            (+ (cadr base-pt)
                               (* u (sin axis-angle))
                               (* v (cos axis-angle))))
                      pts)))
                  (entmake (append
                    (list '(0 . "LWPOLYLINE") '(100 . "AcDbEntity")
                          '(100 . "AcDbPolyline") '(90 . 4) '(70 . 1))
                    (mapcar '(lambda (p) (cons 10 p)) (reverse pts))))
                  (setq pe (entlast))
                  ;; la rampa va dentro del anden: misma estructura
                  (setq mov (urb:earthworks-from-picks pe picks *urb-anden-depth*))
                  (if (entget pe) (entdel pe))
                  (if mov
                    (progn
                      (urb:set-xdata-strings
                        (urb:as-ename block-ref) "URB_RAMPA_MOV"
                        (list (rtos (car mov) 2 2) (rtos (cadr mov) 2 2)))
                      (prompt (strcat "\nCorte: " (rtos (car mov) 2 2)
                        " m3 | Relleno: " (rtos (cadr mov) 2 2) " m3"))))))))
          (prompt
           (strcat "\n" (nth 1 (assoc tipo *urb-rampa-tipos*))
                    " creada: superficie " (rtos (+ width 0.6) 2 2)
                    "m en la via (central " (rtos width 2 2)
                    "m), modulo total " (rtos (+ width 1.2) 2 2)
                    "m x " (rtos depth 2 2) "m | Etapa " etapa
                    ". Cambie etapa/subetapa en lote desde el menu URBANISMO.")))))
    (prompt "\nComando cancelado."))
  (if undo-open
    (progn (vl-catch-all-apply 'vla-EndUndoMark (list doc)) (setq undo-open nil)))
  (princ)
)

(defun urb:ramp-poly-pts (base-pt axis-angle side-sign lpts layer / wpts)
  ;; polilinea cerrada a partir de puntos LOCALES (u v) del marco de la rampa
  (setq wpts
    (mapcar
      '(lambda (p)
         (urb:ramp-local-point base-pt axis-angle side-sign (car p) (cadr p)))
      lpts))
  (entmake
    (append
      (list (cons 0 "LWPOLYLINE") (cons 100 "AcDbEntity") (cons 100 "AcDbPolyline")
            (cons 8 layer) (cons 90 (length wpts)) (cons 70 1))
      (mapcar '(lambda (p) (cons 10 p)) wpts)))
  (entlast)
)

(defun urb:ramp-frame-uv (base-pt axis-angle side-sign lu lv / w)
  ;; coordenadas del marco rotado (las que esperan clip-stripe y los
  ;; simbolos) para un punto LOCAL (u v) de la rampa
  (setq w (urb:ramp-local-point base-pt axis-angle side-sign lu lv))
  (list
    (+ (* (car w) (cos axis-angle)) (* (cadr w) (sin axis-angle)))
    (+ (* (- (car w)) (sin axis-angle)) (* (cadr w) (cos axis-angle))))
)

(defun urb:build-ramp
  (base-pt axis-angle side-sign width depth etapa subetapa ext tipo
   / doc objects obj hatch boundary area total v0 u1 ent trap treg breg forigin
   rorigin pair piece s e bw gray bp vlo vhi lu lv uvh corners
   block-name blocks block-definition copy-result insert-result block-ref
   block-ename)
  ;; Geometria segun los bloques B RAMPA T1/T2 reales de U-201 (disecados
  ;; 2026-08-09, espécimen sin rotar "T2 - 3.00MT - Anden 4.00MT"):
  ;;  - franjas laterales de 0.20 m a TODO el fondo del anden, con
  ;;    relleno solido (las columnas grises del plano)
  ;;  - superficie de rampa TRAPEZOIDAL: ancho W+0.60 contra la via
  ;;    (W=3.00 -> 3.60, la medida que el usuario senalo) cerrando a W al
  ;;    fondo de la rampa, con 1.10 m de desarrollo (v=0.20 a 1.30)
  ;;  - banda inferior v=1.30-1.50 y junta a v=1.70; el resto del fondo
  ;;    es anden normal (la rampa NO ocupa todo el fondo)
  ;; Ancho total del modulo = W + 1.20 (W=3.00 -> 4.20).
  ;; Componentes por capa segun el marcado del usuario sobre la foto del
  ;; plano (2026-08-09): AMARILLO superficie de rampa con el mismo patron
  ;; del anden (bandas gris/blanco + reticula); NARANJA toperol de 0.20 en
  ;; los dos costados a todo el fondo; VERDE vigas de confinamiento (0.10
  ;; junto a cada toperol + una horizontal de 0.20 entre rampa y anden);
  ;; MORADO prefabricado A81 (las 2 cunas inclinadas que flanquean la
  ;; rampa). Todo queda unido en el mismo bloque URB_RAMPA_*.
  (setq doc (urb:doc))
  (urb:ensure-layer "URB-RAMPA" 7 T)
  (if (<= depth 1.70)
    (vl-exit-with-error "Fondo insuficiente: rampa peatonal y sardinel posterior requieren mas de 1.70 m."))
  (urb:ensure-layer "URB-RAMPA-A105" 6 T)
  (urb:ensure-layer "URB-SARDINEL-A-86" 3 T)
  (urb:ensure-layer "URB-ANDEN-LOSETA-TOPEROL-20X20" 2 T)
  (if (not (tblsearch "APPID" "URB_ANDEN_GEN")) (regapp "URB_ANDEN_GEN"))
  (setq total (+ width 1.20))
  ;; v0: arranque del modulo hacia la via. Con ext > 0 (2026-08-11) todo el
  ;; modulo se extiende hasta el bordillo de la via (v0 = -ext); el resto de
  ;; la geometria (bordillo horizontal 1.3-1.5, fondo, etc.) no cambia.
  (setq v0 (- (max 0.0 (if ext ext 0.0))))
  (setq objects nil)
  ;; contorno total del modulo
  (setq boundary
    (urb:ramp-quad-poly base-pt axis-angle side-sign 0.0 v0 total depth "URB-RAMPA"))
  (setq objects (cons (vlax-ename->vla-object boundary) objects))
  ;; NARANJA: toperol 0.20 en cada costado, a todo el fondo, con puntos
  (foreach u1 (list 0.0 (+ width 1.0))
    (setq obj
      (vlax-ename->vla-object
        (urb:ramp-quad-poly base-pt axis-angle side-sign
          u1 v0 (+ u1 0.2) depth "URB-ANDEN-LOSETA-TOPEROL-20X20")))
    (setq objects (cons obj objects))
    (setq hatch
      (vl-catch-all-apply 'urb:add-solid-hatch
        (list obj "URB-ANDEN-LOSETA-TOPEROL-20X20"
          (urb:tactile-fill-color "TOPEROL" T))))
    (if (not (vl-catch-all-error-p hatch)) (setq objects (cons hatch objects)))
    (setq lu (+ u1 0.025))
    (while (<= lu (+ u1 0.175 1e-6))
      (setq lv (+ v0 0.025))
      (while (<= lv (- depth 0.025))
        (setq uvh (urb:ramp-frame-uv base-pt axis-angle side-sign lu lv))
        (setq ent
          (urb:add-circle-symbol (car uvh) (cadr uvh) *urb-toperol-radio* axis-angle
            "URB-ANDEN-LOSETA-TOPEROL-20X20" ""
            (urb:tactile-symbol-color "TOPEROL" T)))
        (setq objects (cons (vlax-ename->vla-object ent) objects))
        (setq lv (+ lv 0.05)))
      (setq lu (+ lu 0.05))))
  ;; VERDE (correccion del usuario: es BORDILLO, no viga): 2 verticales de
  ;; 0.10 junto a cada toperol + 1 horizontal de 0.20 entre rampa y anden,
  ;; en la capa existente de bordillo
  (if (not (tblsearch "LAYER" "URB-BORDILLO"))
    (urb:ensure-layer "URB-BORDILLO" 9 T))
  (foreach u1 (list 0.2 (+ width 0.9))
    (setq obj
      (vlax-ename->vla-object
        (urb:ramp-quad-poly base-pt axis-angle side-sign
          u1 v0 (+ u1 0.1) depth "URB-BORDILLO")))
    (setq objects (cons obj objects))
    (setq hatch (vl-catch-all-apply 'urb:add-solid-hatch (list obj "URB-BORDILLO" 9)))
    (if (not (vl-catch-all-error-p hatch)) (setq objects (cons hatch objects))))
  (setq obj
    (vlax-ename->vla-object
      (urb:ramp-quad-poly base-pt axis-angle side-sign
        0.3 1.3 (+ width 0.9) 1.5 "URB-BORDILLO")))
  (setq objects (cons obj objects))
  (setq hatch (vl-catch-all-apply 'urb:add-solid-hatch (list obj "URB-BORDILLO" 9)))
  (if (not (vl-catch-all-error-p hatch)) (setq objects (cons hatch objects)))
  ;; MORADO: prefabricado A81 -- rectangulo CON DIAGONAL (no triangulo),
  ;; flanqueando la rampa a cada lado
  (foreach corners
    (list
      (list 0.3 0.6 (list 0.3 v0) (list 0.6 1.3))
      (list (+ width 0.6) (+ width 0.9) (list (+ width 0.9) v0) (list (+ width 0.6) 1.3)))
    (setq obj
      (vlax-ename->vla-object
        (urb:ramp-quad-poly base-pt axis-angle side-sign
          (nth 0 corners) v0 (nth 1 corners) 1.3 "URB-RAMPA-A105")))
    (setq objects (cons obj objects))
    ;; la diagonal del cuadrado (el borde inclinado de la rampa)
    (setq ent
      (urb:ramp-line base-pt axis-angle side-sign
        (car (nth 2 corners)) (cadr (nth 2 corners))
        (car (nth 3 corners)) (cadr (nth 3 corners))
        "URB-RAMPA-A105" 6))
    (setq objects (cons (vlax-ename->vla-object ent) objects)))
  ;; AMARILLO: superficie de rampa RECTANGULAR entre los dos A81 (2026-08-11,
  ;; correccion del usuario sobre el PDF: la rampa NO invade los A81 -- antes
  ;; era un trapecio hasta el borde exterior y su textura pintaba encima de
  ;; ellos -- y lleva la MISMA modelacion del anden que el fondo: la textura
  ;; se aplica por banda mas abajo, en el mismo bucle de fase que el fondo)
  (setq trap
    (urb:ramp-quad-poly base-pt axis-angle side-sign
      0.6 v0 (+ width 0.6) 1.3 "URB-RAMPA"))
  (setq obj (vlax-ename->vla-object trap))
  (setq objects (cons obj objects))
  (setq rorigin (urb:ramp-local-point base-pt axis-angle side-sign 0.3 0.0))
  (setq treg
    (vl-catch-all-apply 'urb:add-region-from-object (list obj)))
  ;; A-86 solicitado en el borde posterior, dentro del contorno. El
  ;; acabado termina contra su cara interior, no debajo del prefabricado.
  (setq obj (urb:as-vla-object
    (urb:ramp-quad-poly base-pt axis-angle side-sign
      0.3 (- depth 0.20) (+ width 0.9) depth "URB-SARDINEL-A-86")))
  (setq objects (cons obj objects))
  (setq hatch (vl-catch-all-apply 'urb:add-solid-hatch
    (list obj "URB-SARDINEL-A-86" 3)))
  (if (not (vl-catch-all-error-p hatch)) (setq objects (cons hatch objects)))
  ;; ZONA POSTERIOR: el fondo del modulo (del bordillo horizontal hasta el
  ;; final) con la MISMA modelacion del anden real: banda por banda (gris
  ;; loseta 20x20 / blanco adoquin 0.10x0.20), NO una reticula uniforme --
  ;; la textura se aplica por banda mas abajo, en el mismo bucle de fase.
  (setq ent
    (urb:ramp-quad-poly base-pt axis-angle side-sign
      0.3 1.5 (+ width 0.9) (- depth 0.20) "URB-RAMPA"))
  (setq obj (vlax-ename->vla-object ent))
  (setq objects (cons obj objects))
  (setq forigin (urb:ramp-local-point base-pt axis-angle side-sign 0.3 1.5))
  (setq breg
    (vl-catch-all-apply 'urb:add-region-from-object (list obj)))
  ;; bandas grises 0.80/1.00 compartidas (misma fase en rampa y fondo,
  ;; para que las bandas queden alineadas de corrido)
  (setq bp (+ (* (car base-pt) (cos axis-angle))
              (* (cadr base-pt) (sin axis-angle))))
  (setq vlo nil vhi nil)
  (foreach corners
    (list (list 0.3 v0) (list (+ width 0.9) v0)
          (list 0.3 depth) (list (+ width 0.9) depth))
    (setq uvh (urb:ramp-frame-uv base-pt axis-angle side-sign
                (car corners) (cadr corners)))
    (if (or (null vlo) (< (cadr uvh) vlo)) (setq vlo (cadr uvh)))
    (if (or (null vhi) (> (cadr uvh) vhi)) (setq vhi (cadr uvh))))
  (setq vlo (- vlo 0.5) vhi (+ vhi 0.5))
  ;; RAMPA y FONDO: la MISMA textura real del anden por banda (2026-08-11,
  ;; correccion del usuario sobre el PDF) -- gris = loseta 20x20 (solido
  ;; gris + reticula 0.20 doble, como urb:decorate-gray-stripe); blanco =
  ;; adoquin (solido blanco + juntas 0.10 al eje y 0.20 perpendicular, como
  ;; urb:decorate-white-stripe). Misma fase de bandas en las dos zonas (el
  ;; bucle de u es compartido) y mismo origen en u (0.3) para que las
  ;; columnas de adoquin queden alineadas de corrido entre rampa y fondo.
  (setq s 0.3 gray nil)
  (while (< s (+ width 0.9 -1e-6))
    (setq bw (if gray 0.80 1.00))
    (setq e (min (+ s bw) (+ width 0.9)))
    (foreach pair (list (list treg rorigin) (list breg forigin))
      (if (not (vl-catch-all-error-p (car pair)))
        (progn
          (setq piece
            (urb:clip-stripe (car pair) (+ bp s) (+ bp e) vlo vhi axis-angle))
          (if piece
            (progn
              (vla-put-Layer piece "URB-RAMPA")
              (setq objects (cons piece objects))
              (if gray
                (progn
                  (setq hatch
                    (vl-catch-all-apply 'urb:add-solid-hatch
                      (list piece "URB-RAMPA" 8)))
                  (if (not (vl-catch-all-error-p hatch))
                    (setq objects (cons hatch objects)))
                  (setq hatch
                    (vl-catch-all-apply 'urb:add-user-hatch
                      (list piece "URB-RAMPA" 0.20 axis-angle T 9 (cadr pair))))
                  (if (not (vl-catch-all-error-p hatch))
                    (setq objects (cons hatch objects))))
                (progn
                  (setq hatch
                    (vl-catch-all-apply 'urb:add-solid-hatch
                      (list piece "URB-RAMPA" 7)))
                  (if (not (vl-catch-all-error-p hatch))
                    (setq objects (cons hatch objects)))
                  (setq hatch
                    (vl-catch-all-apply 'urb:add-user-hatch
                      (list piece "URB-RAMPA" 0.10 axis-angle nil 8 (cadr pair))))
                  (if (not (vl-catch-all-error-p hatch))
                    (setq objects (cons hatch objects)))
                  (setq hatch
                    (vl-catch-all-apply 'urb:add-user-hatch
                      (list piece "URB-RAMPA" 0.20 (+ axis-angle (/ pi 2.0))
                        nil 8 (cadr pair))))
                  (if (not (vl-catch-all-error-p hatch))
                    (setq objects (cons hatch objects))))))))))
    (setq s e gray (not gray)))
  (if (not (vl-catch-all-error-p treg)) (urb:safe-delete treg))
  (if (not (vl-catch-all-error-p breg)) (urb:safe-delete breg))
  (setq objects (reverse objects))
  ;; area util = superficie rectangular de rampa (entre los dos A81),
  ;; incluida la extension hasta el bordillo si la hay
  (setq area (* width (- 1.3 v0)))
  (setq block-name (strcat "URB_RAMPA_" (itoa (getvar "MILLISECS"))))
  (setq blocks (vla-get-Blocks doc))
  (setq block-definition
    (vla-Add blocks (vlax-3d-point '(0.0 0.0 0.0)) block-name))
  (setq copy-result
    (vl-catch-all-apply
      'vla-CopyObjects
      (list doc (urb:object-array-variant objects) block-definition)))
  (if (vl-catch-all-error-p copy-result)
    (progn
      (urb:safe-delete block-definition)
      (prompt (strcat "\nERROR al crear el bloque de la rampa: "
                      (vl-catch-all-error-message copy-result)))
      nil)
    (progn
      (urb:add-invisible-attribute block-definition base-pt "TIPO" "Tipo" tipo)
      (urb:add-invisible-attribute block-definition base-pt "ANCHO_RAMPA" "Ancho rampa m" (rtos width 2 2))
      (urb:add-invisible-attribute block-definition base-pt "FONDO_M" "Fondo m" (rtos depth 2 2))
      (urb:add-invisible-attribute block-definition base-pt "AREA_M2" "Area m2" (rtos area 2 2))
      (urb:add-invisible-attribute block-definition base-pt "TOPEROL_ML" "Toperol ml"
        (rtos (* 2.0 (- depth v0)) 2 2))
      (urb:add-invisible-attribute block-definition base-pt "BORDILLO_ML" "Bordillo ml"
        (rtos (+ (* 2.0 (- depth v0)) (+ width 0.6)) 2 2))
      (urb:add-invisible-attribute block-definition base-pt "A81_UND" "Legado A81 und" "0")
      (urb:add-invisible-attribute block-definition base-pt "A105_UND" "Remate A105 und" "2")
      (urb:add-invisible-attribute block-definition base-pt "SARDINEL_A86_ML" "Sardinel alto A86 ml"
        (rtos (+ width 0.6) 2 6))
      (urb:add-invisible-attribute block-definition base-pt "ETAPA" "Etapa" etapa)
      (urb:add-invisible-attribute block-definition base-pt "SUBETAPA" "Subetapa" subetapa)
      (setq insert-result
        (vl-catch-all-apply
          'vla-InsertBlock
          (list (urb:space) (vlax-3d-point '(0.0 0.0 0.0)) block-name 1.0 1.0 1.0 0.0)))
      (if (vl-catch-all-error-p insert-result)
        (progn
          (urb:safe-delete block-definition)
          (prompt (strcat "\nERROR al insertar el bloque de la rampa: "
                          (vl-catch-all-error-message insert-result)))
          nil)
        (progn
          (setq block-ref insert-result)
          (vla-put-Layer block-ref "URB-RAMPA")
          (setq block-ename (urb:as-ename block-ref))
          (if block-ename
            (urb:set-xdata-strings block-ename "URB_RAMPA_BLOCK"
              (list tipo etapa subetapa
                    (rtos width 2 8) (rtos depth 2 8) (rtos area 2 8))))
          (foreach obj objects (urb:safe-delete obj))
          block-ref))))
)

(defun urb:write-stage-dcl ()
  (urb:write-dialog-dcl
    "urbanismo_etapas"
    '*urb-stage-dcl-ok*
    (list
      "urbanismo_etapas : dialog { label = \"Cambiar etapa/subetapa\";"
      ": popup_list { label = \"Etapa\"; key = \"etapa\"; }"
      ": popup_list { label = \"Subetapa\"; key = \"subetapa\"; }"
      "ok_cancel; }"))
)

(defun urb:dialog-stage
  (current-etapa current-subetapa / filename dcl-id accepted subetapas result)
  (setq filename (urb:write-stage-dcl))
  (setq current-etapa (urb:safe-string current-etapa "1"))
  (setq current-subetapa (urb:safe-string current-subetapa current-etapa))
  (if (and filename
           (> (setq dcl-id (load_dialog filename)) 0)
           (new_dialog "urbanismo_etapas" dcl-id))
    (progn
      (urb:fill-popup
        "etapa" *urb-etapa-list*
        (urb:index-of current-etapa *urb-etapa-list*))
      (setq *urb-dialog-etapa*
        (nth (atoi (get_tile "etapa")) *urb-etapa-list*))
      (setq subetapas (urb:subetapas-for *urb-dialog-etapa*))
      (urb:fill-popup
        "subetapa" subetapas
        (urb:index-of current-subetapa subetapas))
      (action_tile "etapa" "(urb:dialog-update-subetapa)")
      (action_tile
        "accept"
        (strcat
          "(setq *urb-dialog-etapa-index* (atoi (get_tile \"etapa\"))"
          " *urb-dialog-subetapa-index* (atoi (get_tile \"subetapa\")))"
          "(done_dialog 1)"))
      (setq accepted (= 1 (start_dialog)))
      (unload_dialog dcl-id)
      (if accepted
        (progn
          (setq current-etapa
            (nth *urb-dialog-etapa-index* *urb-etapa-list*))
          (setq subetapas (urb:subetapas-for current-etapa))
          (setq current-subetapa
            (nth *urb-dialog-subetapa-index* subetapas))
          (setq result (list current-etapa current-subetapa)))))
  )
  result
)

(defun urb:apply-etapa-subetapa
  (ename etapa subetapa / obj data category app new-data before atts
   old-etapa old-subetapa has-etapa has-subetapa result restore-result)
  ;; Cambia SOLO etapa/subetapa de un elemento ya creado, sin reconstruir
  ;; geometria ni recalcular cantidades: la xdata del tipo correspondiente
  ;; (lo que leen las cantidades/Excel) + los atributos ETAPA/SUBETAPA si
  ;; el bloque los tiene (las redes mp: los llevan SOLO como atributos).
  ;; Devuelve el nombre del tipo reconocido, o nil si el objeto no es del
  ;; programa.
  (setq obj (urb:as-vla-object ename)
        before (entget ename '("*"))
        atts (if obj (urb:block-attribute-values obj) nil)
        old-etapa (cdr (assoc "ETAPA" atts))
        old-subetapa (cdr (assoc "SUBETAPA" atts))
        has-etapa (if (assoc "ETAPA" atts) T nil)
        has-subetapa (if (assoc "SUBETAPA" atts) T nil))
  (cond
    ((setq data (urb:get-xdata-strings ename "URB_ANDEN_BLOCK"))
      (setq app "URB_ANDEN_BLOCK"
            new-data (urb:replace-nth 3 subetapa (urb:replace-nth 2 etapa data))
            category "Andenes"))
    ((setq data (urb:get-xdata-strings ename "URB_VIA"))
      (setq app "URB_VIA"
            new-data (urb:replace-nth 3 subetapa (urb:replace-nth 2 etapa data))
            category "Vias"))
    ((setq data (urb:get-xdata-strings ename "URB_PREFAB_BLOCK"))
      (setq app "URB_PREFAB_BLOCK"
            new-data (urb:replace-nth 2 subetapa (urb:replace-nth 1 etapa data))
            category "Prefabricados"))
    ((setq data (urb:get-xdata-strings ename "URB_GREEN_BLOCK"))
      (setq app "URB_GREEN_BLOCK"
            new-data (urb:replace-nth 2 subetapa (urb:replace-nth 1 etapa data))
            category "Zonas verdes"))
    ((setq data (urb:get-xdata-strings ename "URB_RAMPA_BLOCK"))
      (setq app "URB_RAMPA_BLOCK"
            new-data (urb:replace-nth 2 subetapa (urb:replace-nth 1 etapa data))
            category "Rampas"))
    ;; senderos/ciclorrutas/bioswales (v4.49): etapa y subetapa viven en
    ;; la xdata URB_SENDERO (posiciones 1 y 2)
    ((setq data (urb:get-xdata-strings ename "URB_SENDERO"))
      (setq app "URB_SENDERO"
            new-data (urb:replace-nth 2 subetapa (urb:replace-nth 1 etapa data))
            category "Senderos"))
    ((and obj (assoc "ETAPA" (urb:block-attribute-values obj)))
      (setq category "Redes / otros bloques")))
  (if category
    (progn
      (setq result
        (vl-catch-all-apply
          '(lambda ()
            (if app
              (if (not (and (urb:set-xdata-strings ename app new-data)
                            (equal new-data (urb:get-xdata-strings ename app))))
                (exit)))
            (if has-etapa
              (progn
                (urb:set-block-attribute obj "ETAPA" etapa)
                (if (/= etapa
                       (urb:safe-string
                         (cdr (assoc "ETAPA" (urb:block-attribute-values obj))) ""))
                  (exit))))
            (if has-subetapa
              (progn
                (urb:set-block-attribute obj "SUBETAPA" subetapa)
                (if (/= subetapa
                       (urb:safe-string
                         (cdr (assoc "SUBETAPA" (urb:block-attribute-values obj))) ""))
                  (exit))))
            ;; Un bloque de red reconocido por atributos debe tener ambos.
            (if (and (null app) (not (and has-etapa has-subetapa))) (exit))
            T)))
      (if (vl-catch-all-error-p result)
        (progn
          (setq restore-result
            (vl-catch-all-apply
              '(lambda ()
                (if before (entmod before))
                (if has-etapa
                  (urb:set-block-attribute obj "ETAPA" old-etapa))
                (if has-subetapa
                  (urb:set-block-attribute obj "SUBETAPA" old-subetapa))
                (entupd ename))))
          (list "__ERROR__"
            (if (vl-catch-all-error-p restore-result)
              "fallo y no se pudo restaurar completamente"
              "fallo de verificacion; se restauraron los datos anteriores")))
        category))
    nil)
)

(defun urb:batch-stage-command
  (/ data etapa subetapa ss index ename category counts entry total skipped doc undo-open choice failed *error*)
  (setq doc (urb:doc) failed 0)
  (defun *error* (msg)
    (if undo-open (vl-catch-all-apply 'vla-EndUndoMark (list doc)))
    (if msg (prompt (strcat "\nCambio de etapa interrumpido: " msg
      "\nPuede deshacer el lote completo con UNDO."))) (princ))
  ;; Cambio rapido de etapa/subetapa en LOTE: primero se seleccionan los
  ;; elementos (mezcla de andenes, vias, redes, prefabricados, zonas
  ;; verdes) y DESPUES sale el dialogo con los desplegables de etapa y
  ;; subetapa (orden pedido por el usuario). Aplica sin redibujar nada --
  ;; editar via el comando EDITAR reconstruye la geometria completa
  ;; (minutos por anden); esto tarda segundos porque solo toca metadatos.
  (prompt
    "\nSeleccione los elementos a cambiar (andenes, vias, redes, prefabricados, zonas verdes): ")
  (setq ss (ssget))
  (if (null ss)
    (prompt "\nNo se selecciono ningun objeto.")
    (progn
      (setq data (urb:dialog-stage "1" "1"))
      (if (null data)
        (prompt "\nComando cancelado.")
        (progn
          (setq etapa (nth 0 data) subetapa (nth 1 data))
          (prompt (strcat "\nVista previa: " (itoa (sslength ss))
            " objetos seleccionados -> etapa " etapa " / subetapa " subetapa
            ". Se modifican metadatos; no se recalcula geometria."))
          (initget "Aplicar Cancelar")
          (setq choice (getkword "\nContinuar [Aplicar/Cancelar] <Cancelar>: "))
          (if (not (equal choice "Aplicar")) (progn (prompt "\nSin cambios.") (exit)))
          (vla-StartUndoMark doc)
          (setq undo-open T counts nil total 0 index 0)
          (repeat (sslength ss)
            (setq ename (ssname ss index))
            (setq category
              (vl-catch-all-apply
                'urb:apply-etapa-subetapa (list ename etapa subetapa)))
            (if (vl-catch-all-error-p category)
              (progn (setq failed (1+ failed))
                (prompt (strcat "\nFallo en " (urb:q-handle ename) ": "
                  (vl-catch-all-error-message category)))
                (setq category nil)))
            (if (and (listp category) (= (car category) "__ERROR__"))
              (progn
                (setq failed (1+ failed))
                (prompt (strcat "\nFallo en " (urb:q-handle ename) ": "
                  (cadr category)))
                (setq category nil)))
            (if category
              (progn
                (setq total (1+ total))
                (setq entry (assoc category counts))
                (setq counts
                  (if entry
                    (subst (cons category (1+ (cdr entry))) entry counts)
                    (cons (cons category 1) counts)))))
            (setq index (1+ index)))
          (vla-EndUndoMark doc)
          (setq undo-open nil skipped (- (sslength ss) total failed))
          (if (> failed 0) (prompt (strcat "\nObjetos con error: " (itoa failed)
            ". Revise el dibujo; UNDO deshace todo el lote.")))
          (prompt
            (strcat "\nEtapa " etapa " / Subetapa " subetapa
                    " aplicada a " (itoa total) " elemento(s)."))
          (foreach entry (reverse counts)
            (prompt (strcat "\n  " (car entry) ": " (itoa (cdr entry)))))
          (if (> skipped 0)
            (prompt
              (strcat "\n  Ignorados (no son elementos del programa): "
                      (itoa skipped))))))))
  (princ)
)

(defun urb:write-main-menu-dcl (/ filename)
  (setq filename (urb:temp-file "urbanismo_menu" ".dcl"))
  (if
    (urb:write-lines filename
      '("urb_main : dialog { label = \"Urbanismo\";"
        ": boxed_column { label = \"Seleccione una opcion\";"
        ": button { label = \"Crear\"; key = \"create\"; height = 2; width = 32; }"
        ": button { label = \"Editar\"; key = \"edit\"; height = 2; width = 32; }"
        ": button { label = \"Cambiar etapa/subetapa (lote)\"; key = \"stages\"; height = 2; width = 32; }"
        ": button { label = \"Cantidades\"; key = \"quantities\"; height = 2; width = 32; }"
        ": button { label = \"Configuracion\"; key = \"config\"; height = 2; width = 32; } }"
        "cancel_button; }"
        "urb_create : dialog { label = \"Crear elemento\";"
        ": boxed_column { label = \"Tipo de elemento\";"
        ": button { label = \"Via\"; key = \"road\"; height = 2; width = 32; }"
        ": button { label = \"Anden\"; key = \"sidewalk\"; height = 2; width = 32; }"
        ": button { label = \"Rampas y paso peatonal\"; key = \"ramp\"; height = 2; width = 32; }"
        ": button { label = \"Zona verde\"; key = \"green\"; height = 2; width = 32; }"
        ": button { label = \"Prefabricado\"; key = \"precast\"; height = 2; width = 32; }"
        ": button { label = \"Red\"; key = \"network\"; height = 2; width = 32; } }"
        ": button { label = \"Volver\"; key = \"back\"; is_cancel = true; width = 14; } }"
        "urb_network_create : dialog { label = \"Crear red\";"
        ": row { : boxed_column { label = \"Tramos\";"
        ": button { label = \"Sanitario\"; key = \"segment_sanitary\"; height = 2; width = 38; }"
        ": button { label = \"Pluvial\"; key = \"segment_storm\"; height = 2; width = 38; }"
        ": button { label = \"Acueducto\"; key = \"segment_water\"; height = 2; width = 38; }"
        ": button { label = \"Media tension\"; key = \"segment_mt\"; height = 2; width = 38; }"
        ": button { label = \"Baja tension\"; key = \"segment_bt\"; height = 2; width = 38; }"
        ": button { label = \"Alumbrado publico\"; key = \"segment_ap\"; height = 2; width = 38; } }"
        ": boxed_column { label = \"Elementos puntuales\";"
        ": button { label = \"Pozo sanitario\"; key = \"sanitary_manhole\"; height = 2; width = 38; }"
        ": button { label = \"Pozo pluvial\"; key = \"storm_manhole\"; height = 2; width = 38; }"
        ": button { label = \"Sumidero\"; key = \"inlet\"; height = 2; width = 38; }"
        ": button { label = \"Camara electrica\"; key = \"electrical_chamber\"; height = 2; width = 38; }"
        ": button { label = \"Accesorio de acueducto\"; key = \"water_accessory\"; height = 2; width = 38; }"
        ": button { label = \"Luminaria\"; key = \"luminaire\"; height = 2; width = 38; } } }"
        ": button { label = \"Volver\"; key = \"back\"; is_cancel = true; width = 14; } }"
        "urb_config : dialog { label = \"Configuracion de urbanismo\";"
        ": boxed_column { label = \"Bibliotecas\";"
        ": button { label = \"Etapas y subetapas\"; key = \"etapas_config\"; height = 2; width = 40; }"
        ": button { label = \"Diametros de tuberia\"; key = \"diametros_config\"; height = 2; width = 40; } }"
        ": boxed_column { label = \"Movimiento de tierras\";"
        ": button { label = \"Movimiento de tierras (perfiles, sobreanchos, referencia)\"; key = \"earthworks_config\"; height = 2; width = 40; } }"
        ": boxed_column { label = \"Apariencia de redes\";"
        ": button { label = \"Espesor de linea y tamano de datos de tramos\"; key = \"tramo_appearance\"; height = 2; width = 40; } }"
        ": boxed_column { label = \"Capas y limpieza\";"
        ": button { label = \"Organizar capas del plugin (filtro URBANISMO)\"; key = \"layers_organize\"; height = 2; width = 40; }"
        ": button { label = \"Depurar dibujo (PURGE; no oculta objetos)\"; key = \"purge_dwg\"; height = 2; width = 40; }"
        ": button { label = \"Modo fluido: ocultar/restaurar guia y toperol\"; key = \"light_dwg\"; height = 2; width = 40; }"
        ": button { label = \"Version instalada y sesion\"; key = \"version_info\"; height = 2; width = 40; } }"
        ": button { label = \"Volver\"; key = \"back\"; is_cancel = true; width = 14; } }"
        "urb_earthworks : dialog { label = \"Movimiento de tierras\";"
        ": boxed_column { label = \"Vias\";"
        ": row { : text { label = \"Sobreancho izquierdo de via (m)\"; width = 38; } : edit_box { key = \"road_left\"; edit_width = 12; } }"
        ": row { : text { label = \"Sobreancho derecho de via (m)\"; width = 38; } : edit_box { key = \"road_right\"; edit_width = 12; } }"
        ": row { : text { label = \"Bombeo de la calzada (%)\"; width = 38; } : edit_box { key = \"road_cross\"; edit_width = 12; } }"
        ": row { : text { label = \"Profundidad maxima de control (m; 0 desactiva)\"; width = 38; } : edit_box { key = \"road_max_depth\"; edit_width = 12; } }"
        ": text { label = \"Predeterminado 20 m: admite cortes locales de 12-15 m y aun detecta rasantes equivocadas.\"; } }"
        ": boxed_column { label = \"Andenes -- perfil estratigrafico (editable)\";"
        ": row { : text { label = \"Adoquin / loseta (m)\"; width = 38; } : edit_box { key = \"ad_adoquin\"; edit_width = 12; } }"
        ": row { : text { label = \"Arena de nivelacion (m)\"; width = 38; } : edit_box { key = \"ad_arena\"; edit_width = 12; } }"
        ": row { : text { label = \"Subbase granular SBG-C (m)\"; width = 38; } : edit_box { key = \"ad_sbg\"; edit_width = 12; } }"
        ": text { label = \"Excavacion del anden = area x (suma de las 3 capas). Geotextil 15% traslapo fijo.\"; } }"
        ": boxed_column { label = \"Sobreexcavacion y esponjamiento (vias, andenes, senderos y zonas verdes)\";"
        ": row { : text { label = \"Material no portante bajo el terreno (m)\"; width = 38; } : edit_box { key = \"over_depth\"; edit_width = 12; } }"
        ": row { : text { label = \"Expansion del material de corte (%)\"; width = 38; } : edit_box { key = \"cut_exp\"; edit_width = 12; } }"
        ": row { : text { label = \"Sobreconsumo del relleno compactado (%)\"; width = 38; } : edit_box { key = \"fill_shrink\"; edit_width = 12; } }"
        ": text { label = \"Si el corte es menor que esa altura, igual se excava hasta el suelo portante y el relleno crece.\"; } }"
        ": boxed_column { label = \"Redes\";"
        ": popup_list { label = \"Relleno de tramos de red hasta\"; key = \"relleno_ref\"; }"
        ": row { : text { label = \"Triturado sobre la clave (m)\"; width = 38; } : edit_box { key = \"trit_clave\"; edit_width = 12; } }"
        ": button { label = \"Normas de zanja: CODENSA y anchos PVC (ver tabla)...\"; key = \"normas\"; height = 2; width = 46; } }"
        ": boxed_column { label = \"Perfiles estratigraficos\";"
        ": button { label = \"Perfiles de vias (capas de pavimento)...\"; key = \"perfiles\"; height = 2; width = 46; }"
        ": button { label = \"Estructura de senderos (capas y espesores)...\"; key = \"senderos\"; height = 2; width = 46; } }"
        ": text { label = \"OK guarda los valores; los botones abren su propia ventana y vuelven aqui.\"; }"
        "ok_cancel; }"
        "urb_normas : dialog { label = \"Normas de excavacion de redes (solo lectura)\";"
        ": list_box { key = \"tabla\"; width = 92; height = 28; }"
        "ok_only; }"
        "urb_etapas : dialog { label = \"Etapas y subetapas\";"
        ": toggle { key = \"activo\"; label = \"Habilitadas (etapa/subetapa activas en los dialogos de creacion)\"; }"
        ": boxed_column { label = \"Catalogo\";"
        ": popup_list { key = \"etapa\"; label = \"Etapa\"; width = 22; }"
        ": edit_box { key = \"subs\"; label = \"Subetapas (separadas por coma)\"; edit_width = 30; }"
        ": row {"
        ": button { key = \"guardar\"; label = \"Guardar subetapas\"; width = 20; }"
        ": button { key = \"quitar\"; label = \"Quitar etapa\"; width = 16; } } }"
        ": boxed_column { label = \"Nueva etapa\";"
        ": edit_box { key = \"nueva\"; label = \"Nombre\"; edit_width = 12; }"
        ": edit_box { key = \"nuevasubs\"; label = \"Subetapas (separadas por coma)\"; edit_width = 30; }"
        ": button { key = \"agregar\"; label = \"Agregar etapa\"; width = 20; } }"
        ": row {"
        ": button { key = \"restaurar\"; label = \"Restaurar original\"; width = 20; }"
        "ok_only; } }"
        "urb_diametros : dialog { label = \"Diametros de tuberia\";"
        ": popup_list { key = \"red\"; label = \"Red\"; width = 22; }"
        ": boxed_column { label = \"Diametros disponibles (pulgadas)\";"
        ": list_box { key = \"diam\"; width = 20; height = 12; }"
        ": button { key = \"quitar\"; label = \"Quitar el seleccionado\"; width = 24; } }"
        ": boxed_column { label = \"Agregar\";"
        ": edit_box { key = \"nuevo\"; label = \"Diametro en pulgadas\"; edit_width = 8; }"
        ": button { key = \"agregar\"; label = \"Agregar diametro\"; width = 22; } }"
        ": text { key = \"info\"; label = \"\"; width = 64; }"
        ": row {"
        ": button { key = \"restaurar\"; label = \"Restaurar original\"; width = 20; }"
        "ok_only; } }"
        "urb_quantities : dialog { label = \"Cantidades\";"
        ": boxed_column { label = \"Seleccione una opcion\";"
        ": button { label = \"Diagnostico de integridad\"; key = \"diagnostic\"; height = 2; width = 44; }"
        ": button { label = \"Consultar cantidades de un elemento\"; key = \"trace\"; height = 2; width = 44; }"
        ": button { label = \"Cuadro en dibujo: andenes y prefabricados\"; key = \"table\"; height = 2; width = 44; }"
        ": button { label = \"Memoria de via\"; key = \"road\"; height = 2; width = 40; }"
        ": button { label = \"Tabla de verificacion de via (desplegar)\"; key = \"road_audit\"; height = 2; width = 44; }"
        ": button { label = \"Incluir o excluir seleccion\"; key = \"scope\"; height = 2; width = 44; }"
        ": button { label = \"Crear Excel independiente (tabla general)\"; key = \"excel\"; height = 2; width = 44; }"
        ": button { label = \"Vincular o cambiar Excel maestro\"; key = \"link_excel\"; height = 2; width = 44; }"
        ": button { label = \"Actualizar Excel vinculado\"; key = \"update_excel\"; height = 2; width = 44; }"
        ": button { label = \"Eliminar vinculo con Excel\"; key = \"unlink_excel\"; height = 2; width = 44; }"
        ": button { label = \"Exportar detalle tecnico de redes (CSV)\"; key = \"network\"; height = 2; width = 44; }"
        ": button { label = \"Cuadros de red en el dibujo (accesorios/tramos/pozos)\"; key = \"cuadros\"; height = 2; width = 44; }"
        ": button { label = \"Perfil esquematico de mov. de tierras de via\"; key = \"via_perfil\"; height = 2; width = 44; } }"
        ": button { label = \"Volver\"; key = \"back\"; is_cancel = true; width = 14; } }"))
    filename))

(defun urb:simple-menu-dialog
  (dialog-name buttons / filename load-result dcl dialog-result action button)
  (setq filename (urb:write-main-menu-dcl))
  (if (not filename)
    (alert "No fue posible crear el archivo temporal del menu URBANISMO.")
    (progn
      (setq load-result
        (vl-catch-all-apply 'load_dialog (list filename)))
      (if (or (vl-catch-all-error-p load-result) (<= load-result 0))
        (alert
          (strcat "No fue posible cargar el menu URBANISMO."
            (if (vl-catch-all-error-p load-result)
              (strcat "\n" (vl-catch-all-error-message load-result)) "")))
        (progn
          (setq dcl load-result
                dialog-result
                  (vl-catch-all-apply 'new_dialog
                    (list dialog-name dcl)))
          (if (or (vl-catch-all-error-p dialog-result)
                  (not dialog-result))
            (alert
              (strcat "No fue posible abrir el cuadro " dialog-name "."))
            (progn
              (foreach button buttons
                (action_tile (car button)
                  (strcat "(setq action \"" (cadr button)
                    "\")(done_dialog 1)")))
              (vl-catch-all-apply 'action_tile
                (list "back" "(setq action \"back\")(done_dialog 0)"))
              (vl-catch-all-apply 'action_tile
                (list "cancel" "(setq action nil)(done_dialog 0)"))
              (start_dialog)))
          (unload_dialog dcl)))))
  action)

(defun urb:create-network-segment-direct (action)
  (if (urb:confirm-meter-units)
    (cond
      ((= action "segment_sanitary")
        (mp:insert-tramo-forced "Aresidual"))
      ((= action "segment_storm")
        (mp:insert-tramo-forced "Alluvias"))
      ((= action "segment_water")
        (mp:insert-tramo-forced "Acueducto"))
      ((= action "segment_mt")
        (mp:insert-electrical-tramo
          "TRAMO_E_MT"
          "\nExtremo inicial tramo MT: "
          "\nExtremo final tramo MT: "
          'mp:dialog-tramo-mt "MT"))
      ((= action "segment_bt")
        (mp:insert-electrical-tramo
          "TRAMO_E_BT_AP"
          "\nExtremo inicial tramo BT: "
          "\nExtremo final tramo BT: "
          'mp:dialog-tramo-bt "BT"))
      ((= action "segment_ap")
        (mp:insert-electrical-tramo
          "TRAMO_E_BT_AP"
          "\nExtremo inicial tramo alumbrado: "
          "\nExtremo final tramo alumbrado: "
          'mp:dialog-tramo-bt "AP")))
    (prompt
      "\nCreacion de tramo cancelada: confirme primero las unidades del dibujo."))
  (princ)
)

(defun urb:network-create-menu (/ action)
  (setq action
    (urb:simple-menu-dialog "urb_network_create"
      '(("segment_sanitary" "segment_sanitary")
        ("segment_storm" "segment_storm")
        ("segment_water" "segment_water")
        ("segment_mt" "segment_mt")
        ("segment_bt" "segment_bt")
        ("segment_ap" "segment_ap")
        ("sanitary_manhole" "sanitary_manhole")
        ("storm_manhole" "storm_manhole")
        ("inlet" "inlet")
        ("electrical_chamber" "electrical_chamber")
        ("water_accessory" "water_accessory")
        ("luminaire" "luminaire"))))
  (cond
    ((or (null action) (= action "back")) "back")
    ((member action
       '("segment_sanitary" "segment_storm" "segment_water"
         "segment_mt" "segment_bt" "segment_ap"))
      (urb:create-network-segment-direct action))
    ((= action "sanitary_manhole")
      (if (urb:confirm-meter-units) (urb:create-sanitary-manhole)))
    ((= action "storm_manhole")
      (if (urb:confirm-meter-units) (urb:create-storm-manhole)))
    ((= action "inlet")
      (if (urb:confirm-meter-units) (urb:create-inlet)))
    ((= action "electrical_chamber")
      (if (urb:confirm-meter-units) (urb:create-electrical-chamber)))
    ((= action "water_accessory")
      (if (urb:confirm-meter-units) (urb:create-water-accessory)))
    ((= action "luminaire")
      (if (urb:confirm-meter-units) (urb:create-luminaire))))
  (if (or (null action) (= action "back")) "back" nil))

(defun urb:create-menu (/ action done result)
  (while (not done)
    (setq action
      (urb:simple-menu-dialog "urb_create"
        '(("road" "road") ("sidewalk" "sidewalk") ("ramp" "ramp")
          ("green" "green")
          ("precast" "precast") ("network" "network"))))
    (cond
      ((or (null action) (= action "back"))
        (setq done T result "back"))
      ((= action "road") (urb:create-road) (setq done T))
      ((= action "sidewalk") (urb:create-sidewalk-command) (setq done T))
      ((= action "ramp") (urb:create-ramp-command) (setq done T))
      ((= action "green") (urb:create-green-zone-command) (setq done T))
      ((= action "precast") (urb:create-precast-command) (setq done T))
      ((= action "network")
        (if (not
              (urb:string-equal-p
                (urb:network-create-menu) "back"))
          (setq done T)))))
  result)

;; ============================================================
;; EXPORTACION CONSOLIDADA A EXCEL (4.10.0)
;; Un registro normalizado tiene la forma:
;; (capitulo sistema elemento especificacion etapa subetapa unidad
;;  cantidad handle estado vinculo-id vinculo-nombre)
;; ============================================================

(defun urb:q-safe-nth (index values default)
  (if (and (listp values) (> (length values) index))
    (nth index values)
    default)
)

(defun urb:q-scope-included-p (ename / data value)
  (setq data
    (if (urb:valid-ename-p ename)
      (urb:get-xdata-strings ename "URB_Q_SCOPE") nil)
    value (strcase (urb:safe-string (if data (car data) "SI") "SI")))
  (not (member value '("NO" "EXCLUIR" "0")))
)

(defun urb:q-modelspace-p (ename / data layout space)
  ;; La extraccion contractual se limita a ModelSpace. ssget "_X" tambien
  ;; encuentra copias en layouts; sin este filtro esas copias se sumaban.
  (setq data (if (urb:valid-ename-p ename) (entget ename) nil)
        layout (urb:safe-string (cdr (assoc 410 data)) "")
        space (cdr (assoc 67 data)))
  (and
    (or (urb:string-equal-p layout "Model")
        (and (= layout "") (or (null space) (= space 0))))
    (urb:q-scope-included-p ename))
)

(defun urb:q-unscaled-reference-p (ename / object xscale yscale zscale)
  (setq object (urb:as-vla-object ename))
  (if (and object
           (urb:string-equal-p
             (urb:safe-string
               (vl-catch-all-apply 'vla-get-ObjectName (list object)) "")
             "AcDbBlockReference"))
    (progn
      (setq xscale
        (vl-catch-all-apply 'vla-get-XScaleFactor (list object))
        yscale (vl-catch-all-apply 'vla-get-YScaleFactor (list object))
        zscale (vl-catch-all-apply 'vla-get-ZScaleFactor (list object)))
      (and (numberp xscale) (numberp yscale) (numberp zscale)
           (equal (abs xscale) 1.0 1e-6)
           (equal (abs yscale) 1.0 1e-6)
           (equal (abs zscale) 1.0 1e-6)))
    T)
)

(defun urb:q-approved-status-p (status / normalized)
  (setq normalized (strcase (urb:safe-string status "")))
  (if (member normalized '("OK" "CALCULADO" "APROBADO")) T nil)
)

(defun urb:q-basic-status (stage substage valid-geometry)
  (if (and (/= (vl-string-trim " " (urb:safe-string stage "")) "")
           (/= (vl-string-trim " " (urb:safe-string substage "")) "")
           valid-geometry)
    "OK"
    "REVISAR")
)

(defun urb:q-number (value / parsed)
  (cond
    ((numberp value) (float value))
    ((= (type value) 'STR)
      (setq parsed (urb:parse-real value))
      (if parsed (float parsed) 0.0))
    (T 0.0))
)

(defun urb:q-handle (value / ename)
  ;; El handle ya esta en DXF: evita una conversion y una llamada COM por fila.
  (if (setq ename (urb:as-ename value))
    (urb:safe-string (cdr (assoc 5 (entget ename))) "")
    ""))

(defun urb:q-record
  (chapter system element specification stage substage unit quantity
   handle status link-id link-name)
  (list
    (urb:safe-string chapter "")
    (urb:safe-string system "")
    (urb:safe-string element "")
    (urb:safe-string specification "")
    (urb:safe-string stage "")
    (urb:safe-string substage "")
    (urb:safe-string unit "")
    (urb:q-number quantity)
    (urb:safe-string handle "")
    (if (< (urb:q-number quantity) -1e-9) "REVISAR" (urb:safe-string status ""))
    (urb:safe-string link-id "")
    (urb:safe-string link-name ""))
)

(defun urb:q-record-key (record)
  (strcat
    (nth 0 record) "\t" (nth 1 record) "\t" (nth 2 record) "\t"
    (nth 3 record) "\t" (nth 4 record) "\t" (nth 5 record) "\t"
    (nth 6 record) "\t" (nth 9 record))
)

(defun urb:q-aggregate (records / indexed index record item key current result first-index)
  ;; Ordenar por clave e indice conserva orden de suma y primera aparicion.
  ;; El indice unico evita que vl-sort descarte registros iguales.
  (setq index 0)
  (foreach record records
    (setq indexed (cons (list (urb:q-record-key record) index record) indexed)
          index (1+ index)))
  (setq indexed (vl-sort indexed
    '(lambda (a b) (if (= (car a) (car b)) (< (cadr a) (cadr b))
                    (< (car a) (car b))))))
  (foreach item indexed
    (setq record (caddr item))
    (if (and current (= key (car item)))
      (setq current (list key (nth 1 current) (nth 2 current)
        (nth 3 current) (nth 4 current) (nth 5 current) (nth 6 current)
        (nth 7 current) (+ (nth 8 current) (nth 7 record))
        (1+ (nth 9 current)) (nth 10 current)))
      (progn
        (if current (setq result (cons (cons first-index current) result)))
        (setq key (car item) first-index (cadr item)
          current (list key (nth 0 record) (nth 1 record) (nth 2 record)
            (nth 3 record) (nth 4 record) (nth 5 record) (nth 6 record)
            (nth 7 record) 1 (nth 9 record))))))
  (if current (setq result (cons (cons first-index current) result)))
  (mapcar 'cdr (vl-sort result '(lambda (a b) (< (car a) (car b))))))

(defun urb:q-control-row (severity category handle element finding action)
  (list severity category handle element finding action)
)

(setq *urb-q-only-ename* nil)

(defun urb:q-candidate-set (filter / ss)
  ;; CONSULTAR usa solo el bloque seleccionado; el diagnostico general
  ;; conserva los filtros globales. Evita recorrer miles de entidades cinco
  ;; veces para localizar un unico handle.
  (if (and *urb-q-only-ename* (entget *urb-q-only-ename*))
    (progn
      (setq ss (ssadd))
      (ssadd *urb-q-only-ename* ss))
    (ssget "_X" filter)))

(defun urb:q-collect-andenes
  (/ ss index ename data mov handle material stage substage area perimeter
   format guide toperol surface grade calculate smooth-area smooth-units
   guide-ml toperol-ml adoquin-area adoquin-units cut fill valid total
   coverage via-id via-name status quantity-status finish-status finish-area
   tactile-p records details controls layer layer-type
   thickness overlap quantity unit specification)
  (setq ss (urb:q-candidate-set '((-3 ("URB_ANDEN_BLOCK")))))
  (if ss
    (progn
      (setq index 0)
      (repeat (sslength ss)
        (setq ename (ssname ss index))
        (setq data (urb:get-xdata-strings ename "URB_ANDEN_BLOCK"))
        (if (and (urb:q-modelspace-p ename)
                 data (urb:string-equal-p (car data) "ANDEN"))
          (progn
            (setq mov (urb:get-xdata-strings ename "URB_ANDEN_MOV"))
            (if (not (and mov (urb:string-equal-p (car mov) "ANDEN_MOV")))
              (setq mov nil))
            (setq handle (urb:q-handle ename)
                  material (strcase (urb:safe-string (urb:q-safe-nth 1 data "") ""))
                  stage (urb:safe-string (urb:q-safe-nth 2 data "") "")
                  substage (urb:safe-string (urb:q-safe-nth 3 data "") "")
                  area (urb:q-number (urb:q-safe-nth 4 data "0"))
                  perimeter (urb:q-number (urb:q-safe-nth 5 data "0"))
                  guide (urb:safe-string (urb:q-safe-nth 7 data "No") "No")
                  toperol (urb:safe-string (urb:q-safe-nth 8 data "No") "No")
                  format (urb:safe-string (urb:q-safe-nth 9 data "") "")
                  calculate (urb:safe-string (urb:q-safe-nth 10 data "No") "No")
                  surface (urb:safe-string (urb:q-safe-nth 11 data "") "")
                  grade (urb:safe-string (urb:q-safe-nth 12 data "") "")
                  smooth-area (urb:q-number (urb:q-safe-nth 13 data "0"))
                  smooth-units (urb:q-number (urb:q-safe-nth 14 data "0"))
                  guide-ml (urb:q-number (urb:q-safe-nth 15 data "0"))
                  toperol-ml (urb:q-number (urb:q-safe-nth 16 data "0"))
                  adoquin-area (urb:q-number (urb:q-safe-nth 17 data "0"))
                  adoquin-units (urb:q-number (urb:q-safe-nth 18 data "0"))
                  cut (urb:q-number (urb:q-safe-nth 2 mov "0"))
                  fill (urb:q-number (urb:q-safe-nth 3 mov "0"))
                  valid (fix (urb:q-number (urb:q-safe-nth 4 mov "0")))
                  total (fix (urb:q-number (urb:q-safe-nth 6 mov "0")))
                  coverage (urb:q-number (urb:q-safe-nth 7 mov "0"))
                  via-id (urb:safe-string (urb:q-safe-nth 8 mov "") "")
                  via-name (urb:safe-string (urb:q-safe-nth 9 mov "") ""))
            (setq quantity-status
              (urb:q-basic-status stage substage
                (and (> area 1e-9)
                     (member material '("LOSETA" "ADOQUIN"))
                     (urb:q-unscaled-reference-p ename))))
            (setq tactile-p
              (or (urb:yes-p guide) (urb:yes-p toperol))
                  finish-area
                    (if (= material "ADOQUIN")
                      (cond
                        ((> adoquin-area 1e-9) adoquin-area)
                        ((not tactile-p) area)
                        (T 0.0))
                      area)
                  finish-status
                    (if (and (= material "ADOQUIN") tactile-p
                             (<= adoquin-area 1e-9))
                      "REVISAR"
                      quantity-status))
            (setq status
              (cond
                (mov "CALCULADO")
                ((urb:yes-p calculate) "PENDIENTE")
                (T "NO SOLICITADO")))
            (setq details
              (cons
                (list handle material stage substage area perimeter format
                  guide toperol surface grade smooth-area smooth-units guide-ml
                  toperol-ml adoquin-area adoquin-units cut fill coverage
                  via-id via-name status)
                details))
            (setq specification
              (if (= material "LOSETA") format material))
            (setq records
              (cons
                (urb:q-record "ANDENES" "Acabados"
                  (if (= material "ADOQUIN")
                    "Suministro e instalacion de adoquin de arcilla color natural 20x10x6 cm"
                    "Suministro e instalacion de loseta prefabricada")
                  specification stage substage "M2" finish-area handle finish-status
                  via-id via-name)
                records))
            (setq records
              (cons
                (urb:q-record "ANDENES" "Descapote y nivelacion subrasante"
                  "Compactacion de subrasante (Incluye nivelacion)"
                  "Area modelada del anden" stage substage "M2" area
                  handle quantity-status via-id via-name)
                records))
            (setq records
              (cons
                (urb:q-record "ANDENES" "Descapote y nivelacion subrasante"
                  "Descapote mecanico de material vegetal (Incluye cargue y retiro externo)"
                  "Area modelada del anden" stage substage "M2" area
                  handle quantity-status via-id via-name)
                records))
            (if (> perimeter 1e-9)
              (setq records
                (cons
                    (urb:q-record "ANDENES" "Geometria" "Perimetro modelado"
                    material stage substage "ML" perimeter handle quantity-status
                    via-id via-name)
                  records)))
            (if (> smooth-units 1e-9)
              (setq records
                (cons
                   (urb:q-record "ANDENES" "Acabado" "Loseta lisa"
                    format stage substage "UND" smooth-units handle quantity-status
                    via-id via-name)
                  records)))
            (if (> guide-ml 1e-9)
              (setq records
                (cons
                   (urb:q-record "ANDENES" "Acabados"
                    "Cenefa lineal en loseta prefabricada guia color natural A-56 (0,40x0,40) m"
                    format stage substage "ML" guide-ml handle quantity-status
                    via-id via-name)
                  records)))
            (if (> toperol-ml 1e-9)
              (setq records
                (cons
                   (urb:q-record "ANDENES" "Accesibilidad" "Loseta toperol"
                    format stage substage "ML" toperol-ml handle quantity-status
                    via-id via-name)
                  records)))
            (if (and (= material "LOSETA") (> adoquin-units 1e-9))
              (setq records
                (cons
                  (urb:q-record "ANDENES" "Acabado"
                   "Adoquin blanco 20 x 10 cm" "20 x 10 cm"
                    stage substage "UND" adoquin-units handle quantity-status
                    via-id via-name)
                  records)))
            (foreach layer (cdr *urb-anden-structure*)
              (setq layer-type (nth 1 layer)
                    thickness (atof (nth 2 layer))
                    overlap (atof (nth 3 layer)))
              (if (urb:string-equal-p layer-type "Volumen")
                (setq quantity (* area thickness)
                      unit "M3"
                      specification
                        (strcat (rtos (* 100.0 thickness) 2 0) " cm"))
                (setq quantity (* area (+ 1.0 (/ overlap 100.0)))
                      unit "M2"
                      specification
                        (strcat "Traslapo " (rtos overlap 2 1) "%")))
              (setq records
                (cons
                  (urb:q-record "ANDENES" "Estructura" (car layer)
                    specification stage substage unit quantity handle quantity-status
                    via-id via-name)
                  records)))
            (if mov
              (progn
                (setq records
                  (cons
                    (urb:q-record "ANDENES" "Movimiento de tierras"
                      "Excavacion mecanica en material comun (Incluye cargue, transporte y disposicion)"
                      (urb:q-safe-nth 1 mov "")
                      stage substage "M3" cut handle
                      (if (= quantity-status "OK") "CALCULADO" "REVISAR")
                      via-id via-name)
                    records))
                (setq records
                  (cons
                    (urb:q-record "ANDENES" "Movimiento de tierras"
                      "Suministro y colocacion de recebo B-200"
                      (urb:q-safe-nth 1 mov "")
                      stage substage "M3" fill handle
                      (if (= quantity-status "OK") "CALCULADO" "REVISAR")
                      via-id via-name)
                    records)))
              (if (urb:yes-p calculate)
                (setq controls
                  (cons
                    (urb:q-control-row "ALTA" "ANDEN" handle material
                      "Movimiento de tierras pendiente."
                      "Editar el anden y completar superficie y rasante.")
                    controls))))
            (if (= quantity-status "REVISAR")
              (setq controls
                (cons
                  (urb:q-control-row "ALTA" "ANDEN" handle material
                    "El anden no tiene etapa, subetapa, geometria valida o fue escalado fuera de EDITAR."
                    "Completar o reconstruir mediante EDITAR; sus cantidades no se sumaran.")
                  controls)))
            (if (and (= material "ADOQUIN") tactile-p
                     (<= adoquin-area 1e-9))
              (setq controls
                (cons
                  (urb:q-control-row "ALTA" "ANDEN" handle material
                    "El anden tiene franjas tactiles pero no conserva el area neta de adoquin."
                    "Abrirlo con EDITAR y aceptar para recalcular las franjas con la version 4.15.1.")
                  controls)))
            (if (and (urb:string-equal-p grade "Via creada") (= via-id ""))
              (setq controls
                (cons
                  (urb:q-control-row "MEDIA" "VINCULO VIA-ANDEN" handle material
                    "El anden no conserva el ID de la via controladora."
                    "Editar y recalcular el anden con la version 4.10.0.")
                  controls)))))
        (setq index (1+ index)))))
  (list (reverse records) (reverse details) (reverse controls))
)

(defun urb:q-collect-vias
  (/ ss index ename data mov handle via-id name stage substage profile
   surface area road-length average-width status cut fill method sections
   skipped width depth records details controls road-profile layers layer
   layer-name layer-type layer-scope thickness overlap left right left-area
   right-area base-area layer-area quantity unit specification quantity-status)
  (setq ss (urb:q-candidate-set '((-3 ("URB_VIA")))))
  (if ss
    (progn
      (setq index 0)
      (repeat (sslength ss)
        (setq ename (ssname ss index))
        (setq data (urb:get-xdata-strings ename "URB_VIA"))
        (if (and (urb:q-modelspace-p ename)
                 data (urb:string-equal-p (car data) "VIA"))
          (progn
            (setq mov (urb:road-movement-data ename)
                  handle (urb:q-handle ename)
                  via-id (urb:safe-string (urb:q-safe-nth 22 data handle) handle)
                  name (urb:safe-string (urb:q-safe-nth 1 data "VIA") "VIA")
                  stage (urb:safe-string (urb:q-safe-nth 2 data "") "")
                  substage (urb:safe-string (urb:q-safe-nth 3 data "") "")
                  profile (urb:safe-string (urb:q-safe-nth 4 data "") "")
                  surface (urb:safe-string (urb:q-safe-nth 6 data "") "")
                  area (urb:q-number (urb:q-safe-nth 17 data "0"))
                  road-length (urb:q-number (urb:q-safe-nth 18 data "0"))
                  average-width (if (> road-length 1e-9) (/ area road-length) 0.0)
                  status (urb:safe-string (urb:q-safe-nth 19 data "") "")
                  cut (urb:q-number (urb:q-safe-nth 0 mov "0"))
                  fill (urb:q-number (urb:q-safe-nth 1 mov "0"))
                  method (urb:safe-string (urb:q-safe-nth 2 mov "") "")
                  sections (fix (urb:q-number (urb:q-safe-nth 3 mov "0")))
                  skipped (fix (urb:q-number (urb:q-safe-nth 4 mov "0")))
                  width (urb:q-number (urb:q-safe-nth 5 mov "0"))
                  depth (urb:q-number (urb:q-safe-nth 6 mov "0")))
            (setq road-profile (urb:road-profile-by-name profile)
                  layers (if road-profile (cadr road-profile) nil)
                  quantity-status
                    (urb:q-basic-status stage substage
                      (and (> area 1e-9) (> road-length 1e-9) layers
                           (urb:q-unscaled-reference-p ename))))
            (setq details
              (cons
                (list handle via-id name stage substage profile surface area
                  road-length average-width
                  (urb:safe-string (urb:q-safe-nth 10 data "") "")
                  status cut fill method sections skipped width depth)
                details))
            (setq records
              (cons
                (urb:q-record "VIAS" "Geometria" "Longitud de via"
                  profile stage substage "ML" road-length handle quantity-status
                  via-id name)
                records))
            (setq records
              (cons
                (urb:q-record "VIAS" "Geometria" "Area vial modelada"
                  profile stage substage "M2" area handle quantity-status
                  via-id name)
                records))
            (setq records
              (cons
                (urb:q-record "VIAS" "Descapote y nivelacion subrasante"
                  "Compactacion de subrasante (Incluye nivelacion)"
                  "Area vial modelada" stage substage "M2" area
                  handle quantity-status via-id name)
                records))
            (setq records
              (cons
                (urb:q-record "VIAS" "Descapote y nivelacion subrasante"
                  "Descapote mecanico de material vegetal (Incluye cargue y retiro externo)"
                  "Area vial modelada" stage substage "M2" area
                  handle quantity-status via-id name)
                records))
            (setq left (urb:q-number (urb:q-safe-nth 14 data "0"))
                  right (urb:q-number (urb:q-safe-nth 15 data "0"))
                  left-area (min area (* road-length left))
                  right-area (min (- area left-area) (* road-length right))
                  base-area (max 0.0 (- area left-area right-area)))
            (if (null layers)
              (setq controls
                (cons
                  (urb:q-control-row "ALTA" "VIA" handle name
                    (strcat "No se encontro el perfil vial: " profile ".")
                    "Revisar la biblioteca de perfiles del dibujo.")
                  controls)))
            (foreach layer layers
              (setq layer-name (urb:safe-string (nth 0 layer) "Capa")
                    layer-type (urb:safe-string (nth 1 layer) "Volumen")
                    thickness (atof (nth 2 layer))
                    overlap (atof (nth 3 layer))
                    layer-scope (urb:safe-string (nth 4 layer) "Total")
                    layer-area
                      (if (urb:string-equal-p layer-scope "Base") base-area area))
              (if (urb:string-equal-p layer-type "Volumen")
                (setq quantity (* layer-area thickness)
                      unit "M3"
                      specification
                        (strcat profile " | "
                          (rtos (* 100.0 thickness) 2 1) " cm | " layer-scope))
                (setq quantity (* layer-area (+ 1.0 (/ overlap 100.0)))
                      unit "M2"
                      specification
                        (strcat profile " | traslapo "
                          (rtos overlap 2 1) "% | " layer-scope)))
              (setq records
                (cons
                  (urb:q-record "VIAS" "Pavimento" layer-name specification
                    stage substage unit quantity handle quantity-status via-id name)
                  records)))
            (if mov
              (progn
                (setq records
                  (cons
                    (urb:q-record "VIAS" "Excavaciones y rellenos"
                      "Excavacion mecanica en material comun (Incluye cargue, transporte y disposicion)"
                      method stage substage "M3" cut handle
                      (if (= quantity-status "OK") "CALCULADO" "REVISAR")
                      via-id name)
                    records))
                (setq records
                  (cons
                    (urb:q-record "VIAS" "Movimiento de tierras" "Relleno"
                      method stage substage "M3" fill handle
                      (if (= quantity-status "OK") "CALCULADO" "REVISAR")
                      via-id name)
                    records)))
              (setq controls
                (cons
                  (urb:q-control-row "ALTA" "VIA" handle name
                    "Movimiento de tierras pendiente."
                    "Editar la via y completar superficie y rasante.")
                  controls)))
            (if (= quantity-status "REVISAR")
              (setq controls
                (cons
                  (urb:q-control-row "ALTA" "VIA" handle name
                    "La via no tiene etapa, subetapa, geometria/perfil valido o fue escalada fuera de EDITAR."
                    "Completar o reconstruir mediante EDITAR; sus cantidades no se sumaran.")
                  controls)))))
        (setq index (1+ index)))))
  (list (reverse records) (reverse details) (reverse controls))
)

(defun urb:q-collect-prefabricados
  (/ ss index ename data handle prefab stage substage width length-value
   mode destino red conceptos budget-name records details controls quantity-status)
  (setq ss (urb:q-candidate-set '((-3 ("URB_PREFAB_BLOCK")))))
  (if ss
    (progn
      (setq index 0)
      (repeat (sslength ss)
        (setq ename (ssname ss index))
        (setq data (urb:get-xdata-strings ename "URB_PREFAB_BLOCK"))
        (if (and (urb:q-modelspace-p ename) data)
          (progn
            (setq handle (urb:q-handle ename)
                  prefab (strcase (urb:safe-string (urb:q-safe-nth 0 data "") ""))
                  stage (urb:safe-string (urb:q-safe-nth 1 data "") "")
                  substage (urb:safe-string (urb:q-safe-nth 2 data "") "")
                  width (urb:q-number (urb:q-safe-nth 3 data "0"))
                  length-value (urb:q-number (urb:q-safe-nth 4 data "0"))
                  mode (urb:safe-string (urb:q-safe-nth 5 data "") "")
                  destino (urb:safe-string (urb:q-safe-nth 7 data "")
                    (urb:prefab-destino-default prefab))
                  red (urb:prefab-destino-red destino prefab)
                  conceptos (urb:prefab-conceptos prefab)
                  budget-name (car conceptos))
            (setq quantity-status
              (urb:q-basic-status stage substage
                (and (> width 1e-9) (> length-value 1e-9)
                     (member prefab '("BORDILLO" "SARDINEL" "CANUELA"))
                     (urb:q-unscaled-reference-p ename))))
            (setq details
              (cons
                (list handle prefab stage substage width length-value mode
                  destino red quantity-status)
                details))
            (setq records
              (cons
                (urb:q-record "PREFABRICADOS" "Acabados" budget-name
                  (strcat "Ancho " (rtos width 2 3) " m | " mode)
                  stage substage "ML" length-value handle quantity-status "" "")
                records))
            ;; Una entidad representa un tramo, no una pieza comercial. La
            ;; salida UND=1 se retiro porque inducía a contar tramos como piezas.
            (if (= quantity-status "REVISAR")
              (setq controls
                (cons
                  (urb:q-control-row "ALTA" "PREFABRICADO" handle prefab
                    "El prefabricado no tiene datos validos o fue escalado fuera de EDITAR."
                    "Completarlo o reconstruirlo mediante EDITAR; su longitud no se sumara.")
                  controls)))))
        (setq index (1+ index)))))
  (list (reverse records) (reverse details) (reverse controls))
)

(defun urb:q-collect-green-zones
  (/ ss index ename data handle stage substage area perimeter thickness
   volume quantity-status records details controls)
  (setq ss (urb:q-candidate-set '((-3 ("URB_GREEN_BLOCK")))))
  (if ss
    (progn
      (setq index 0)
      (repeat (sslength ss)
        (setq ename (ssname ss index)
              data (urb:get-xdata-strings ename "URB_GREEN_BLOCK"))
        (if (and (urb:q-modelspace-p ename)
                 data
                 (urb:string-equal-p
                   (urb:q-safe-nth 0 data "") "ZONA_VERDE"))
          (progn
            (setq handle (urb:q-handle ename)
                  stage (urb:safe-string
                    (urb:q-safe-nth 1 data "") "")
                  substage (urb:safe-string
                    (urb:q-safe-nth 2 data "") "")
                  area (urb:q-number
                    (urb:q-safe-nth 3 data "0"))
                  perimeter (urb:q-number
                    (urb:q-safe-nth 4 data "0"))
                  thickness (urb:q-number
                    (urb:q-safe-nth 5 data "0"))
                  volume (urb:q-number
                    (urb:q-safe-nth 6 data "0"))
                  quantity-status
                    (urb:q-basic-status stage substage
                      (and (> area 1e-9)
                           (> thickness 1e-9)
                           (> volume 1e-9)
                           (urb:q-unscaled-reference-p ename))))
            (setq details
              (cons
                (list handle stage substage area perimeter
                  thickness volume quantity-status)
                details))
            (setq records
              (cons
                (urb:q-record "ZONAS VERDES" "Paisajismo"
                  "Conformacion de zona verde"
                  "Area neta modelada"
                  stage substage "M2" area handle quantity-status "" "")
                records))
            (setq records
              (cons
                (urb:q-record "ZONAS VERDES" "Paisajismo"
                  "Suministro y colocacion de tierra negra"
                  (strcat "Espesor " (rtos thickness 2 3) " m")
                  stage substage "M3" volume handle quantity-status "" "")
                records))
            (if (= quantity-status "REVISAR")
              (setq controls
                (cons
                  (urb:q-control-row "ALTA" "ZONA VERDE" handle
                    "Zona verde"
                    "Faltan etapa, subetapa, area o espesor valido; o el bloque fue escalado."
                    "Abra la zona con EDITAR y complete sus datos.")
                  controls)))))
        (setq index (1+ index)))))
  (list (reverse records) (reverse details) (reverse controls))
)

(defun urb:q-network-group (base)
  (cond
    ((= base "LUMINARIA_AP") "LUMINARIAS")
    ((member base
       '("TRAMO_ARESIDUAL" "TRAMO_ALLUVIAS" "TRAMO_ACUEDUCTO"
         "POZO_SANITARIO" "POZO_PLUVIAL" "SUMIDERO"
         "ACCESORIO_ACUEDUCTO"))
      "HIDROSANITARIAS")
    (T "ELECTRICAS"))
)

(defun urb:q-network-element (base atts)
  (cond
    ((= base "TRAMO_ARESIDUAL") "Tuberia sanitaria")
    ((= base "TRAMO_ALLUVIAS") "Tuberia pluvial")
    ((= base "TRAMO_ACUEDUCTO") "Tuberia de acueducto")
    ((= base "TRAMO_E_MT") "Canalizacion media tension")
    ((= base "TRAMO_E_BT_AP")
      (if (= (strcase (mp:getval "TIPO_RED" atts "BT")) "AP")
        "Canalizacion alumbrado publico"
        "Canalizacion baja tension"))
    ((= base "POZO_SANITARIO") "Pozo sanitario")
    ((= base "POZO_PLUVIAL") "Pozo pluvial")
    ((= base "SUMIDERO") "Sumidero")
    ((= base "ACCESORIO_ACUEDUCTO") "Accesorio de acueducto")
    ((= base "LUMINARIA_AP") "Luminaria")
    (T base))
)

(defun urb:q-network-detail-row
  (group base handle layer point atts)
  (list group base handle layer
    (urb:q-number (car point)) (urb:q-number (cadr point))
    (mp:getval "ETAPA" atts "")
    (mp:getval "SUBETAPA" atts "")
    (mp:getval "ID" atts "")
    (mp:getval "CODIGO" atts "")
    (mp:getval "RED" atts "")
    (mp:getval "TIPO_RED" atts "")
    (mp:getval "DESDE" atts "")
    (mp:getval "HASTA" atts "")
    (mp:getval "POZO_INI" atts "")
    (mp:getval "POZO_FIN" atts "")
    (mp:getval "TIPO_EXTREMO_INI" atts "")
    (mp:getval "TIPO_EXTREMO_FIN" atts "")
    (mp:getval "HANDLE_EXTREMO_INI" atts "")
    (mp:getval "HANDLE_EXTREMO_FIN" atts "")
    (mp:getval "DIAMETRO" atts "")
    (mp:getval "MATERIAL" atts "")
    (urb:q-number (mp:getval "LONGITUD" atts "0"))
    (urb:q-number (mp:getval "LONGITUD_2D" atts "0"))
    (urb:q-number (mp:getval "LONGITUD_3D" atts "0"))
    (mp:getval "MODO_LONGITUD" atts "")
    (urb:q-number (mp:getval "PENDIENTE" atts "0"))
    (urb:q-number (mp:getval "PENDIENTE_CALCULADA" atts "0"))
    (urb:q-number (mp:getval "COTA_TN_INI" atts "0"))
    (urb:q-number (mp:getval "COTA_TN_FIN" atts "0"))
    (urb:q-number (mp:getval "COTA_CLAVE_INI" atts "0"))
    (urb:q-number (mp:getval "COTA_CLAVE_FIN" atts "0"))
    (urb:q-number (mp:getval "PROFUNDIDAD_INI" atts "0"))
    (urb:q-number (mp:getval "PROFUNDIDAD_FIN" atts "0"))
    (urb:q-number (mp:getval "PROFUNDIDAD_MEDIA" atts "0"))
    (mp:getval "CONDUCTOR" atts (mp:getval "CONDUCTORES" atts ""))
    (urb:q-number (mp:getval "DUCTOS" atts "0"))
    (urb:q-number (mp:getval "LIBRES" atts "0"))
    (mp:getval "DIAM_DUCTO" atts "")
    (mp:getval "MATERIAL_DUCTO" atts "")
    (mp:getval "TIPO_CAJA" atts "")
    (mp:getval "TIPO_LUMINARIA" atts "")
    (mp:getval "FUENTE_LED" atts "")
    (mp:getval "CIRCUITO" atts "")
    (mp:getval "CIRCUITO_AP" atts "")
    (urb:q-number (mp:getval "PROFUNDIDAD" atts "0"))
    (urb:q-number (mp:getval "ANCHO_ZANJA" atts "0"))
    (urb:q-number (mp:getval "ESPESOR_CAMA" atts "0"))
    (urb:q-number (mp:getval "ANCHO_REPOSICION" atts "0"))
    (urb:q-number (mp:getval "EXCAVACION_M3" atts "0"))
    (urb:q-number (mp:getval "CAMA_M3" atts "0"))
    (urb:q-number (mp:getval "VOLUMEN_ELEMENTO_M3" atts "0"))
    (urb:q-number (mp:getval "RELLENO_M3" atts "0"))
    (urb:q-number (mp:getval "SOBRANTE_M3" atts "0"))
    (urb:q-number (mp:getval "REPOSICION_M2" atts "0"))
    (mp:getval "METODO_CANTIDADES" atts "")
    (mp:getval "CONTROL_ESTADO" atts "")
    (mp:getval "CONTROL_MENSAJES" atts "")
    (mp:getval "TIPO_ACCESORIO" atts "")
    (mp:getval "SERIE" atts "")
    (mp:getval "CD" atts "")
    (mp:getval "PF" atts ""))
)


(defun urb:q-network-linear-specification (group atts ducts conductor)
  (if (= group "HIDROSANITARIAS")
    (strcat
      "Diam. " (mp:getval "DIAMETRO" atts "-")
      " | " (mp:getval "MATERIAL" atts "-"))
    (strcat
      (rtos ducts 2 0) " ducto(s) "
      (mp:getval "DIAM_DUCTO" atts "-") " "
      (mp:getval "MATERIAL_DUCTO" atts "-")
      (if (/= conductor "") (strcat " | " conductor) "")))
)

(defun urb:q-network-point-specification (base atts)
  (cond
    ((= base "LUMINARIA_AP")
      (strcat
        (mp:getval "TIPO_LUMINARIA" atts "-")
        " | " (mp:getval "FUENTE_LED" atts "-")
        " | altura " (mp:getval "ALTURA" atts "-") " m"
        " | brazo " (mp:getval "BRAZO" atts "-") " m"
        " | avance " (mp:getval "AVANCE" atts "-") " m"))
    ((= base "ACCESORIO_ACUEDUCTO")
      (strcat
        (mp:getval "TIPO_ACCESORIO" atts "-")
        " | Diam. " (mp:getval "DIAMETRO" atts "-")
        " | salida " (mp:getval "DIAMETRO_SALIDA" atts "-")
        " | " (mp:getval "MATERIAL" atts "-")))
    ((member base '("POZO_SANITARIO" "POZO_PLUVIAL" "SUMIDERO"))
      (strcat
        (mp:getval "TIPO_RED" atts base)
        " | Diam. " (mp:getval "DIAMETRO" atts "-")
        " | profundidad " (mp:getval "PROFUNDIDAD" atts "-") " m"))
    ((member base *mp-caja-elec-list*)
      (strcat
        (mp:getval "TIPO_CAJA" atts base)
        " | serie " (mp:getval "SERIE" atts "-")
        " | profundidad " (mp:getval "PROFUNDIDAD" atts "-") " m"))
    (T
      (mp:getval "TIPO_CAJA" atts
        (mp:getval "TIPO_RED" atts base))))
)

(defun urb:q-network-quantity-records
  (group element specification atts stage substage length-value ducts conductor
   handle status / records handle-ini handle-fin endpoint-ini endpoint-fin
   link-id link-name construction-spec quantity)
  (setq handle-ini (mp:getval "HANDLE_EXTREMO_INI" atts "")
        handle-fin (mp:getval "HANDLE_EXTREMO_FIN" atts "")
        endpoint-ini
          (mp:getval "DESDE" atts (mp:getval "POZO_INI" atts ""))
        endpoint-fin
          (mp:getval "HASTA" atts (mp:getval "POZO_FIN" atts ""))
        link-id
          (if (or (/= handle-ini "") (/= handle-fin ""))
            (strcat handle-ini " -> " handle-fin)
            "")
        link-name
          (if (or (/= endpoint-ini "") (/= endpoint-fin ""))
            (strcat endpoint-ini " -> " endpoint-fin)
            "")
        construction-spec
          (strcat
            "Metodo " (mp:getval "METODO_CANTIDADES" atts "-")
            " | ancho " (mp:getval "ANCHO_ZANJA" atts "-") " m"
            " | profundidad media "
            (mp:getval "PROFUNDIDAD_MEDIA" atts
              (mp:getval "PROFUNDIDAD" atts "-")) " m")
        records
          (list
            (urb:q-record group "Tramos" element specification
              stage substage "ML" length-value handle status
              link-id link-name)))
  (if (and (= group "ELECTRICAS") (> ducts 0.0))
    (setq records
      (append records
        (list
          (urb:q-record group "Ducteria" "Ducteria instalada"
            (strcat
              (mp:getval "DIAM_DUCTO" atts "-") " "
              (mp:getval "MATERIAL_DUCTO" atts "-"))
            stage substage "ML" (* length-value ducts)
            handle status link-id link-name)))))
  (if (and (= group "ELECTRICAS") (/= conductor ""))
    (setq records
      (append records
        (list
          (urb:q-record group "Conductores"
            "Tendido de conductor - longitud de ruta" conductor
            stage substage "ML" length-value handle status
            link-id link-name)))))
  (foreach item
    '(("EXCAVACION_M3" "Excavacion de zanja" "M3")
      ("CAMA_M3" "Cama de apoyo" "M3")
      ("RELLENO_M3" "Relleno de zanja" "M3")
      ("TRITURADO_M3" "Cimentacion en triturado tamano grava" "M3")
      ("RECEBO_M3" "Suministro y colocacion de recebo B-200" "M3")
      ("ENTIBADO_LE3_M2" "Entibado para excavaciones <=3m" "M2")
      ("ENTIBADO_GT3_M2" "Entibado para excavaciones >3m" "M2")
      ("SOBRANTE_M3" "Retiro de sobrantes" "M3")
      ("REPOSICION_M2" "Reposicion superficial" "M2"))
    (setq quantity (urb:q-number (mp:getval (car item) atts "0")))
    (if (> quantity 1e-9)
      (setq records
        (append records
          (list
            (urb:q-record group "Movimiento de tierras" (cadr item)
              construction-spec stage substage (caddr item) quantity
              handle status link-id link-name))))))
  records
)

(defun urb:q-network-control-rows
  (group handle element stage base length-value atts
   / controls control-state control-messages substage identity)
  (setq substage (mp:getval "SUBETAPA" atts "")
        identity (mp:getval "ID" atts (mp:getval "CODIGO" atts "")))
  (if (= stage "")
    (setq controls
      (cons
        (urb:q-control-row "MEDIA" group handle element
          "El elemento no tiene etapa."
          "Completar los atributos mediante EDITAR.")
        controls)))
  (if (= substage "")
    (setq controls
      (cons
        (urb:q-control-row "MEDIA" group handle element
          "El elemento no tiene subetapa."
          "Completar los atributos mediante EDITAR.")
        controls)))
  (if (and (not (mp:base-is-tramo base)) (= identity ""))
    (setq controls
      (cons
        (urb:q-control-row "ALTA" group handle element
          "El elemento puntual no tiene ID o codigo."
          "Asignar una identidad mediante EDITAR; no se sumara hasta corregirlo.")
        controls)))
  (if (and (mp:base-is-tramo base) (<= length-value 1e-9))
    (setq controls
      (cons
        (urb:q-control-row "ALTA" group handle element
          "El tramo no tiene una longitud valida."
          "Usar EDITAR para revisar el tramo o reconstruirlo si su geometria es invalida.")
        controls)))
  (if (mp:base-is-tramo base)
    (progn
      (setq control-state (strcase (mp:getval "CONTROL_ESTADO" atts ""))
            control-messages (mp:getval "CONTROL_MENSAJES" atts ""))
      (cond
        ((= control-state "")
          (setq controls
            (cons
              (urb:q-control-row "ALTA" group handle element
                "El tramo no ha sido migrado al esquema constructivo vigente."
                "El bloque requiere migracion al esquema actual antes de exportar.")
              controls)))
        ((/= control-state "OK")
          (setq controls
            (cons
              (urb:q-control-row "ALTA" group handle element
                (if (= control-messages "")
                  "El tramo tiene observaciones de validacion."
                  control-messages)
                "Usar EDITAR para completar datos y revisar sus extremos vinculados.")
              controls))))))
  (reverse controls)
)

(defun urb:q-network-entity-package
  (ename / obj bname atts base group handle layer point stage substage
   element length-value ducts conductor status control-state detail specification records
   identity
   hydro electric lighting controls)
  (setq obj (urb:as-vla-object ename))
  (if (and obj (urb:q-modelspace-p ename))
    (progn
      (setq bname
        (urb:safe-string
          (vl-catch-all-apply 'vla-get-EffectiveName (list obj)) ""))
      (if (and (/= bname "") (mp:is-cant-blockname bname))
        (progn
          (setq atts (mp:att-alist ename)
                base
                  (strcase
                    (urb:safe-string (mp:infer-base bname atts) "")))
          (if (/= base "")
            (progn
              (setq group (urb:q-network-group base)
                    handle (urb:q-handle ename)
                    layer (urb:safe-string (vla-get-Layer obj) "")
                    point (vlax-get obj 'InsertionPoint)
                    stage (mp:getval "ETAPA" atts "")
                    substage (mp:getval "SUBETAPA" atts "")
                    identity
                      (mp:getval "ID" atts (mp:getval "CODIGO" atts ""))
                    element (urb:q-network-element base atts)
                    length-value
                      (urb:q-number (mp:getval "LONGITUD" atts "0"))
                    ducts (urb:q-number (mp:getval "DUCTOS" atts "0"))
                    conductor
                      (mp:getval "CONDUCTOR" atts
                        (mp:getval "CONDUCTORES" atts ""))
                    control-state
                      (strcase (mp:getval "CONTROL_ESTADO" atts ""))
                    status
                      (cond
                        ((and (mp:base-is-tramo base)
                              (<= length-value 1e-9)) "PENDIENTE")
                        ((not (mp:base-is-tramo base))
                          (urb:q-basic-status stage substage (/= identity "")))
                        ((= control-state "OK") "OK")
                        ((= control-state "") "MIGRAR")
                        (T "REVISAR"))
                    detail
                      (urb:q-network-detail-row
                        group base handle layer point atts))
              (cond
                ((= group "HIDROSANITARIAS") (setq hydro (list detail)))
                ((= group "LUMINARIAS") (setq lighting (list detail)))
                (T (setq electric (list detail))))
              (if (mp:base-is-tramo base)
                (progn
                  (setq specification
                    (urb:q-network-linear-specification
                      group atts ducts conductor))
                  (setq records
                    (urb:q-network-quantity-records
                      group element specification atts stage substage
                      length-value ducts conductor handle status)))
                (progn
                  (setq specification
                    (urb:q-network-point-specification base atts))
                  (setq records
                    (list
                      (urb:q-record group "Elementos puntuales"
                        element specification stage substage "UND" 1.0
                        handle status "" "")))))
              (setq controls
                (urb:q-network-control-rows
                  group handle element stage base length-value atts))
              (list records hydro electric lighting controls)))))))
)

(defun urb:q-network-duplicate-point-audit
  (details / counts detail base identity key found duplicate-keys handles controls)
  (foreach detail details
    (setq base (urb:safe-string (nth 1 detail) "")
          identity
            (urb:safe-string
              (if (/= (urb:safe-string (nth 8 detail) "") "")
                (nth 8 detail) (nth 9 detail)) ""))
    (if (and (not (mp:base-is-tramo base)) (/= identity ""))
      (progn
        (setq key (strcat (nth 0 detail) "|" base "|" (strcase identity)))
        (if (setq found (assoc key counts))
          (setq counts
            (subst (cons key (1+ (cdr found))) found counts))
          (setq counts (cons (cons key 1) counts))))))
  (foreach found counts
    (if (> (cdr found) 1)
      (setq duplicate-keys (cons (car found) duplicate-keys))))
  (foreach detail details
    (setq base (urb:safe-string (nth 1 detail) "")
          identity
            (urb:safe-string
              (if (/= (urb:safe-string (nth 8 detail) "") "")
                (nth 8 detail) (nth 9 detail)) "")
          key (strcat (nth 0 detail) "|" base "|" (strcase identity)))
    (if (and (/= identity "") (member key duplicate-keys))
      (progn
        (setq handles (cons (nth 2 detail) handles))
        (setq controls
          (cons
            (urb:q-control-row "ALTA" (nth 0 detail) (nth 2 detail) base
              (strcat "El ID/codigo " identity " esta repetido para " base ".")
              "Asignar identificadores unicos; el elemento no se sumara hasta corregirlo.")
            controls)))))
  (list handles (reverse controls))
)

(defun urb:q-collect-networks
  (/ ss index ename package records hydro electric lighting controls audit
   duplicate-handles adjusted result record)
  (setq ss (urb:q-candidate-set '((0 . "INSERT"))))
  (if ss
    (progn
      (setq index 0)
      (repeat (sslength ss)
        (setq ename (ssname ss index)
              package (urb:q-network-entity-package ename))
        (if package
          (setq records
                  (append (reverse (nth 0 package)) records)
                hydro
                  (append (reverse (nth 1 package)) hydro)
                electric
                  (append (reverse (nth 2 package)) electric)
                lighting
                  (append (reverse (nth 3 package)) lighting)
                controls
                  (append (reverse (nth 4 package)) controls)))
        (setq index (1+ index)))))
  (setq audit
    (urb:q-network-duplicate-point-audit
      (append hydro electric lighting))
    duplicate-handles (nth 0 audit)
    controls (append controls (nth 1 audit)))
  (foreach record records
    (if (member (nth 8 record) duplicate-handles)
      (setq adjusted (urb:list-set-nth 9 "REVISAR" record))
      (setq adjusted record))
    (setq result (cons adjusted result)))
  (list
    (reverse result)
    (reverse hydro)
    (reverse electric)
    (reverse lighting)
    (reverse controls))
)

(defun urb:excel-column-name (index / result remainder)
  (setq result "")
  (while (> index 0)
    (setq remainder (rem (1- index) 26))
    (setq result (strcat (chr (+ 65 remainder)) result))
    (setq index (fix (/ (1- index) 26))))
  result
)

(defun urb:excel-matrix-variant
  (matrix / row-count col-count array row-index col-index row value)
  (setq row-count (length matrix)
        col-count (if matrix (length (car matrix)) 0))
  (if (and (> row-count 0) (> col-count 0))
    (progn
      (setq array
        (vlax-make-safearray
          vlax-vbVariant
          (cons 0 (1- row-count))
          (cons 0 (1- col-count))))
      (setq row-index 0)
      (foreach row matrix
        (setq col-index 0)
        (repeat col-count
          (setq value
            (if (> (length row) col-index) (nth col-index row) ""))
          (vlax-safearray-put-element array row-index col-index value)
          (setq col-index (1+ col-index)))
        (setq row-index (1+ row-index)))
      (vlax-make-variant array))
    nil)
)

(defun urb:excel-rgb (red green blue)
  (+ red (* 256 green) (* 65536 blue))
)

(defun urb:excel-release (object)
  (if (= (type object) 'VLA-OBJECT)
    (vl-catch-all-apply 'vlax-release-object (list object)))
  nil
)

(defun urb:excel-write-table
  (application sheet matrix numeric-columns
   / row-count col-count last-column address target header font interior
   columns column index width number-range window result)
  (setq row-count (length matrix)
        col-count (if matrix (length (car matrix)) 0))
  (if (and (> row-count 0) (> col-count 0))
    (progn
      (setq last-column (urb:excel-column-name col-count)
            address (strcat "A1:" last-column (itoa row-count))
            target (vlax-get-property sheet 'Range address))
      (vlax-put-property target 'Value2 (urb:excel-matrix-variant matrix))
      (setq header
        (vlax-get-property sheet 'Range
          (strcat "A1:" last-column "1")))
      (setq font (vlax-get-property header 'Font))
      (vlax-put-property font 'Bold :vlax-true)
      (vlax-put-property font 'Color (urb:excel-rgb 255 255 255))
      (setq interior (vlax-get-property header 'Interior))
      (vlax-put-property interior 'Color (urb:excel-rgb 31 78 121))
      (vlax-put-property header 'WrapText :vlax-true)
      (vlax-put-property header 'HorizontalAlignment -4108)
      (vlax-put-property header 'VerticalAlignment -4108)
      (vlax-put-property header 'RowHeight 30.0)
      (vl-catch-all-apply 'vlax-invoke-method (list target 'AutoFilter))
      (setq columns (vlax-get-property target 'Columns))
      (vl-catch-all-apply 'vlax-invoke-method (list columns 'AutoFit))
      (setq index 1)
      (repeat col-count
        (setq column
          (vl-catch-all-apply 'vlax-get-property (list columns 'Item index)))
        (if (not (vl-catch-all-error-p column))
          (progn
            (setq width (vlax-get-property column 'ColumnWidth))
            (if (> width 42.0) (vlax-put-property column 'ColumnWidth 42.0))
            (if (< width 9.0) (vlax-put-property column 'ColumnWidth 9.0))
            (urb:excel-release column)))
        (setq index (1+ index)))
      (foreach index numeric-columns
        (if (> row-count 1)
          (progn
            (setq number-range
              (vlax-get-property sheet 'Range
                (strcat (urb:excel-column-name index) "2:"
                        (urb:excel-column-name index) (itoa row-count))))
            (vlax-put-property number-range 'NumberFormatLocal "#.##0,00")
            (urb:excel-release number-range))))
      (vlax-invoke-method sheet 'Activate)
      (setq window
        (vl-catch-all-apply 'vlax-get-property (list application 'ActiveWindow)))
      (if (not (vl-catch-all-error-p window))
        (progn
          (vl-catch-all-apply 'vlax-put-property
            (list window 'SplitRow 1))
          (vl-catch-all-apply 'vlax-put-property
            (list window 'FreezePanes :vlax-true))
          (vl-catch-all-apply 'vlax-put-property
            (list window 'DisplayGridlines :vlax-false))
          (urb:excel-release window)))
      (urb:excel-release columns)
      (urb:excel-release interior)
      (urb:excel-release font)
      (urb:excel-release header)
      (urb:excel-release target)
      T)
    nil)
)

(defun urb:excel-format-column
  (sheet column-index row-count number-format / column-name number-range)
  (if (> row-count 1)
    (progn
      (setq column-name (urb:excel-column-name column-index)
            number-range
              (vlax-get-property sheet 'Range
                (strcat column-name "2:" column-name (itoa row-count))))
      (vlax-put-property number-range 'NumberFormatLocal number-format)
      (urb:excel-release number-range)))
  nil
)

(defun urb:excel-add-sheet (sheets name / sheet result)
  (setq result (vl-catch-all-apply 'vlax-invoke-method (list sheets 'Add)))
  (if (vl-catch-all-error-p result)
    nil
    (progn
      (setq sheet result)
      (vlax-put-property sheet 'Name name)
      sheet))
)

(defun urb:q-summary-matrix (aggregated / matrix item)
  (setq matrix
    (list
      '("CAPITULO" "SISTEMA" "ELEMENTO" "ESPECIFICACION"
        "ETAPA" "SUBETAPA" "UND" "CANTIDAD" "OBJETOS" "ESTADO")))
  (foreach item aggregated
    (setq matrix
      (append matrix
        (list
          (list
            (nth 1 item) (nth 2 item) (nth 3 item) (nth 4 item)
            (nth 5 item) (nth 6 item) (nth 7 item) (nth 8 item)
            (nth 9 item) (nth 10 item))))))
  matrix
)

(defun urb:q-trace-matrix (records / matrix item)
  (setq matrix
    (list
      '("CAPITULO" "SISTEMA" "ELEMENTO" "ESPECIFICACION"
        "ETAPA" "SUBETAPA" "UND" "CANTIDAD" "HANDLE" "ESTADO"
        "VINCULO_ID" "VINCULO_NOMBRE")))
  (foreach item records
    (setq matrix (append matrix (list item))))
  matrix
)

(defun urb:q-control-matrix (controls / matrix item)
  (setq matrix
    (list '("SEVERIDAD" "CATEGORIA" "HANDLE" "ELEMENTO" "HALLAZGO" "ACCION")))
  (foreach item controls
    (setq matrix (append matrix (list item))))
  matrix
)

(defun urb:q-detail-matrix (headers rows / matrix row)
  (setq matrix (list headers))
  (foreach row rows (setq matrix (append matrix (list row))))
  matrix
)

(setq *urb-excel-general-sheet* "CANTIDADES_URBANISMO")
(setq *urb-excel-general-table* "tbl_urbanismo_cantidades")
(setq *urb-excel-link-key* "EXCEL_MASTER_PATH")
(setq *urb-excel-table-schema* "2")
(setq *urb-excel-general-headers*
  '("ID_REGISTRO" "TIPO_REGISTRO" "VERSION_ESQUEMA" "VERSION_LSP"
    "ID_DWG" "ARCHIVO_DWG" "RUTA_DWG" "FECHA_ACTUALIZACION" "CAPITULO"
    "SISTEMA" "ELEMENTO" "ESPECIFICACION" "ETAPA" "SUBETAPA"
    "UNIDAD" "CANTIDAD" "CANTIDAD_ORIGINAL" "INCLUIR_CANTIDAD"
    "HANDLE" "ESTADO" "VINCULO_ID"
    "VINCULO_NOMBRE" "OBSERVACION" "ACCION"))

(defun urb:excel-safe-text (value / text first-character)
  (setq text (urb:safe-string value ""))
  (if (> (strlen text) 0)
    (progn
      (setq first-character (substr text 1 1))
      (if (member first-character '("=" "+" "-" "@"))
        (strcat "'" text)
        text))
    text)
)

(defun urb:excel-display-timestamp ()
  (menucmd "M=$(edtime,$(getvar,date),YYYY-MO-DD HH:MM:SS)")
)

(defun urb:excel-file-timestamp ()
  (menucmd "M=$(edtime,$(getvar,date),YYYYMODD_HHMMSS)")
)

(defun urb:q-duplicate-road-id-controls
  (records / counts record id found duplicates adjusted controls result)
  (foreach record records
    (if (and (urb:string-equal-p (nth 0 record) "VIAS")
             (urb:string-equal-p (nth 2 record) "Longitud de via")
             (/= (setq id (urb:safe-string (nth 10 record) "")) ""))
      (if (setq found (assoc id counts))
        (setq counts
          (subst (cons id (1+ (cdr found))) found counts))
        (setq counts (cons (cons id 1) counts)))))
  (foreach found counts
    (if (> (cdr found) 1)
      (setq duplicates (cons (car found) duplicates))))
  (foreach record records
    (setq id (urb:safe-string (nth 10 record) ""))
    (if (and (/= id "") (member id duplicates)
             (member (strcase (nth 0 record)) '("VIAS" "ANDENES")))
      (progn
        (setq adjusted (urb:list-set-nth 9 "REVISAR" record))
        (if (and (urb:string-equal-p (nth 0 record) "VIAS")
                 (urb:string-equal-p (nth 2 record) "Longitud de via"))
          (setq controls
            (cons
              (urb:q-control-row "ALTA" "VINCULO VIA-ANDEN"
                (nth 8 record) (nth 11 record)
                (strcat "El VIA_ID " id " esta repetido en varias vias.")
                "Editar o reconstruir la copia duplicada; sus cantidades y andenes vinculados no se sumaran.")
              controls))))
      (setq adjusted record))
    (setq result (cons adjusted result)))
  (list (reverse result) (reverse controls))
)

(defun urb:q-refresh-network-one (ename / obj bname atts base)
  (if (urb:q-modelspace-p ename)
    (progn
      (setq obj (urb:as-vla-object ename))
      (if obj
        (progn
          (setq bname
            (urb:safe-string
              (vl-catch-all-apply 'vla-get-EffectiveName (list obj)) ""))
          (if (and (/= bname "") (mp:is-cant-blockname bname))
            (progn
              (setq atts (mp:att-alist ename)
                    base (mp:infer-base bname atts))
              (if (mp:base-is-tramo base)
                (progn (mp:update-block-after-edit ename nil) T)))))))))

;; ---------- preactualizacion de PUNTOS (2026-09-13) ----------
;; Los tramos ya se recalculaban solos antes de cada exportacion, pero los
;; puntos no entraban en la barrida: corregir la cota de un pozo no
;; recalculaba su profundidad, y tocaba rehacerla a mano uno por uno.
;; Ahora la profundidad se REDERIVA de las dos cotas (tapa - clave).
;; Condicion estricta a proposito: solo cuando AMBAS son elevaciones
;; validas y la diferencia es positiva y razonable. Si falta una cota, o
;; alguna trae una profundidad escrita donde va la elevacion, NO se
;; inventa nada -- se deja como esta y la auditoria de cotas lo reporta.
;; Esto respeta la regla de no intercambiar cotas ni inferirlas solas.
(defun urb:q-refresh-punto-one (ename / base atts tapa clave dif nueva actual)
  (if (urb:q-modelspace-p ename)
    (progn
      (setq atts (mp:att-alist ename))
      ;; mismo filtro barato que la auditoria: sin las dos casillas de
      ;; cota no hay nada que rederivar
      (if (and (assoc "COTA_CLAVE_INI" atts) (assoc "COTA_TN_INI" atts)
               (mp:base-con-cota-p (setq base (mp:point-reference-base ename))))
        (progn
          (setq tapa (mp:numeric-real (mp:getval "COTA_TN_INI" atts ""))
                clave (mp:numeric-real (mp:getval "COTA_CLAVE_INI" atts "")))
          (if (and tapa clave
                   (>= (abs tapa) *mp-cota-elevacion-minima*)
                   (>= (abs clave) *mp-cota-elevacion-minima*))
            (progn
              (setq dif (- tapa clave))
              (if (and (> dif 0.0) (<= dif *mp-pozo-depth-review-limit*))
                (progn
                  (setq nueva (rtos dif 2 3)
                        actual (vl-string-trim " "
                          (mp:getval "PROFUNDIDAD" atts "")))
                  (if (/= nueva actual)
                    (progn
                      ;; OJO: aqui NO se usa mp:update-block-after-edit.
                      ;; En la rama de punto esa funcion llama a
                      ;; mp:auto-terrain-values, que REESCRIBE COTA_TN_INI
                      ;; con lo que devuelva SUP_TN (solo se protege de
                      ;; consultas fallidas). Usarla aqui pisaria en
                      ;; silencio las cotas de terreno digitadas a mano y
                      ;; dejaria la profundidad recien escrita peleada con
                      ;; la tapa nueva. Este barrido solo deriva la
                      ;; profundidad de las dos cotas TAL COMO ESTAN.
                      (mp:setatt-one ename "PROFUNDIDAD" nueva)
                      (setq atts (mp:alist-set atts "PROFUNDIDAD" nueva))
                      ;; la etiqueta puede mostrar la profundidad
                      (vl-catch-all-apply 'mp:setatt-one
                        (list ename "ETIQUETA" (mp:label-point base atts)))
                      ;; el arrastre al tramo NO se hace aqui:
                      ;; mp:update-segments-for-endpoint barre TODOS los
                      ;; inserts por cada punto (cuadratico), y de todas
                      ;; formas urb:q-refresh-network-segments corre justo
                      ;; despues y resincroniza cada tramo desde los
                      ;; handles de sus extremos, en una sola pasada.
                      T)))))))))))

(defun urb:q-refresh-puntos (/ ss i ename result updated failed
                             doc undo-open old-suppress)
  (setq ss (ssget "_X" '((0 . "INSERT") (2 . "MP_PUNTO_*")))
        doc (urb:doc) updated 0 failed 0)
  (if ss
    (progn
      (if (not
            (vl-catch-all-error-p
              (vl-catch-all-apply 'vla-StartUndoMark (list doc))))
        (setq undo-open T))
      (setq old-suppress *mp-suppress-regen*
            *mp-suppress-regen* T)
      (setq i 0)
      (repeat (sslength ss)
        (setq ename (ssname ss i)
              result (vl-catch-all-apply 'urb:q-refresh-punto-one (list ename)))
        (cond
          ((vl-catch-all-error-p result) (setq failed (1+ failed)))
          (result (setq updated (1+ updated))))
        (setq i (1+ i)))
      (if undo-open
        (vl-catch-all-apply 'vla-EndUndoMark (list doc)))
      (setq *mp-suppress-regen* old-suppress)))
  (if (or (> updated 0) (> failed 0))
    (prompt
      (strcat "\nPreactualizacion de puntos: " (itoa updated)
        " profundidad(es) rederivadas de sus cotas | "
        (itoa failed) " con error.")))
  (list updated failed))

(defun urb:q-refresh-network-segments
  (/ ss index ename result updated failed doc undo-open old-suppress)
  (setq ss (ssget "_X"
             '((0 . "INSERT")
               (2 . "MP_TRAMO_*,TRAMO_*,CANT_TRAMO_*")))
        doc (urb:doc))
  (if ss
    (progn
      (if (not
            (vl-catch-all-error-p
              (vl-catch-all-apply 'vla-StartUndoMark (list doc))))
        (setq undo-open T))
      (setq old-suppress *mp-suppress-regen*
            *mp-suppress-regen* T)
      (setq index 0)
      (repeat (sslength ss)
        (setq ename (ssname ss index))
        (setq result
          (vl-catch-all-apply 'urb:q-refresh-network-one (list ename)))
        (cond
          ((vl-catch-all-error-p result)
            (setq failed (1+ (if failed failed 0))))
          (result
            (setq updated (1+ (if updated updated 0)))))
        (setq index (1+ index)))
      (if undo-open
        (vl-catch-all-apply 'vla-EndUndoMark (list doc)))
      (setq *mp-suppress-regen* old-suppress)
      (vl-catch-all-apply 'vla-Regen (list doc 1))))
  (if (or updated failed)
    (prompt
      (strcat "\nPreactualizacion de redes: "
        (itoa (if updated updated 0)) " tramo(s) recalculados"
        " | " (itoa (if failed failed 0)) " con error.")))
  (list (if updated updated 0) (if failed failed 0))
)

(defun urb:q-scope-controls (/ ss index ename data entity-data layout handle layer result)
  (setq ss (urb:q-candidate-set '((-3 ("URB_Q_SCOPE"))))
        index 0)
  (if ss
    (repeat (sslength ss)
      (setq ename (ssname ss index)
            data (urb:get-xdata-strings ename "URB_Q_SCOPE")
            entity-data (entget ename)
            layout (urb:safe-string (cdr (assoc 410 entity-data)) "")
            handle (urb:q-handle ename)
            layer (urb:safe-string (cdr (assoc 8 entity-data)) ""))
      (if (and (urb:string-equal-p layout "Model")
               data
               (member (strcase (urb:safe-string (car data) "SI"))
                 '("NO" "EXCLUIR" "0")))
        (setq result
          (cons
            (urb:q-control-row "INFO" "ALCANCE" handle layer
              "Elemento excluido manualmente de las cantidades."
              "Use Cantidades > Incluir o excluir seleccion para reincorporarlo.")
            result)))
      (setq index (1+ index))))
  (reverse result)
)

(defun urb:q-collect-all (/ refreshed)
  ;; los puntos primero: si una cota se corrigio, la profundidad queda al
  ;; dia ANTES de que se recalculen los tramos y se recojan cantidades
  (urb:q-refresh-puntos)
  (setq refreshed (urb:q-refresh-network-segments))
  ;; No exportar valores anteriores como validos tras fallar el recalculo.
  (if (> (cadr refreshed) 0)
    (progn
      (prompt "\nExportacion cancelada: hubo errores al recalcular redes. Revise el diagnostico y EDITAR.")
      (exit)))
  (urb:q-collect-readonly))

(defun urb:q-approved-record-count (records / count record)
  (setq count 0)
  (foreach record records
    (if (urb:q-approved-status-p (nth 9 record))
      (setq count (1+ count))))
  count
)

(defun urb:xref-definition-count (/ blocks block result is-xref)
  (setq result 0
        blocks (vla-get-Blocks (urb:doc)))
  (vlax-for block blocks
    (setq is-xref
      (vl-catch-all-apply 'vla-get-IsXRef (list block)))
    (if (and (not (vl-catch-all-error-p is-xref))
             (= is-xref :vlax-true))
      (setq result (1+ result))))
  (urb:excel-release blocks)
  result
)

(defun urb:q-preflight-report (records controls / approved blocked xrefs migrate record)
  (setq approved (urb:q-approved-record-count records)
        blocked (- (length records) approved)
        xrefs (urb:xref-definition-count))
  (foreach record records
    (if (urb:string-equal-p (nth 9 record) "MIGRAR")
      (setq migrate (1+ (if migrate migrate 0)))))
  (prompt
    (strcat
      "\nPrevalidacion de cantidades: " (itoa approved) " aprobadas"
      " | " (itoa blocked) " bloqueadas (se exportan con CANTIDAD=0)"
      " | " (itoa (length controls)) " controles."
      (if (and migrate (> migrate 0))
        (strcat " Hay " (itoa migrate)
          " registro(s) de red por revisar; use Cantidades > Diagnostico de integridad y EDITAR.")
        "")
      (if (> xrefs 0)
        (strcat " Aviso: hay " (itoa xrefs)
          " XREF; sus elementos internos no se incluyen.")
        "")))
  (list approved blocked xrefs)
)

(defun urb:drawing-id (/ value seed)
  (setq value
    (vl-string-trim " "
      (urb:safe-string (urb:config-read "URB_DRAWING_ID") "")))
  (if (= value "")
    (progn
      (setq seed
        (strcat
          (menucmd "M=$(edtime,$(getvar,date),YYYYMODDHHMMSS)")
          "-" (itoa (getvar "MILLISECS"))
          "-" (urb:safe-string (getvar "DWGTITLED") "0")))
      (setq value (strcat "URB-DWG-" seed))
      (urb:config-write "URB_DRAWING_ID" value)))
  value
)

(defun urb:q-general-record-id (drawing-id record)
  (strcat
    drawing-id "|" (nth 8 record) "|" (nth 0 record) "|"
    (nth 1 record) "|" (nth 2 record) "|" (nth 3 record) "|"
    (nth 4 record) "|" (nth 5 record) "|" (nth 6 record))
)

(defun urb:q-general-matrix
  (records controls / drawing-id drawing-name drawing-path timestamp rows item
   index original-quantity approved)
  (setq drawing-id (urb:drawing-id)
        drawing-name (getvar "DWGNAME")
        drawing-path (strcat (getvar "DWGPREFIX") drawing-name)
        timestamp (urb:excel-display-timestamp)
        rows nil
        index 0)
  (foreach item records
    (setq index (1+ index))
    (setq rows
      (cons
        (list
          (urb:excel-safe-text
            (urb:q-general-record-id drawing-id item))
          "CANTIDAD" *urb-excel-table-schema* *urb-version*
          (urb:excel-safe-text drawing-id)
          (urb:excel-safe-text drawing-name)
          (urb:excel-safe-text drawing-path)
          timestamp
          (urb:excel-safe-text (nth 0 item))
          (urb:excel-safe-text (nth 1 item))
          (urb:excel-safe-text (nth 2 item))
          (urb:excel-safe-text (nth 3 item))
          (urb:excel-safe-text (nth 4 item))
          (urb:excel-safe-text (nth 5 item))
          (urb:excel-safe-text (nth 6 item))
          (setq original-quantity (urb:q-number (nth 7 item)))
          (setq approved (urb:q-approved-status-p (nth 9 item)))
          (if approved original-quantity 0.0)
          original-quantity
          (if approved "SI" "NO")
          (urb:excel-safe-text (nth 8 item))
          (urb:excel-safe-text (nth 9 item))
          (urb:excel-safe-text (nth 10 item))
          (urb:excel-safe-text (nth 11 item))
          "" "")
        rows)))
  (foreach item controls
    (setq index (1+ index))
    (setq rows
      (cons
        (list
          (urb:excel-safe-text
            (strcat drawing-id "|CONTROL|" (nth 2 item) "|"
              (nth 1 item) "|" (nth 3 item) "|" (nth 4 item)))
          "CONTROL" *urb-excel-table-schema* *urb-version*
          (urb:excel-safe-text drawing-id)
          (urb:excel-safe-text drawing-name)
          (urb:excel-safe-text drawing-path)
          timestamp
          "CONTROL_CALIDAD"
          (urb:excel-safe-text (nth 1 item))
          (urb:excel-safe-text (nth 3 item))
          "" "" "" "" 0.0 0.0 "NO"
          (urb:excel-safe-text (nth 2 item))
          (urb:excel-safe-text (nth 0 item))
          "" ""
          (urb:excel-safe-text (nth 4 item))
          (urb:excel-safe-text (nth 5 item)))
        rows)))
  (cons *urb-excel-general-headers* (reverse rows))
)

(defun urb:excel-item (collection key / result)
  (setq result
    (vl-catch-all-apply 'vlax-get-property (list collection 'Item key)))
  (if (vl-catch-all-error-p result)
    nil
    (urb:excel-variant-value result))
)

(defun urb:excel-fail (message)
  (setq *urb-excel-last-error*
    (urb:safe-string message "Error de Excel sin descripcion."))
  nil
)

(defun urb:excel-variant-value (value / result next guard)
  ;; Value2 puede devolver un VARIANT vacio en vez de nil. Normalizarlo
  ;; evita confundir una hoja nueva con una hoja que ya contiene datos.
  ;; Algunas propiedades de Excel tambien envuelven objetos COM en uno o
  ;; mas VARIANT; se desenvuelven hasta obtener el valor u objeto real.
  (setq result value guard 0)
  (while (and (= (type result) 'VARIANT) (< guard 8))
    (setq next
      (vl-catch-all-apply 'vlax-variant-value (list result)))
    (if (vl-catch-all-error-p next)
      (setq result nil guard 8)
      (setq result next guard (1+ guard))))
  result
)

(defun urb:excel-save-as-xlsx (workbook filename / empty windows-path)
  ;; Excel expone Workbook.SaveAs con doce parametros. Al invocarlo mediante
  ;; IDispatch desde AutoLISP algunas versiones de Office no completan los
  ;; opcionales y responden "too few actual parameters". Enviar los doce
  ;; conserva el formato XLSX (51) y aplica la configuracion local del Excel.
  (setq empty (vlax-make-variant)
        windows-path (vl-string-translate "/" "\\" filename))
  (vl-catch-all-apply 'vlax-invoke-method
    (list workbook 'SaveAs windows-path 51
      empty empty :vlax-false :vlax-false
      1 empty :vlax-false empty empty :vlax-true))
)

(defun urb:excel-sheet-blank-p (sheet / used count value blank)
  (setq *urb-excel-stage* "verificacion de hoja vacia")
  (setq used (vlax-get-property sheet 'UsedRange)
        count (vlax-get-property used 'Count)
        value
          (urb:excel-variant-value
            (vlax-get-property used 'Value2))
        blank
          (and (= count 1)
            (or (null value) (and (= (type value) 'STR) (= value "")))))
  (urb:excel-release used)
  blank
)

(defun urb:excel-find-table
  (sheets table-name / count index sheet tables candidate found)
  (setq count (vlax-get-property sheets 'Count)
        index 1)
  (while (and (<= index count) (null found))
    (setq sheet (urb:excel-item sheets index))
    (if sheet
      (progn
        (setq tables
                (urb:excel-variant-value
                  (vlax-get-property sheet 'ListObjects))
              candidate (urb:excel-item tables table-name))
        (urb:excel-release tables)
        (if candidate
          (setq found (list candidate sheet))
          (urb:excel-release sheet))))
    (setq index (1+ index)))
  found
)

(defun urb:excel-get-or-create-sheet
  (sheets name / sheet result created)
  (setq sheet (urb:excel-item sheets name))
  (if sheet
    (list sheet nil)
    (progn
      (setq result
        (vl-catch-all-apply 'vlax-invoke-method (list sheets 'Add)))
      (if (vl-catch-all-error-p result)
        nil
        (progn
          (setq sheet (urb:excel-variant-value result) created T)
          (vlax-put-property sheet 'Name name)
          (list sheet created)))))
)

(defun urb:excel-table-column (table header / columns column)
  (setq columns
          (urb:excel-variant-value
            (vlax-get-property table 'ListColumns))
        column (urb:excel-item columns header))
  (urb:excel-release columns)
  column
)

(defun urb:excel-ensure-table-columns
  (table headers / columns header column result ok)
  (setq columns
          (urb:excel-variant-value
            (vlax-get-property table 'ListColumns))
        ok T)
  (while (and headers ok)
    (setq header (car headers)
          column (urb:excel-item columns header))
    (if (null column)
      (progn
        (setq result
          (vl-catch-all-apply 'vlax-invoke-method (list columns 'Add)))
        (if (vl-catch-all-error-p result)
          (progn
            (urb:excel-fail
              (strcat "No fue posible agregar la columna " header ": "
                (vl-catch-all-error-message result)))
            (setq ok nil))
          (progn
            (setq column (urb:excel-variant-value result))
            (vlax-put-property column 'Name header)))))
    (urb:excel-release column)
    (setq headers (cdr headers)))
  (urb:excel-release columns)
  ok
)

(defun urb:excel-create-general-table
  (sheet matrix / row-count col-count address target tables result table)
  (setq *urb-excel-stage* "preparacion del rango de la tabla general")
  (setq row-count (length matrix)
        col-count (length (car matrix))
        address
          (strcat "A1:" (urb:excel-column-name col-count) (itoa row-count))
        target
          (urb:excel-variant-value
            (vlax-get-property sheet 'Range address)))
  (vlax-put-property target 'Value2 (urb:excel-matrix-variant matrix))
  (setq *urb-excel-stage* "creacion del objeto tabla general")
  (setq tables
          (urb:excel-variant-value
            (vlax-get-property sheet 'ListObjects))
        result
          (vl-catch-all-apply 'vlax-invoke-method
            (list tables 'Add 1 target :vlax-false 1)))
  (if (vl-catch-all-error-p result)
    (progn
      (urb:excel-release tables)
      (urb:excel-release target)
      (urb:excel-fail
        (strcat "No fue posible crear la tabla general: "
          (vl-catch-all-error-message result))))
    (progn
      (setq table (urb:excel-variant-value result))
      (setq *urb-excel-stage* "asignacion del nombre de la tabla general")
      (vlax-put-property table 'Name *urb-excel-general-table*)
      (vl-catch-all-apply 'vlax-put-property
        (list table 'TableStyle "TableStyleMedium2"))
      (urb:excel-release tables)
      (urb:excel-release target)
      table))
)

(defun urb:excel-format-quantity-column (table / header column data-range)
  (foreach header '("CANTIDAD" "CANTIDAD_ORIGINAL")
    (setq column (urb:excel-table-column table header))
    (if column
      (progn
        (setq data-range
          (vl-catch-all-apply 'vlax-get-property
            (list column 'DataBodyRange)))
        (if (not (vl-catch-all-error-p data-range))
          (progn
            (setq data-range (urb:excel-variant-value data-range))
            (vlax-put-property data-range 'NumberFormatLocal "#.##0,00")
            (urb:excel-release data-range)))
        (urb:excel-release column))))
  nil
)

(defun urb:excel-format-date-column (table / column data-range)
  (setq column (urb:excel-table-column table "FECHA_ACTUALIZACION"))
  (if column
    (progn
      (setq data-range
        (vl-catch-all-apply 'vlax-get-property
          (list column 'DataBodyRange)))
      (if (not (vl-catch-all-error-p data-range))
        (progn
          (setq data-range (urb:excel-variant-value data-range))
          ;; NumberFormat usa codigos invariantes de Excel y evita que una
          ;; fecha colombiana termine mostrandose mes/dia en otro equipo.
          (vlax-put-property data-range 'NumberFormat "dd/mm/yyyy hh:mm:ss")
          (urb:excel-release data-range)))
      (urb:excel-release column)))
  nil
)

(defun urb:list-index-ci (value values / index found)
  (setq index 0)
  (while (and values (null found))
    (if (urb:string-equal-p value (car values))
      (setq found index)
      (setq index (1+ index)
            values (cdr values))))
  found
)

(defun urb:list-set-nth (index value values / cursor result item)
  (setq cursor 0 result nil)
  (foreach item values
    (setq result
      (cons (if (= cursor index) value item) result)
      cursor (1+ cursor)))
  (reverse result)
)

(defun urb:excel-cell-value (value / current next)
  (setq current value)
  (while (= (type current) 'VARIANT)
    (setq next (vl-catch-all-apply 'vlax-variant-value (list current)))
    (if (vl-catch-all-error-p next)
      (setq current nil)
      (setq current next)))
  (if (= (type current) 'SAFEARRAY)
    (setq current (vlax-safearray->list current)))
  (if (= (type current) 'LIST)
    (if current (urb:excel-cell-value (car current)) "")
    current)
)

(defun urb:excel-column-property-values
  (table header property / column range raw data result item)
  (setq column (urb:excel-table-column table header))
  (if column
    (progn
      (setq range
        (vl-catch-all-apply 'vlax-get-property
          (list column 'DataBodyRange)))
      (if (not (vl-catch-all-error-p range))
        (progn
          (setq range (urb:excel-variant-value range)
                raw
                  (vl-catch-all-apply 'vlax-get-property
                    (list range property)))
          (if (not (vl-catch-all-error-p raw))
            (progn
              (setq data (urb:excel-variant-value raw))
              (if (= (type data) 'SAFEARRAY)
                (setq data (vlax-safearray->list data)))
              (if (= (type data) 'LIST)
                (foreach item data
                  (setq result
                    (cons (urb:excel-cell-value item) result)))
                (setq result (list (urb:excel-cell-value data)))))
            (setq result nil))
          (urb:excel-release range)))
      (urb:excel-release column)))
  (reverse result)
)

(defun urb:excel-table-column-names
  (table / columns count index column name result)
  (setq columns
    (urb:excel-variant-value
      (vlax-get-property table 'ListColumns))
    count (vlax-get-property columns 'Count)
    index 1)
  (repeat count
    (setq column (urb:excel-item columns index))
    (if column
      (progn
        (setq name (urb:safe-string (vla-get-Name column) ""))
        (if (/= name "") (setq result (cons name result)))
        (urb:excel-release column)))
    (setq index (1+ index)))
  (urb:excel-release columns)
  (reverse result)
)

(defun urb:excel-table-required-rows
  (table headers / columns values max-count index row rows)
  (setq max-count 0 columns nil)
  (foreach header headers
    (setq values
      (urb:excel-column-property-values table header 'Value2))
    (setq columns (append columns (list values))
          max-count (max max-count (length values))))
  (setq index 0)
  (repeat max-count
    (setq row nil)
    (foreach values columns
      (setq row
        (append row
          (list (if (> (length values) index) (nth index values) "")))))
    (setq rows (append rows (list row))
          index (1+ index)))
  rows
)

(defun urb:excel-formula-template (values / found value)
  (foreach value values
    (if (and (null found) (= (type value) 'STR)
             (> (strlen value) 0) (= (substr value 1 1) "="))
      (setq found value)))
  found
)

(defun urb:excel-capture-extra-columns
  (table required-headers / ids required-rows names name values mapping index
   template result id row)
  (setq ids
    (urb:excel-column-property-values table "ID_REGISTRO" 'Value2)
    required-rows (urb:excel-table-required-rows table required-headers)
    names (urb:excel-table-column-names table))
  (foreach name names
    (if (null (urb:list-index-ci name required-headers))
      (progn
        (setq values
          (urb:excel-column-property-values table name 'Formula)
          mapping nil
          index 0)
        (foreach id ids
          (setq row
            (if (> (length required-rows) index)
              (nth index required-rows) nil))
          (if (and (/= (urb:safe-string id "") "")
                   (> (length values) index))
            (setq mapping
              (cons
                (cons (strcat "ID:" (urb:safe-string id ""))
                  (nth index values))
                mapping)))
          (if (and row (> (length values) index))
            (setq mapping
              (cons
                (cons
                  (strcat "SIG:"
                    (urb:excel-row-signature row required-headers))
                  (nth index values))
                mapping)))
          (setq index (1+ index)))
        (setq template (urb:excel-formula-template values)
              result (cons (list name mapping template) result)))))
  (reverse result)
)

(defun urb:excel-row-signature (row headers / fields index result)
  (setq fields
    '("TIPO_REGISTRO" "RUTA_DWG" "CAPITULO" "SISTEMA" "ELEMENTO"
      "ESPECIFICACION" "ETAPA" "SUBETAPA" "UNIDAD" "HANDLE")
    result "")
  (foreach field fields
    (setq index (urb:list-index-ci field headers)
          result
            (strcat result "|"
              (strcase
                (urb:safe-string
                  (if index (nth index row) "") "")))))
  result
)

(defun urb:excel-merge-master-matrix
  (table matrix / headers new-rows old-rows id-index type-index dwg-index
   path-index observation-index action-index quantity-index original-index
   include-index status-index schema-index current-dwg current-path
   current-map preserved row row-id same-drawing found adjusted value approved)
  (setq headers (car matrix)
        new-rows (cdr matrix)
        old-rows (urb:excel-table-required-rows table headers)
        id-index (urb:list-index-ci "ID_REGISTRO" headers)
        type-index (urb:list-index-ci "TIPO_REGISTRO" headers)
        dwg-index (urb:list-index-ci "ID_DWG" headers)
        path-index (urb:list-index-ci "RUTA_DWG" headers)
        observation-index (urb:list-index-ci "OBSERVACION" headers)
        action-index (urb:list-index-ci "ACCION" headers)
        quantity-index (urb:list-index-ci "CANTIDAD" headers)
        original-index (urb:list-index-ci "CANTIDAD_ORIGINAL" headers)
        include-index (urb:list-index-ci "INCLUIR_CANTIDAD" headers)
        status-index (urb:list-index-ci "ESTADO" headers)
        schema-index (urb:list-index-ci "VERSION_ESQUEMA" headers)
        current-dwg
          (urb:safe-string
            (if (and new-rows dwg-index) (nth dwg-index (car new-rows)) "") "")
        current-path
          (urb:safe-string
            (if (and new-rows path-index) (nth path-index (car new-rows)) "") ""))
  (foreach row old-rows
    (setq same-drawing
      (if (and dwg-index
               (/= current-dwg "")
               (/= (urb:safe-string (nth dwg-index row) "") ""))
        (urb:string-equal-p current-dwg (nth dwg-index row))
        (and path-index
             (urb:string-equal-p current-path (nth path-index row)))))
    (if same-drawing
      (progn
        (setq row-id (urb:safe-string (nth id-index row) ""))
        (if (/= row-id "")
          (setq current-map
            (cons (cons (strcat "ID:" row-id) row) current-map)))
        (setq current-map
          (cons
            (cons
              (strcat "SIG:" (urb:excel-row-signature row headers))
              row)
            current-map)))
      (progn
        ;; Los registros de otros DWG se conservan, pero al migrar una tabla
        ;; antigua también se neutralizan cantidades con estado no aprobado.
        (setq adjusted row)
        (if (urb:string-equal-p (nth type-index row) "CANTIDAD")
          (progn
            (setq value (urb:q-number (nth quantity-index row))
                  approved
                    (urb:q-approved-status-p (nth status-index row))
                  adjusted
                    (urb:list-set-nth original-index
                      (if (> (abs (urb:q-number (nth original-index row))) 1e-12)
                        (urb:q-number (nth original-index row))
                        value)
                      adjusted)
                  adjusted
                    (urb:list-set-nth include-index
                      (if approved "SI" "NO") adjusted)
                  adjusted
                    (urb:list-set-nth quantity-index
                      (if approved value 0.0) adjusted)))
          (setq adjusted
            (urb:list-set-nth include-index "NO"
              (urb:list-set-nth quantity-index 0.0 adjusted))))
        (setq adjusted
          (urb:list-set-nth schema-index *urb-excel-table-schema* adjusted)
          preserved (append preserved (list adjusted))))))
  (foreach row new-rows
    ;; or de AutoLISP devuelve T, no el valor: (cdr found) tronaba
    (setq row-id (urb:safe-string (nth id-index row) "")
          found (assoc (strcat "ID:" row-id) current-map)
          adjusted row)
    (if (null found)
      (setq found
        (assoc
          (strcat "SIG:" (urb:excel-row-signature row headers))
          current-map)))
    (if (and found
             (urb:string-equal-p (nth type-index row) "CANTIDAD"))
      (progn
        (setq value (nth observation-index (cdr found)))
        (if (/= (urb:safe-string value "") "")
          (setq adjusted
            (urb:list-set-nth observation-index value adjusted)))
        (setq value (nth action-index (cdr found)))
        (if (/= (urb:safe-string value "") "")
          (setq adjusted
            (urb:list-set-nth action-index value adjusted)))))
    (setq preserved (append preserved (list adjusted))))
  (cons headers preserved)
)

(defun urb:excel-restore-extra-columns
  (table matrix extra-state / headers rows id-index state name mapping
   template values id found column range result row)
  (setq headers (car matrix)
        rows (cdr matrix)
        id-index (urb:list-index-ci "ID_REGISTRO" headers))
  (foreach state extra-state
    (setq name (nth 0 state)
          mapping (nth 1 state)
          template (nth 2 state)
          values nil)
    (foreach row rows
      ;; or de AutoLISP devuelve T, no el valor: (cdr found) tronaba
      (setq id (urb:safe-string (nth id-index row) "")
            found (assoc (strcat "ID:" id) mapping))
      (if (null found)
        (setq found
          (assoc
            (strcat "SIG:" (urb:excel-row-signature row headers))
            mapping)))
      (setq values
        (append values
          (list
            (list
              (cond
                (found (cdr found))
                (template template)
                (T "")))))))
    (setq column (urb:excel-table-column table name))
    (if column
      (progn
        (setq range
          (vl-catch-all-apply 'vlax-get-property
            (list column 'DataBodyRange)))
        (if (not (vl-catch-all-error-p range))
          (progn
            (setq range (urb:excel-variant-value range)
                  result
                    (vl-catch-all-apply 'vlax-put-property
                      (list range 'Formula
                        (urb:excel-matrix-variant values))))
            (urb:excel-release range)))
        (urb:excel-release column))))
  nil
)

(defun urb:excel-update-general-table
  (sheet table matrix
   / headers rows new-data-count table-range start-row start-column
    old-data-range old-data-rows old-data-count table-columns column-count header column
    data-range new-address new-range tail-address tail-range index values row
    extra-state)
  (setq headers (car matrix))
  (if (= (length (cdr matrix)) 0)
    (urb:excel-fail
      "La tabla general no contiene registros para actualizar.")
    (if (not (urb:excel-ensure-table-columns table headers))
      nil
      (progn
  (setq extra-state (urb:excel-capture-extra-columns table headers)
        matrix (urb:excel-merge-master-matrix table matrix)
        headers (car matrix)
        rows (cdr matrix)
        new-data-count (length rows))
  (setq table-range
          (urb:excel-variant-value
            (vlax-get-property table 'Range))
        start-row (vlax-get-property table-range 'Row)
        start-column (vlax-get-property table-range 'Column)
        table-columns
          (urb:excel-variant-value
            (vlax-get-property table-range 'Columns))
        column-count (vlax-get-property table-columns 'Count))
  (setq old-data-range
    (vl-catch-all-apply 'vlax-get-property (list table 'DataBodyRange)))
  (if (or (vl-catch-all-error-p old-data-range) (null old-data-range))
    (setq old-data-count 0)
    (progn
      (setq old-data-range (urb:excel-variant-value old-data-range)
            old-data-rows
              (urb:excel-variant-value
                (vlax-get-property old-data-range 'Rows))
            old-data-count (vlax-get-property old-data-rows 'Count))
      (urb:excel-release old-data-rows)
      (urb:excel-release old-data-range)))
  (urb:excel-release table-columns)
  (foreach header headers
    (setq column (urb:excel-table-column table header))
    (if column
      (progn
        (setq data-range
          (vl-catch-all-apply 'vlax-get-property
            (list column 'DataBodyRange)))
        (if (not (vl-catch-all-error-p data-range))
          (progn
            (setq data-range (urb:excel-variant-value data-range))
            (vl-catch-all-apply 'vlax-invoke-method
              (list data-range 'ClearContents))
            (urb:excel-release data-range)))
        (urb:excel-release column))))
  (setq new-address
    (strcat
      (urb:excel-column-name start-column) (itoa start-row) ":"
      (urb:excel-column-name (+ start-column column-count -1))
      (itoa (+ start-row new-data-count)))
    new-range
      (urb:excel-variant-value
        (vlax-get-property sheet 'Range new-address)))
  (vlax-invoke-method table 'Resize new-range)
  (if (< new-data-count old-data-count)
    (progn
      (setq tail-address
        (strcat
          (urb:excel-column-name start-column)
          (itoa (+ start-row new-data-count 1)) ":"
          (urb:excel-column-name (+ start-column column-count -1))
          (itoa (+ start-row old-data-count)))
        tail-range
          (urb:excel-variant-value
            (vlax-get-property sheet 'Range tail-address)))
      (vl-catch-all-apply 'vlax-invoke-method
        (list tail-range 'ClearContents))
      (urb:excel-release tail-range)))
  (setq index 0)
  (foreach header headers
    (setq values nil)
    (foreach row rows
      (setq values (cons (list (nth index row)) values)))
    (setq values (reverse values)
          column (urb:excel-table-column table header))
    (if column
      (progn
        (setq data-range
          (urb:excel-variant-value
            (vlax-get-property column 'DataBodyRange)))
        (vlax-put-property data-range 'Value2
          (urb:excel-matrix-variant values))
        (urb:excel-release data-range)
        (urb:excel-release column)))
    (setq index (1+ index)))
  (urb:excel-format-quantity-column table)
  (urb:excel-format-date-column table)
  (urb:excel-restore-extra-columns table matrix extra-state)
  (urb:excel-release new-range)
  (urb:excel-release table-range)
  T
      ))
  )
)

(defun urb:excel-format-new-general-table
  (application sheet table
   / table-range header columns column index count width window header-name
   column-range data-range table-rows)
  (setq *urb-excel-stage* "formato de la tabla general")
  (setq table-range
          (urb:excel-variant-value
            (vlax-get-property table 'Range))
        header
          (urb:excel-variant-value
            (vlax-get-property table 'HeaderRowRange))
        columns
          (urb:excel-variant-value
            (vlax-get-property table-range 'Columns)))
  (vlax-put-property header 'WrapText :vlax-true)
  (vlax-put-property header 'HorizontalAlignment -4108)
  (vlax-put-property header 'VerticalAlignment -4108)
  (vlax-put-property header 'RowHeight 32.0)
  (vl-catch-all-apply 'vlax-invoke-method (list columns 'AutoFit))
  (setq count (vlax-get-property columns 'Count)
        index 1)
  (repeat count
    (setq column (urb:excel-item columns index))
    (if column
      (progn
        (setq width
          (urb:excel-variant-value
            (vlax-get-property column 'ColumnWidth)))
        (if (> width 42.0) (vlax-put-property column 'ColumnWidth 42.0))
        (if (< width 9.0) (vlax-put-property column 'ColumnWidth 9.0))
        (urb:excel-release column)))
    (setq index (1+ index)))
  (foreach header-name '("ID_REGISTRO" "OBSERVACION" "ACCION")
    (setq column (urb:excel-table-column table header-name))
    (if column
      (progn
        (setq column-range
          (urb:excel-variant-value
            (vlax-get-property column 'Range)))
        (vlax-put-property column-range 'ColumnWidth 42.0)
        (if (member header-name '("OBSERVACION" "ACCION"))
          (progn
            (setq data-range
              (urb:excel-variant-value
                (vlax-get-property column 'DataBodyRange)))
            (vlax-put-property data-range 'WrapText :vlax-true)
            (urb:excel-release data-range)))
        (urb:excel-release column-range)
        (urb:excel-release column))))
  (setq table-rows
    (urb:excel-variant-value
      (vlax-get-property table-range 'Rows)))
  (vl-catch-all-apply 'vlax-invoke-method (list table-rows 'AutoFit))
  (urb:excel-release table-rows)
  (urb:excel-format-quantity-column table)
  (urb:excel-format-date-column table)
  (vlax-invoke-method sheet 'Activate)
  (setq window
    (vl-catch-all-apply 'vlax-get-property (list application 'ActiveWindow)))
  (if (not (vl-catch-all-error-p window))
    (progn
      (setq window (urb:excel-variant-value window))
      (vlax-put-property window 'SplitRow 1)
      (vlax-put-property window 'FreezePanes :vlax-true)
      (vlax-put-property window 'DisplayGridlines :vlax-false)
      (urb:excel-release window)))
  (urb:excel-release columns)
  (urb:excel-release header)
  (urb:excel-release table-range)
  nil
)

(defun urb:excel-prepare-general-table
  (application sheets matrix / found table sheet sheet-info created updated)
  (setq *urb-excel-stage* "busqueda de tabla general existente")
  (setq found (urb:excel-find-table sheets *urb-excel-general-table*))
  (if found
    (progn
      (setq table (car found)
            sheet (cadr found)
            updated (urb:excel-update-general-table sheet table matrix))
      (if updated
        (list table sheet nil)
        (progn
          (urb:excel-release table)
          (urb:excel-release sheet)
          nil)))
    (progn
      (setq *urb-excel-stage* "obtencion de la hoja de cantidades")
      (setq sheet-info
        (urb:excel-get-or-create-sheet sheets *urb-excel-general-sheet*))
      (cond
        ((null sheet-info)
          (urb:excel-fail
            "No fue posible obtener la hoja CANTIDADES_URBANISMO."))
        (T
          (setq sheet (car sheet-info)
                created (cadr sheet-info))
          (setq *urb-excel-stage* "validacion de la hoja de cantidades")
          (if (and (not created) (not (urb:excel-sheet-blank-p sheet)))
            (progn
              (urb:excel-fail
                (strcat "La hoja " *urb-excel-general-sheet*
                  " ya contiene datos pero no la tabla "
                  *urb-excel-general-table*
                  ". Cambie el nombre de esa hoja o dejela vacia."))
              (urb:excel-release sheet)
              nil)
            (progn
              (setq *urb-excel-stage* "creacion de la tabla general")
              (setq table (urb:excel-create-general-table sheet matrix))
              (if table
                (progn
                  (urb:excel-format-new-general-table
                    application sheet table)
                  (list table sheet created))
                (progn
                  (urb:excel-release sheet)
                  nil))))))))
)

(defun urb:excel-delete-extra-new-sheets (sheets / count index sheet)
  (setq count (vlax-get-property sheets 'Count)
        index count)
  (while (> index 1)
    (setq sheet (urb:excel-item sheets index))
    (if sheet
      (progn
        (vlax-invoke-method sheet 'Delete)
        (urb:excel-release sheet)))
    (setq index (1- index)))
  nil
)

(defun urb:excel-backup-path (filename / directory base extension name)
  (setq directory (vl-filename-directory filename)
        base (vl-filename-base filename)
        extension (urb:safe-string (vl-filename-extension filename) ".xlsx")
        name
          (strcat base "_backup_" (urb:excel-file-timestamp) "_"
            (itoa (getvar "MILLISECS")) extension))
  (if directory (urb:join-path directory name) name)
)

(defun urb:excel-create-backup (filename / backup copied)
  (setq backup (urb:excel-backup-path filename)
        copied (vl-catch-all-apply 'vl-file-copy (list filename backup)))
  (if (or (vl-catch-all-error-p copied) (null copied)) nil backup)
)

(defun urb:excel-linked-path (/ value)
  (setq value (urb:safe-string (urb:config-read *urb-excel-link-key*) ""))
  (vl-string-trim " \t\r\n" value)
)

(defun urb:excel-save-linked-path (filename)
  (urb:config-write *urb-excel-link-key* filename)
)

(defun urb:excel-supported-master-p (filename / extension)
  (setq extension
    (strcase (urb:safe-string (vl-filename-extension filename) "")))
  (if (member extension '(".XLSX" ".XLSM")) T nil)
)

(defun urb:excel-calculation-ready-p (application / result state)
  (setq result
    (vl-catch-all-apply 'vlax-get-property
      (list application 'CalculationState)))
  (if (vl-catch-all-error-p result)
    nil
    (progn
      (setq state (urb:excel-variant-value result))
      (= state 0)))
)

(defun urb:write-general-excel
  (filename linked
   / collected records controls matrix backup app-result application
   workbooks workbook-result workbook sheets first-sheet prepared table sheet
   read-only refresh-result wait-result refresh-ok refresh-message save-result
   *error*)
  (defun *error* (message)
    (if workbook
      (vl-catch-all-apply 'vlax-invoke-method
        (list workbook 'Close :vlax-false)))
    (if application
      (vl-catch-all-apply 'vlax-invoke-method (list application 'Quit)))
    (urb:excel-release table)
    (urb:excel-release sheet)
    (urb:excel-release sheets)
    (urb:excel-release workbook)
    (urb:excel-release workbooks)
    (urb:excel-release application)
    (if (and message
             (not (member message '("Function cancelled" "quit / exit abort"))))
      (prompt (strcat "\nERROR AL ACTUALIZAR EXCEL: " message)))
    nil)
  (setq *urb-excel-last-error* nil
        *urb-excel-stage* "recoleccion de cantidades"
        collected (urb:q-collect-all)
        records (nth 0 collected)
        controls (nth 1 collected)
        matrix (urb:q-general-matrix records controls))
  (if records (urb:q-preflight-report records controls))
  (cond
    ((null records)
      (prompt "\nNo se encontraron cantidades cuantificables en el dibujo.")
      nil)
    ((and linked (not (findfile filename)))
      (prompt (strcat "\nNo se encontro el Excel vinculado: " filename))
      nil)
    ((and linked (null (setq backup (urb:excel-create-backup filename))))
      (prompt
        "\nNo fue posible crear el respaldo. El Excel no fue modificado.")
      nil)
    (T
      (setq app-result
        (vl-catch-all-apply 'vlax-create-object (list "Excel.Application")))
      (if (vl-catch-all-error-p app-result)
        (progn
          (prompt
            (strcat "\nNo fue posible iniciar Microsoft Excel: "
              (vl-catch-all-error-message app-result)))
          nil)
        (progn
          (setq application app-result)
          (vlax-put-property application 'Visible :vlax-false)
          (vlax-put-property application 'DisplayAlerts :vlax-false)
          (vlax-put-property application 'ScreenUpdating :vlax-false)
          (vlax-put-property application 'DecimalSeparator ",")
          (vlax-put-property application 'ThousandsSeparator ".")
          (vlax-put-property application 'UseSystemSeparators :vlax-false)
          (setq workbooks (vlax-get-property application 'Workbooks)
                workbook-result
                  (if linked
                    (vl-catch-all-apply 'vlax-invoke-method
                      (list workbooks 'Open filename))
                    (vl-catch-all-apply 'vlax-invoke-method
                      (list workbooks 'Add))))
          (if (vl-catch-all-error-p workbook-result)
            (*error* (vl-catch-all-error-message workbook-result))
            (progn
              (setq workbook workbook-result
                    read-only (vlax-get-property workbook 'ReadOnly))
              (if (and linked (= read-only :vlax-true))
                (*error*
                  "El Excel esta abierto o bloqueado y solo se pudo abrir en modo lectura. Cierrelo y vuelva a intentar.")
                (progn
                  (setq sheets (vlax-get-property workbook 'Worksheets))
                  (if (not linked)
                    (progn
                      (urb:excel-delete-extra-new-sheets sheets)
                      (setq first-sheet (urb:excel-item sheets 1))
                      (vlax-put-property first-sheet 'Name
                        *urb-excel-general-sheet*)
                      (urb:excel-release first-sheet)))
                  (setq *urb-excel-stage* "preparacion de la tabla general")
                  (setq prepared
                    (urb:excel-prepare-general-table
                      application sheets matrix))
                  (if (null prepared)
                    (*error*
                      (urb:safe-string *urb-excel-last-error*
                        "No fue posible preparar la tabla general."))
                    (progn
                  (setq table (nth 0 prepared)
                        sheet (nth 1 prepared))
                  (vlax-invoke-method sheet 'Activate)
                  (setq refresh-ok T refresh-message "")
                  (if linked
                    (progn
                      (setq refresh-result
                        (vl-catch-all-apply 'vlax-invoke-method
                          (list workbook 'RefreshAll)))
                      (if (vl-catch-all-error-p refresh-result)
                        (setq refresh-ok nil
                              refresh-message
                                (vl-catch-all-error-message refresh-result))
                        (progn
                          (setq wait-result
                            (vl-catch-all-apply 'vlax-invoke-method
                              (list application 'CalculateUntilAsyncQueriesDone)))
                           (if (vl-catch-all-error-p wait-result)
                             (setq refresh-ok nil
                                   refresh-message
                                     (vl-catch-all-error-message wait-result)))
                           (vl-catch-all-apply 'vlax-invoke-method
                             (list application 'CalculateFull))
                           (if (and refresh-ok
                                    (not (urb:excel-calculation-ready-p application)))
                             (setq refresh-ok nil
                                   refresh-message
                                     "Excel no confirmo el estado de calculo finalizado."))))))
                  (setq *urb-excel-stage* "guardado del libro Excel")
                  (setq save-result
                    (if linked
                      (vl-catch-all-apply 'vlax-invoke-method
                        (list workbook 'Save))
                      (urb:excel-save-as-xlsx workbook filename)))
                  (if (vl-catch-all-error-p save-result)
                    (*error* (vl-catch-all-error-message save-result))
                    (progn
                      (vlax-put-property application 'ScreenUpdating :vlax-true)
                      (vlax-put-property application 'DisplayAlerts :vlax-true)
                      (vlax-put-property application 'Visible :vlax-true)
                      (urb:excel-release table)
                      (urb:excel-release sheet)
                      (urb:excel-release sheets)
                      (urb:excel-release workbook)
                      (urb:excel-release workbooks)
                      (urb:excel-release application)
                      (prompt
                        (strcat
                          "\nTabla " *urb-excel-general-table* " actualizada: "
                          filename
                          " | Cantidades: " (itoa (length records))
                          " | Controles: " (itoa (length controls))
                          (if linked (strcat " | Respaldo: " backup) "")
                          (if refresh-ok
                            " | Consultas actualizadas."
                            (strcat
                              " | ADVERTENCIA: datos guardados, pero Excel no confirmo la actualizacion de consultas: "
                              refresh-message))))
                      T)))))))))))))

(defun urb:export-quantities-excel (filename)
  (urb:write-general-excel filename nil)
)

(defun urb:update-linked-quantities-excel (filename)
  (urb:write-general-excel filename T)
)

(setq *urb-excel-network-headers*
  '("GRUPO" "BLOQUE" "HANDLE" "CAPA" "X" "Y" "ETAPA" "SUBETAPA"
    "ID" "CODIGO" "RED" "TIPO_RED" "DESDE" "HASTA" "POZO_INI"
    "POZO_FIN" "TIPO_EXTREMO_INI" "TIPO_EXTREMO_FIN"
    "HANDLE_EXTREMO_INI" "HANDLE_EXTREMO_FIN" "DIAMETRO" "MATERIAL"
    "LONGITUD" "LONGITUD_2D" "LONGITUD_3D" "MODO_LONGITUD"
    "PENDIENTE" "PENDIENTE_CALCULADA" "COTA_TN_INI" "COTA_TN_FIN"
    "SUPERFICIE_TN" "ESTADO_COTA_TN"
    "COTA_CLAVE_INI" "COTA_CLAVE_FIN" "PROFUNDIDAD_INI"
    "PROFUNDIDAD_FIN" "PROFUNDIDAD_MEDIA" "CONDUCTOR" "DUCTOS" "LIBRES"
    "DIAM_DUCTO" "MATERIAL_DUCTO" "TIPO_CAJA" "TIPO_LUMINARIA"
    "FUENTE_LED" "CIRCUITO" "CIRCUITO_AP" "PROFUNDIDAD" "ANCHO_ZANJA"
    "ESPESOR_CAMA" "ANCHO_REPOSICION" "EXCAVACION_M3" "CAMA_M3"
    "VOLUMEN_ELEMENTO_M3" "RELLENO_M3" "TRITURADO_M3" "RECEBO_M3"
    "ENTIBADO_LE3_M2" "ENTIBADO_GT3_M2" "SOBRANTE_M3" "REPOSICION_M2"
    "METODO_CANTIDADES" "CONTROL_ESTADO" "CONTROL_MENSAJES"
    "TIPO_ACCESORIO" "SERIE" "CD" "PF"))

(defun urb:excel-export-command (/ filename result)
  (if (urb:confirm-meter-units)
    (progn
      (setq filename
        (getfiled "Guardar todas las cantidades en Excel"
          (strcat (getvar "DWGPREFIX") "cantidades_urbanismo.xlsx")
          "xlsx" 1))
      (if filename
        (progn
          (if (not (urb:ends-with (strcase filename) ".XLSX"))
            (setq filename (strcat filename ".xlsx")))
          (setq result
            (vl-catch-all-apply 'urb:export-quantities-excel (list filename)))
          (if (vl-catch-all-error-p result)
            (prompt
              (strcat "\nNo se completo la exportacion: "
                (vl-catch-all-error-message result)
                " | etapa: "
                (urb:safe-string *urb-excel-stage* "desconocida")))))
        (prompt "\nExportacion cancelada.")))
    (prompt "\nExportacion a Excel cancelada: confirme primero las unidades del dibujo."))
  (princ)
)

(defun urb:excel-link-command (/ current filename)
  (setq current (urb:excel-linked-path)
        filename
          (getfiled "Seleccionar Excel maestro existente"
            (if (> (strlen current) 0) current (getvar "DWGPREFIX"))
            "" 0))
  (if filename
    (if (urb:excel-supported-master-p filename)
      (progn
        (urb:excel-save-linked-path filename)
        (prompt
          (strcat "\nExcel maestro vinculado al dibujo: " filename
            "\nGuarde el DWG para conservar el vinculo."))
        (urb:excel-update-linked-command))
      (prompt
        "\nArchivo no compatible. Seleccione un libro .xlsx o .xlsm."))
    (prompt "\nVinculacion cancelada."))
  (princ)
)

(defun urb:excel-update-linked-command (/ filename result)
  (setq filename (urb:excel-linked-path))
  (cond
    ((= filename "")
      (prompt "\nEste dibujo aun no tiene un Excel maestro vinculado.")
      (urb:excel-link-command))
    ((not (findfile filename))
      (prompt
        (strcat "\nNo se encontro el Excel vinculado: " filename
          "\nUse URBANISMO > Cantidades > Vincular o cambiar Excel maestro para seleccionar su nueva ubicacion.")))
    ((not (urb:excel-supported-master-p filename))
      (prompt
        "\nEl vinculo no apunta a un libro .xlsx o .xlsm. Cambielo desde URBANISMO > Cantidades."))
    ((urb:confirm-meter-units)
      (setq result
        (vl-catch-all-apply 'urb:update-linked-quantities-excel
          (list filename)))
      (if (vl-catch-all-error-p result)
        (prompt
          (strcat "\nNo se completo la actualizacion: "
            (vl-catch-all-error-message result)))))
    (T
      (prompt
        "\nActualizacion de Excel cancelada: confirme primero las unidades del dibujo.")))
  (princ)
)

(defun urb:excel-unlink-command (/ filename response)
  (setq filename (urb:excel-linked-path))
  (if (= filename "")
    (prompt "\nEste dibujo no tiene un Excel maestro vinculado.")
    (progn
      (initget "Si No")
      (setq response
        (getkword
          (strcat "\nEliminar el vinculo con " filename "? [Si/No] <No>: ")))
      (if (= response "Si")
        (progn
          (urb:excel-save-linked-path "")
          (prompt "\nVinculo eliminado. Guarde el DWG para conservar el cambio."))
        (prompt "\nEl vinculo se conservo."))))
  (princ)
)

;; ============================================================
;; EXPORTACION AL PRESUPUESTO (PPTOEXPORTAR) - 2026-08-17
;; Contrato del handoff urbanismo-externo.md (chat de Excel):
;; un solo comando que valida el libro por TM_MEMORIAS + firma de
;; encabezados, relee el vocabulario vivo de POR EJECUTAR, matchea
;; cada actividad CAD contra la descripcion VIGENTE (cascada
;; capitulo -> keywords -> UM con UNICIDAD obligatoria), escribe
;; DENTRO de TablaMemorias con reemplazo transaccional por DWG y
;; reporta huerfanas. La agregacion queda en los SUMIFS del libro.
;; El plugin jamas exporta precios ni totales.
;; ============================================================

(setq *urb-ppto-headers*
  '("RED" "CONCEPTO" "ESPECIFICACION" "ID" "DESDE" "HASTA"
    "ETAPA" "SUBETAPA" "UM" "CANTIDAD" "DWG" "HANDLE"))

;; RED (subarbol destino) -> nombre de capitulo del ppto (normalizado)
(setq *urb-ppto-red-capitulo*
  '(("VIA" . "via")
    ("ANDEN" . "andenes")
    ("CICLORRUTA" . "ciclorruta")
    ("RAMPA-PEATONAL" . "rampa peatonal")
    ("RAMPA-VEHICULAR" . "rampa vehicular")
    ("PASO-PEATONAL" . "paso peatonal seguro")
    ("ACUEDUCTO" . "red de acueducto")
    ("ALC-SANITARIO" . "red de alcantarillado sanitario")
    ("ALC-PLUVIAL" . "red de alcantarillado pluvial")
    ("RED-GAS" . "red de gas")
    ("ELECTRICA-MT" . "red de media tension")
    ("ELECTRICA-BT-AP" . "red de baja tension")
    ;; 5.7.14 (decision del usuario 2026-09-18: "senderos y andenes todo
    ;; lo que se dibuje se va redireccionar al mismo capitulo de andenes").
    ;; El capitulo "parques y zonas verdes" no existe en el libro y todo
    ;; sendero salia SIN MATCH.
    ("SENDERO" . "andenes")
    ;; 2026-09-11 (reporte del usuario: "la zona verde la dibuja pero no me
    ;; la esta trayendo al presupuesto"): la zona verde no tenia red ni
    ;; fuente de filas. Capitulo 2.2.7 ZONA VERDE de perfiles viales; en un
    ;; parque la zona marcada la redirige al capitulo del parque.
    ("ZONA-VERDE" . "zona verde")))

;; Capitulos ADICIONALES que tambien pertenecen a una red: presupuestos
;; que separan la misma disciplina en varios capitulos de nivel 3
;; (p.ej. alumbrado publico va en RED DE ALUMBRADO PUBLICO, no en
;; "red de baja tension"; la subterranizacion MT va en OBRAS ELECTRICAS).
(setq *urb-ppto-red-capitulo-alias*
  '(("ELECTRICA-MT" "obras electricas")
    ("ELECTRICA-BT-AP" "red de alumbrado publico")))

;; lista completa de capitulos (principal + alias) de una red
(defun urb:ppto-caps-de (red / base)
  (setq base (cdr (assoc red *urb-ppto-red-capitulo*)))
  (if base
    (cons base (cdr (assoc red *urb-ppto-red-capitulo-alias*)))
    nil))

(setq *urb-ppto-stopwords*
  '("de" "del" "la" "el" "los" "las" "y" "e" "o" "u" "a" "en"
    "con" "para" "por" "un" "una" "al" "incluye" "tipo"))

;; ---------- MOBILIARIO URBANO (2026-08-19, pedido del usuario) ----------
;; Bloques LIVIANOS por tipo (forma simple en planta, reutilizados entre
;; instancias) que se insertan con clics repetidos y se CUENTAN solos en
;; la exportacion (una fila UN por tipo+etapa+subetapa, capitulo ANDENES).
;; La actividad de cada tipo es el TEXTO EXACTO del presupuesto real
;; (match directo por igualdad; si renombran la actividad cae al score).
;; catalogo: (codigo etiqueta actividad-ppto forma ancho largo)
(setq *urb-mob-tipos*
  '(("CANECA" "Caneca doble M-121"
      "Suministro e instalación de dos canecas M-121" "CIRC" 0.50 0.50)
    ("BANCA-M30" "Banca en concreto M-30"
      "Suministro e instalación de banca en concreto con espaldar M-30"
      "RECT" 2.00 0.70)
    ("BANCA-L206" "Banca L=2,06m"
      "Suministro e instalación de banca L=2,06m (CIO106682)"
      "RECT" 2.06 0.60)
    ("PARADERO" "Paradero de buses M-10"
      "Suministro e instalación de paradero de buses Tipo M-10"
      "RECT" 3.00 1.50)
    ("PROTECTOR-ARBOL" "Protector de arbol M-91"
      "Suministro e instalación de protector de árbol de dos tubos Tipo M-91"
      "CIRC" 1.00 1.00)
    ("ARBOL" "Arbol"
      "Suministro e instalación de árbol" "ARBOL" 1.20 1.20)
    ("SENAL-SITP" "Senal paradero SITP SI-08"
      "Señal vertical Paradero SITP SI-08 / Plaqueta" "CIRC" 0.30 0.30)
    ;; el bolardo vive en los capitulos de RAMPA del ppto (verificado
    ;; 2026-08-20 contra el libro), no en ANDENES -- red propia (campo 7)
    ("BOLARDO" "Bolardo alto M-63"
      "Suministro e instalación de bolardo alto en hierro Tipo M-63"
      "CIRC" 0.25 0.25 "RAMPA-PEATONAL")
    ("CONT-RAICES" "Contenedor raices 2,0x1,2"
      "Suministro y construcción de contenedor de raíces (Dimensiones: 2,0x1,2m). Incluye tierra negra"
      "CONTEN" 2.00 1.20)
    ("CONT-A" "Contenedor raices Tipo A (2,00x2,20)"
      "Suministro y construcción de contenedor de raíces Tipo A (2,00x2,20)m"
      "CONTEN" 2.00 2.20)
    ("CONT-B" "Contenedor raices Tipo B (1,50x2,20)"
      "Suministro y construcción de contenedor de raíces Tipo B (1,50x2,20)m"
      "CONTEN" 1.50 2.20)
    ("CONT-C" "Contenedor raices Tipo C (1,20x2,20)"
      "Suministro y construcción de contenedor de raíces Tipo C (1,20x2,20)m"
      "CONTEN" 1.20 2.20)
    ("CONT-D" "Contenedor raices Tipo D (0,84x4,20)"
      "Suministro y construcción de contenedor de raíces Tipo D (0,84x4,20)m"
      "CONTEN" 0.84 4.20)
    ("CONT-E" "Contenedor raices Tipo E (0,70x4,20)"
      "Suministro y construcción de contenedor de raíces Tipo E (0,70x4,20)m"
      "CONTEN" 0.70 4.20)
    ("CONT-F" "Contenedor raices Tipo F (0,70x4,20)"
      "Suministro y construcción de contenedor de raíces Tipo F (0,70x4,20)m"
      "CONTEN" 0.70 4.20)
    ;; 2026-09-17 (pedido del usuario): contenedor de 4,20 m de largo x 1,20 m de ancho
    ("CONT-G" "Contenedor raices Tipo G (1,20x4,20)"
      "Suministro y construcción de contenedor de raíces Tipo G (1,20x4,20)m"
      "CONTEN" 1.20 4.20)
    ;; ---------- mobiliario de PARQUE (2026-09-06): descripciones
    ;; EXACTAS de los capitulos por parque del presupuesto nuevo; el
    ;; redireccionamiento por zona los apunta al parque donde caen ----------
    ("CANECA-IDU" "Caneca tipo IDU"
      "Canecas tipo idu" "CIRC" 0.50 0.50)
    ("BANCA-IDU" "Banca tipo IDU sin espaldar"
      "Bancas tipo idu en concreto(sin espaldar)" "RECT" 2.00 0.60)
    ("MESA-RURAL" "Mesa rural con asientos"
      "Mesa rural con asientos" "RECT" 2.20 2.20)
    ("TOTEM" "Totem de parque"
      "totem parque" "RECT" 0.60 0.30)
    ("MAQUINA-GYM" "Maquina de gimnasio"
      "Maquinas gym" "RECT" 1.50 0.80)
    ("BICICLETERO" "Bicicletero enrollado (11 bicis)"
      "Bicicletero enrollado (capacidad: 11 bicicletas)" "RECT" 3.00 0.80)
    ("JUEGO-D5-02" "Deslizadero recto (D5-02)"
      "D5-02 deslizadero recto en polimero" "RECT" 3.50 1.00)
    ("JUEGO-D5-03" "Columpio en canasta (D5-03)"
      "D5-03 columpio en canasta" "RECT" 3.00 2.00)
    ("JUEGO-D5-05" "Red piramidal pequeña (D5-05)"
      "D5-05 red piramidal pequeña" "CIRC" 3.00 3.00)
    ("JUEGO-D5-09" "Presas de escalada (D5-09)"
      "D5-09 presas infantiles de escalada" "RECT" 2.40 1.20)
    ("JUEGO-D2-02" "Laberinto de troncos (D2-02)"
      "D2-02 laberinto de troncos" "RECT" 3.00 3.00)))

;; definicion del bloque liviano de un tipo (si no existe): geometria
;; simple en planta -- circulo doble (caneca/bolardo/senal), rectangulo
;; con diagonal (bancas/paradero/contenedores) o circulo con cruz (arbol)
;; polilinea rectangular CERRADA dentro de una definicion de bloque
(defun urb:mob-rect-poly (bdef x1 y1 x2 y2 / poly)
  (setq poly
    (vla-AddLightWeightPolyline bdef
      (urb:double-array-variant (list x1 y1 x2 y1 x2 y2 x1 y2))))
  (vla-put-Closed poly :vlax-true)
  poly)

(defun urb:mob-ensure-block (entry side-sign / nombre bdef a l a2 l2 y0 y1 marco interior
                             hatch mtx etiqueta th)
  ;; los contenedores llevan sufijo de version (2026-08-20 _C2: la forma
  ;; paso de rectangulo simple a marco doble + relleno verde + texto;
  ;; 2026-08-24 _C3: el largo paso de eje Y local a eje X local -- el
  ;; sufijo obliga a regenerar la definicion en dibujos donde ya existia
  ;; la vieja, que salia rotada 90 grados respecto al sendero/anden)
  (setq nombre
    (strcat "URB_MOB_" (nth 0 entry)
      (if (= (nth 3 entry) "CONTEN")
        (if (< side-sign 0.0) "_C4N" "_C4P") "")))
  (if (not (tblsearch "BLOCK" nombre))
    (progn
      (setq bdef
        (vla-Add (vla-get-Blocks (urb:doc))
          (vlax-3d-point '(0.0 0.0 0.0)) nombre))
      (setq a (nth 4 entry) l (nth 5 entry))
      (setq a2 (/ a 2.0) l2 (/ l 2.0))
      (cond
        ;; contenedor de raices como el detalle del proyecto: marco doble,
        ;; relleno solido verde que TAPA el patron del anden debajo, y el
        ;; texto "Cont. Raices / Tipo X" centrado. Dimensiones reales.
        ;; 2026-08-24 (pedido del usuario, corrigiendo el resultado en
        ;; diamante): el punto de insercion es una ESQUINA (no el centro)
        ;; y el LARGO (l) corre por el eje X LOCAL -- es el eje que
        ;; vla-InsertBlock alinea con el angulo "ang" (direccion del
        ;; segundo clic). Antes el largo corria por Y local, perpendicular
        ;; a la direccion pedida, y por eso el contenedor salia rotado
        ;; 90 grados respecto al sendero/anden.
        ((= (nth 3 entry) "CONTEN")
          (setq y0 (if (< side-sign 0.0) (- a) 0.0)
                y1 (if (< side-sign 0.0) 0.0 a))
          (setq marco (urb:mob-rect-poly bdef 0.0 y0 l y1))
          (vla-put-Color marco 5)
          (setq interior
            (urb:mob-rect-poly bdef 0.06 (+ y0 0.06)
              (- l 0.06) (- y1 0.06)))
          (vla-put-Color interior 5)
          (setq hatch
            (vl-catch-all-apply
              '(lambda ()
                (setq hatch (vla-AddHatch bdef 1 "SOLID" :vlax-true))
                (vla-AppendOuterLoop hatch (urb:make-loop-array interior))
                (vla-put-Color hatch 121)
                (urb:evaluate-render-hatch hatch)
                hatch)))
          (setq etiqueta
            (cond
              ((= (nth 0 entry) "CONT-RAICES") "Cont. Raices\\P2,0x1,2")
              (T (strcat "Cont. Raices\\PTipo "
                   (substr (nth 0 entry) 6)))))
          (setq th (min 0.25 (* (min a l) 0.22)))
          (setq mtx
            (vla-AddMText bdef
              (vlax-3d-point (list l2 (* side-sign a2) 0.0))
              (* (max a l) 0.9) etiqueta))
          (vla-put-Height mtx th)
          (vla-put-AttachmentPoint mtx 5)   ; centro
          (vla-put-InsertionPoint mtx
            (vlax-3d-point (list l2 (* side-sign a2) 0.0))))
        ((= (nth 3 entry) "CIRC")
          (vla-AddCircle bdef (vlax-3d-point '(0.0 0.0 0.0)) a2)
          (vla-AddCircle bdef (vlax-3d-point '(0.0 0.0 0.0)) (* a2 0.6)))
        ((= (nth 3 entry) "ARBOL")
          (vla-AddCircle bdef (vlax-3d-point '(0.0 0.0 0.0)) a2)
          (vla-AddLine bdef
            (vlax-3d-point (list (- a2) 0.0 0.0))
            (vlax-3d-point (list a2 0.0 0.0)))
          (vla-AddLine bdef
            (vlax-3d-point (list 0.0 (- a2) 0.0))
            (vlax-3d-point (list 0.0 a2 0.0))))
        (T   ; RECT centrado con una diagonal para que se lea la forma
          (vla-AddLine bdef
            (vlax-3d-point (list (- a2) (- l2) 0.0))
            (vlax-3d-point (list a2 (- l2) 0.0)))
          (vla-AddLine bdef
            (vlax-3d-point (list a2 (- l2) 0.0))
            (vlax-3d-point (list a2 l2 0.0)))
          (vla-AddLine bdef
            (vlax-3d-point (list a2 l2 0.0))
            (vlax-3d-point (list (- a2) l2 0.0)))
          (vla-AddLine bdef
            (vlax-3d-point (list (- a2) l2 0.0))
            (vlax-3d-point (list (- a2) (- l2) 0.0)))
          (vla-AddLine bdef
            (vlax-3d-point (list (- a2) (- l2) 0.0))
            (vlax-3d-point (list a2 l2 0.0)))))
      (urb:add-invisible-attribute bdef '(0.0 0.0 0.0)
        "TIPO" "Tipo de mobiliario" (nth 0 entry))
      (urb:add-invisible-attribute bdef '(0.0 0.0 0.0)
        "ETAPA" "Etapa" "1")
      (urb:add-invisible-attribute bdef '(0.0 0.0 0.0)
        "SUBETAPA" "Subetapa" "GEN")))
  nombre)

(defun urb:mob-write-dcl ()
  (urb:write-dialog-dcl
    "urb_mobiliario"
    '*urb-mob-dcl-ok*
    (list
      "urb_mobiliario : dialog { label = \"Mobiliario urbano\";"
      ": list_box { key = \"tipo\"; label = \"Tipo (con su actividad del presupuesto)\"; width = 96; height = 17; }"
      ": text { label = \"Aceptar y luego CLIC por cada pieza (Enter o Escape termina). Rotar despues con ROTATE si hace falta.\"; }"
      ": text { label = \"Cada pieza cuenta 1 UN hacia su actividad al exportar; etapa/subetapa editables en Propiedades.\"; }"
      "ok_cancel; }")))

;; marcar la ZONA (parque) de elementos por seleccion: el nombre debe
;; aparecer en el capitulo o la seccion del presupuesto (p.ej. "PARQUE 3",
;; "PQ14", "PL3"); nombre vacio QUITA la marca. Aplica a vias, andenes,
;; prefabricados, zonas verdes, mobiliario y senderos.
(defun urb:loc-marcar (/ selection entities nombre ename n)
  (prompt "\nSeleccione los elementos que pertenecen al parque/zona: ")
  (setq selection (ssget))
  (if (null selection)
    (prompt "\nNo se seleccionaron elementos.")
    (progn
      (setq entities
        (urb:unique-enames
          (append
            (urb:selected-roads selection)
            (urb:selected-anden-parents selection)
            (urb:selected-prefabs selection)
            (urb:selected-green-zones selection)
            (urb:mob-selected selection)
            (urb:send-selected selection)
            (urb:bioswale-selected selection))))
      (if (null entities)
        (prompt "\nLa seleccion no contiene vias, andenes, prefabricados, zonas verdes, mobiliario, senderos ni bioswale reconocidos.")
        (progn
          (setq nombre
            (getstring T
              (strcat "\nNombre de la zona tal como aparece en el presupuesto"
                " (ej. PARQUE 3, PQ14; Enter vacio QUITA la marca): ")))
          (setq nombre (vl-string-trim " " (urb:safe-string nombre "")))
          (setq n 0)
          (foreach ename entities
            (urb:set-xdata-strings ename "URB_ZONA" (list nombre))
            (setq n (1+ n)))
          (if (= nombre "")
            (prompt (strcat "\nZona QUITADA de " (itoa n) " elemento(s)."))
            (prompt (strcat "\n" (itoa n) " elemento(s) marcados en la zona \""
              nombre "\": sus cantidades buscaran las actividades del"
              " capitulo o seccion del presupuesto que contenga ese"
              " nombre."))))))))

;; ---------- LOCALIZACION (2026-08-21 v4.49, pedido del usuario) ----------
;; Ventana dinamica: muestra las zonas YA marcadas con su conteo (antes no
;; habia forma de saber que quedo marcado), permite seleccionarlas en
;; pantalla, quitar la marca o marcar una nueva.
;; 2026-08-24 (pedido del usuario): el FILTRO por etapa/subetapa que vivia
;; aqui se movio a su propio boton FILTRAR en el panel Cantidades (junto
;; con el rastreo por texto del presupuesto) -- Localizacion queda SOLO
;; para georreferenciacion (a que parque/zona pertenece cada elemento),
;; que es lo que se conecta con el capitulo/seccion del presupuesto.

;; zonas marcadas del dibujo: alist (nombre ename1 ename2 ...)
(defun urb:loc-collect-zonas (/ ss i e z out entry)
  (setq out nil)
  (if (and (tblsearch "APPID" "URB_ZONA")
           (setq ss (ssget "_X" '((-3 ("URB_ZONA"))))))
    (progn
      (setq i 0)
      (repeat (sslength ss)
        (setq e (ssname ss i))
        (setq z (urb:ppto-zona-de e))
        (if (/= z "")
          (progn
            (setq entry (assoc z out))
            (setq out
              (if entry
                (subst (cons z (cons e (cdr entry))) entry out)
                (cons (list z e) out)))))
        (setq i (1+ i)))))
  (reverse out))

;; lee (categoria etapa subetapa) de cualquier elemento del programa --
;; espejo de LECTURA de urb:apply-etapa-subetapa (mismas posiciones)
(defun urb:element-etapa (ename / obj data atts)
  (cond
    ((setq data (urb:get-xdata-strings ename "URB_ANDEN_BLOCK"))
      (list "Andenes" (urb:safe-string (nth 2 data) "")
        (urb:safe-string (nth 3 data) "")))
    ((setq data (urb:get-xdata-strings ename "URB_VIA"))
      (list "Vias" (urb:safe-string (nth 2 data) "")
        (urb:safe-string (nth 3 data) "")))
    ((setq data (urb:get-xdata-strings ename "URB_PREFAB_BLOCK"))
      (list "Prefabricados" (urb:safe-string (nth 1 data) "")
        (urb:safe-string (nth 2 data) "")))
    ((setq data (urb:get-xdata-strings ename "URB_GREEN_BLOCK"))
      (list "Zonas verdes" (urb:safe-string (nth 1 data) "")
        (urb:safe-string (nth 2 data) "")))
    ((setq data (urb:get-xdata-strings ename "URB_RAMPA_BLOCK"))
      (list "Rampas" (urb:safe-string (nth 1 data) "")
        (urb:safe-string (nth 2 data) "")))
    ((setq data (urb:get-xdata-strings ename "URB_SENDERO"))
      (list "Senderos" (urb:safe-string (nth 1 data) "")
        (urb:safe-string (nth 2 data) "")))
    ((setq data (urb:get-xdata-strings ename "URB_BIOSWALE"))
      (list "Bioswale" (urb:safe-string (nth 1 data) "")
        (urb:safe-string (nth 2 data) "")))
    ((and (setq obj (urb:as-vla-object ename))
          (setq atts (urb:block-attribute-values obj))
          (assoc "ETAPA" atts))
      (list "Redes / otros"
        (urb:safe-string (cdr (assoc "ETAPA" atts)) "")
        (urb:safe-string (cdr (assoc "SUBETAPA" atts)) "")))))

;; todos los elementos del programa con esa etapa (y subetapa si sub no
;; es nil), en todas las especialidades
(defun urb:loc-collect-etapa (etapa sub / apps sets a ss i e seen out info)
  (setq apps '("URB_ANDEN_BLOCK" "URB_VIA" "URB_PREFAB_BLOCK"
               "URB_GREEN_BLOCK" "URB_RAMPA_BLOCK" "URB_SENDERO"
               "URB_BIOSWALE"))
  (setq sets nil)
  (foreach a apps
    (if (and (tblsearch "APPID" a)
             (setq ss (ssget "_X" (list (list -3 (list a))))))
      (setq sets (cons ss sets))))
  (if (setq ss (ssget "_X" '((0 . "INSERT")
                             (2 . "URB_MOB_*,MP_TRAMO_*,MP_PUNTO_*"))))
    (setq sets (cons ss sets)))
  (setq seen nil out nil)
  (foreach ss sets
    (setq i 0)
    (repeat (sslength ss)
      (setq e (ssname ss i))
      (if (not (member e seen))
        (progn
          (setq seen (cons e seen))
          (setq info (vl-catch-all-apply 'urb:element-etapa (list e)))
          (if (and (not (vl-catch-all-error-p info)) info
                   (= (strcase (urb:safe-string (nth 1 info) ""))
                      (strcase etapa))
                   (or (null sub)
                       (= (strcase (urb:safe-string (nth 2 info) ""))
                          (strcase sub))))
            (setq out (cons e out)))))
      (setq i (1+ i))))
  out)

(defun urb:loc-fill-fsub (idx)
  (start_list "fsub")
  (add_list "(todas)")
  (foreach s (urb:subetapas-for (nth idx *urb-etapa-list*)) (add_list s))
  (end_list)
  (set_tile "fsub" "0"))

(defun urb:loc-write-dcl ()
  (urb:write-dialog-dcl
    "urb_localizacion"
    '*urb-loc-dcl-ok*
    (list
      "urb_localizacion : dialog { label = \"Localizacion\";"
      ": boxed_column { label = \"Zonas / parques marcados en el dibujo\";"
      ": list_box { key = \"zonas\"; width = 54; height = 8; }"
      ": row {"
      ": button { label = \"Seleccionar\"; key = \"selz\"; width = 15; }"
      ": button { label = \"Quitar marca\"; key = \"quitarz\"; width = 15; }"
      ": button { label = \"Marcar zona...\"; key = \"marcar\"; width = 17; } } }"
      "cancel_button; }")))

(defun urb:zona-parque-command (/ dclfile dcl done zonas z zsel ss e n)
  (vl-load-com)
  (setq zonas (urb:loc-collect-zonas))
  (setq dclfile (urb:loc-write-dcl))
  (if (null dclfile)
    (alert "No se pudo preparar la ventana de localizacion (revise permisos de la carpeta temporal de Windows).")
    (progn
      (setq dcl (load_dialog dclfile))
      (if (and dcl (> dcl 0) (new_dialog "urb_localizacion" dcl))
        (progn
          (start_list "zonas")
          (if zonas
            (foreach z zonas
              (add_list (strcat (car z) "   (" (itoa (length (cdr z)))
                " elemento" (if (= (length (cdr z)) 1) "" "s") ")")))
            (add_list "(sin zonas marcadas todavia)"))
          (end_list)
          (set_tile "zonas" "0")
          ;; cada boton captura DENTRO de su action y cierra con su codigo
          ;; (regla de oro DCL v4.41)
          (action_tile "selz"
            "(setq *urb-loc-zsel* (get_tile \"zonas\")) (done_dialog 2)")
          (action_tile "quitarz"
            "(setq *urb-loc-zsel* (get_tile \"zonas\")) (done_dialog 3)")
          (action_tile "marcar" "(done_dialog 4)")
          (setq done (start_dialog))))
      (if (and dcl (> dcl 0)) (unload_dialog dcl))
      (cond
        ((= done 2)
          (setq zsel
            (nth (atoi (urb:safe-string *urb-loc-zsel* "0")) zonas))
          (if zsel
            (progn
              (setq ss (ssadd) n 0)
              (foreach e (cdr zsel)
                (if (and e (entget e)) (progn (ssadd e ss) (setq n (1+ n)))))
              (sssetfirst nil ss)
              (prompt (strcat "\n" (itoa n)
                " elemento(s) de la zona \"" (car zsel)
                "\" quedaron seleccionados en pantalla.")))
            (prompt "\nNo hay zonas marcadas todavia (use Marcar zona...).")))
        ((= done 3)
          (setq zsel
            (nth (atoi (urb:safe-string *urb-loc-zsel* "0")) zonas))
          (if zsel
            (progn
              (setq n 0)
              (foreach e (cdr zsel)
                (if (and e (entget e))
                  (progn
                    (urb:set-xdata-strings e "URB_ZONA" (list ""))
                    (setq n (1+ n)))))
              (prompt (strcat "\nMarca de zona quitada de " (itoa n)
                " elemento(s) de \"" (car zsel) "\".")))
            (prompt "\nNo hay zonas marcadas todavia.")))
        ((= done 4) (urb:loc-marcar)))))
  (princ))

;; ---------- FILTRAR / RASTREAR (2026-08-24, pedido del usuario) --------
;; Boton propio en Cantidades, separado de Localizacion. Dos modos en la
;; misma ventana:
;;  1. Filtro por etapa/subetapa (el que antes vivia en Localizacion,
;;     reutiliza urb:loc-collect-etapa sin cambios).
;;  2. Rastrear por texto del presupuesto: recolecta TODAS las filas de
;;     presupuesto del dibujo (los mismos colectores urb:ppto-rows-* que
;;     usa el export, en memoria y sin abrir Excel) y selecciona los
;;     elementos cuyo concepto+red coinciden con las palabras buscadas,
;;     con el mismo tokenizador/match difuso (urb:ppto-words,
;;     urb:ppto-word-match-p) que usa la vinculacion real -- ej. "tuberia
;;     8" encuentra "Instalacion tuberia PVC 8"" y selecciona todos los
;;     tramos que generan esa fila.

;; ---------- perfilado ligero del export (2026-09-07) ----------
;; si *urb-perf-log* apunta a un archivo, cada colector y el match
;; escriben ahi sus milisegundos -- lo usa el harness de perf; en uso
;; normal (variable sin setear) no cuesta nada.
(defun urb:perf-log (msg / f)
  (if (and (boundp '*urb-perf-log*) *urb-perf-log*)
    (progn
      (setq f (open *urb-perf-log* "a"))
      (if f (progn (write-line msg f) (close f))))))

(defun urb:rows-timed (nombre fn / t0 r)
  (setq t0 (getvar "MILLISECS"))
  (setq r (vl-catch-all-apply fn nil))
  (if (vl-catch-all-error-p r)
    (progn
      (urb:perf-log (strcat nombre ": ERROR "
        (vl-catch-all-error-message r)))
      ;; Un colector fallido no equivale a una disciplina vacia: abortar
      ;; antes de reemplazar las memorias del DWG por un conjunto parcial.
      (prompt (strcat "\nExportacion detenida en " nombre ": "
        (vl-catch-all-error-message r)))
      (exit)))
  (urb:perf-log (strcat nombre ": "
    (itoa (- (getvar "MILLISECS") t0)) " ms, "
    (itoa (length r)) " filas"))
  r)

(defun urb:track-collect-rows ()
  (append
    (urb:ppto-rows-vias)
    (urb:ppto-rows-andenes)
    (urb:ppto-rows-prefabs)
    (urb:ppto-rows-rampas)
    (urb:ppto-rows-tramos)
    (urb:ppto-rows-puntos)
    (urb:ppto-rows-mobiliario)
    (urb:ppto-rows-senderos)
    (urb:ppto-rows-bioswale)
    (urb:ppto-rows-canuela-plu)
    (urb:ppto-rows-zonasverdes)
    (urb:ppto-rows-senalizacion)))

(defun urb:track-words-match-p (termwords candwords / ok w)
  (setq ok T)
  (foreach w termwords
    (if (not (vl-some '(lambda (c) (urb:ppto-word-match-p w c)) candwords))
      (setq ok nil)))
  ok)

;; 2026-08-24 (pedido del usuario): el filtro no debe solo SELECCIONAR
;; (marcar) -- en un plano lleno de todas las disciplinas a la vez, eso no
;; se ve. Debe AISLAR: apagar en pantalla todo lo que NO haga parte del
;; resultado, con el comando nativo ISOLATEOBJECTS (AutoCAD ya trae el
;; mecanismo de "fin de aislamiento" con UNISOLATEOBJECTS -- no hay que
;; reinventar visibilidad a mano).
;; 2026-08-24 (pedido del usuario, tras probar): ISOLATEOBJECTS apaga
;; TODO lo que no este en la seleccion, incluidos los xref (aparecen como
;; un solo INSERT en el dibujo -- si no esta en la seleccion, el xref
;; ENTERO se apaga). El filtro es solo para lo dibujado por el plugin;
;; los xref son el fondo de referencia y deben seguir visibles siempre.
;; Se agregan sus INSERT al aislamiento (recorriendo vla-get-Blocks del
;; documento buscando IsXRef = :vlax-true, mismo patron que el lote
;; RESIDUAL sobre un xref).
(defun urb:track-xref-inserts (/ doc blocks ss i e nom bdef isx out)
  (setq out nil)
  (setq doc (vla-get-ActiveDocument (vlax-get-acad-object)))
  (setq blocks (vla-get-Blocks doc))
  (if (setq ss (ssget "_X" '((0 . "INSERT"))))
    (progn
      (setq i 0)
      (repeat (sslength ss)
        (setq e (ssname ss i) nom (cdr (assoc 2 (entget e))) bdef nil isx nil)
        (if nom
          (progn
            (setq bdef (vl-catch-all-apply 'vla-item (list blocks nom)))
            (if (not (vl-catch-all-error-p bdef))
              (setq isx (vl-catch-all-apply 'vla-get-IsXRef (list bdef))))))
        (if (and isx (not (vl-catch-all-error-p isx)) (eq isx :vlax-true))
          (setq out (cons e out)))
        (setq i (1+ i)))))
  out)

(defun urb:track-isolate (ss / xrefs e)
  (if (and ss (> (sslength ss) 0))
    (progn
      (setq xrefs (urb:track-xref-inserts))
      (foreach e xrefs
        (if (not (ssmemb e ss)) (ssadd e ss)))
      (command "_.ISOLATEOBJECTS" ss "")))
  (princ))

(defun urb:track-clear-isolate ()
  (command "_.UNISOLATEOBJECTS")
  (prompt "\nFiltro quitado: el dibujo vuelve a verse completo.")
  (princ))

(defun urb:track-by-texto (texto / rows termwords ss n r candwords handle
                            en seen)
  (setq termwords (urb:ppto-words texto))
  (if (null termwords)
    (prompt "\nEscriba al menos una palabra para buscar.")
    (progn
      (setq rows (urb:track-collect-rows))
      (setq ss (ssadd) n 0 seen nil)
      (foreach r rows
        (if r
          (progn
            (setq candwords
              (urb:ppto-words (strcat (nth 0 r) " " (nth 1 r))))
            (if (urb:track-words-match-p termwords candwords)
              (progn
                (setq handle (nth 9 r))
                (if (and handle (not (member handle seen)))
                  (progn
                    (setq seen (cons handle seen))
                    (setq en (handent handle))
                    (if (and en (entget en))
                      (progn (ssadd en ss) (setq n (1+ n)))))))))))
      (if (> n 0)
        (progn
          (sssetfirst nil ss)
          (urb:track-isolate ss)
          (prompt (strcat "\n" (itoa n) " elemento(s) coinciden con \""
            texto "\" -- el resto del dibujo se APAGO (UNISOLATEOBJECTS"
            " para volver a verlo todo).")))
        (prompt (strcat "\nNingun elemento del dibujo coincide con \""
          texto "\".")))))
  (princ))

(defun urb:filtrar-write-dcl ()
  (urb:write-dialog-dcl
    "urb_filtrar"
    '*urb-filtrar-dcl-ok*
    (list
      "urb_filtrar : dialog { label = \"Filtrar / Rastrear\";"
      ": boxed_column { label = \"Filtro por etapa y subetapa (todas las especialidades)\";"
      ": popup_list { label = \"Etapa\"; key = \"fetapa\"; }"
      ": popup_list { label = \"Subetapa\"; key = \"fsub\"; }"
      ": button { label = \"Seleccionar elementos de esa etapa/subetapa\"; key = \"self\"; } }"
      ": boxed_column { label = \"Rastrear por texto del presupuesto\";"
      ": edit_box { key = \"texto\"; label = \"Palabras (ej. tuberia 8, adoquin, luminaria)\"; edit_width = 40; }"
      ": button { label = \"Buscar y seleccionar en pantalla\"; key = \"buscar\"; } }"
      ": button { label = \"Quitar filtro (mostrar todo de nuevo)\"; key = \"limpiar\"; }"
      "cancel_button; }")))

(defun urb:filtrar-command (/ dclfile dcl done etapa subs sub elems ss e n
                            texto)
  (setq dclfile (urb:filtrar-write-dcl))
  (if (null dclfile)
    (alert "No se pudo preparar la ventana de filtrar (revise permisos de la carpeta temporal de Windows).")
    (progn
      (setq dcl (load_dialog dclfile))
      (if (and dcl (> dcl 0) (new_dialog "urb_filtrar" dcl))
        (progn
          (start_list "fetapa")
          (foreach e *urb-etapa-list* (add_list e))
          (end_list)
          (set_tile "fetapa" "0")
          (urb:loc-fill-fsub 0)
          (action_tile "fetapa" "(urb:loc-fill-fsub (atoi $value))")
          ;; cada boton captura DENTRO de su action y cierra con su codigo
          ;; (regla de oro DCL v4.41)
          (action_tile "self"
            (strcat
              "(setq *urb-loc-fetapa* (get_tile \"fetapa\")"
              " *urb-loc-fsub* (get_tile \"fsub\")) (done_dialog 5)"))
          (action_tile "buscar"
            "(setq *urb-track-texto* (get_tile \"texto\")) (done_dialog 6)")
          (action_tile "limpiar" "(done_dialog 7)")
          (setq done (start_dialog))))
      (if (and dcl (> dcl 0)) (unload_dialog dcl))
      (cond
        ((= done 5)
          (setq etapa
            (urb:safe-string
              (nth (atoi (urb:safe-string *urb-loc-fetapa* "0"))
                *urb-etapa-list*) "1"))
          (setq subs (cons "(todas)" (urb:subetapas-for etapa)))
          (setq sub
            (urb:safe-string
              (nth (atoi (urb:safe-string *urb-loc-fsub* "0")) subs)
              "(todas)"))
          (setq elems
            (urb:loc-collect-etapa etapa
              (if (= sub "(todas)") nil sub)))
          (if elems
            (progn
              (setq ss (ssadd))
              (foreach e elems (ssadd e ss))
              (sssetfirst nil ss)
              (urb:track-isolate ss)
              (prompt (strcat "\n" (itoa (length elems))
                " elemento(s) de etapa " etapa
                (if (/= sub "(todas)") (strcat " subetapa " sub) "")
                " -- el resto del dibujo se APAGO (UNISOLATEOBJECTS para"
                " volver a verlo todo).")))
            (prompt
              (strcat "\nNingun elemento del programa tiene etapa " etapa
                (if (/= sub "(todas)") (strcat " subetapa " sub) "")
                "."))))
        ((= done 6)
          (urb:track-by-texto (urb:safe-string *urb-track-texto* "")))
        ((= done 7) (urb:track-clear-isolate)))))
  (princ))

;; bloques de mobiliario dentro de una seleccion
(defun urb:mob-selected (selection / i be out nom)
  (setq out nil i 0)
  (if selection
    (repeat (sslength selection)
      (setq be (ssname selection i))
      (setq nom (cdr (assoc 2 (entget be))))
      (if (and nom (wcmatch nom "URB_MOB_*"))
        (setq out (cons be out)))
      (setq i (1+ i))))
  (reverse out))

(defun urb:mobiliario-command
  (/ dclfile dcl done entry nombre pt ref ref-ename n ang side-pt vproj
     side-sign recut-result)
  (vl-load-com)
  (setq dclfile (urb:mob-write-dcl))
  (if (null dclfile)
    (alert "No se pudo preparar la ventana de mobiliario (revise permisos de la carpeta temporal de Windows).")
    (progn
      (setq dcl (load_dialog dclfile))
      (if (and dcl (> dcl 0) (new_dialog "urb_mobiliario" dcl))
        (progn
          (start_list "tipo")
          (foreach entry *urb-mob-tipos*
            (add_list (strcat (nth 1 entry) "   ->  " (nth 2 entry))))
          (end_list)
          (set_tile "tipo" "0")
          ;; seleccion capturada DENTRO del accept (regla de oro DCL v4.41)
          (setq *urb-mob-sel* "0")
          (action_tile "accept"
            "(setq *urb-mob-sel* (get_tile \"tipo\")) (done_dialog 1)")
          (setq done (start_dialog))))
      (if (and dcl (> dcl 0)) (unload_dialog dcl))
      (if (= done 1)
        (progn
          (setq entry
            (nth (atoi (urb:safe-string *urb-mob-sel* "0")) *urb-mob-tipos*))
          (urb:ensure-layer "URB-MOBILIARIO" 92 T)
          (if (/= (nth 3 entry) "CONTEN")
            (setq nombre (urb:mob-ensure-block entry 1.0)))
          (setq n 0)
          (while (setq pt
                   (getpoint (strcat "\nPunto para " (nth 1 entry)
                     " (Enter termina): ")))
            ;; direccion: segundo clic sobre el eje del anden alinea la
            ;; pieza (Enter = sin rotacion). Pedido 2026-08-20 para los
            ;; contenedores de raices sobre el eje del anden.
            (setq ang (getangle pt
              "\nDireccion sobre el eje (clic segundo punto, Enter=0): "))
            (if (null ang) (setq ang 0.0))
            ;; Contenedores: el tercer punto elige el costado del eje. Se
            ;; genera una definicion local positiva/negativa (sin escala
            ;; espejo), para conservar el texto legible.
            (setq side-sign 1.0)
            (if (= (nth 3 entry) "CONTEN")
              (progn
                (setq side-pt
                  (getpoint pt
                    "\nPunto al lado del eje hacia donde se dibuja el contenedor: "))
                (if side-pt
                  (progn
                    (setq vproj
                      (+ (* (- (car side-pt) (car pt)) (- (sin ang)))
                         (* (- (cadr side-pt) (cadr pt)) (cos ang))))
                    (setq side-sign (if (< vproj 0.0) -1.0 1.0)))
                  (setq side-sign nil))
                (if side-sign
                  (setq nombre (urb:mob-ensure-block entry side-sign)))))
            (setq ref
              (if side-sign (vl-catch-all-apply
                '(lambda ()
                  (vla-InsertBlock (urb:space)
                    (vlax-3d-point (trans pt 1 0)) nombre 1.0 1.0 1.0 ang)))))
            (if (or (null ref) (vl-catch-all-error-p ref))
              (prompt
                (if (vl-catch-all-error-p ref)
                  (strcat "\nNo se pudo insertar: "
                    (vl-catch-all-error-message ref))
                  "\nInsercion cancelada: no se definio el lado del eje."))
              (progn
                (vla-put-Layer ref "URB-MOBILIARIO")
                (setq ref-ename (vlax-vla-object->ename ref))
                (urb:set-xdata-strings ref-ename
                  "URB_MOBILIARIO"
                  (list (nth 0 entry)
                    (if (< side-sign 0.0) "IZQUIERDA" "DERECHA")
                    (rtos ang 2 8)))
                ;; 2026-09-08: si el contenedor se inserta DESPUES del
                ;; anden, se reconstruyen automaticamente solo los andenes
                ;; que su huella toca. El bloque anterior se conserva si
                ;; alguna etapa falla.
                (if (= (nth 3 entry) "CONTEN")
                  (progn
                    (setq recut-result
                      (vl-catch-all-apply
                        'urb:recut-andenes-for-container (list ref-ename)))
                    (if (vl-catch-all-error-p recut-result)
                      (prompt (strcat
                        "\nEl contenedor se inserto, pero no fue posible actualizar los andenes: "
                        (vl-catch-all-error-message recut-result)))
                      (progn
                        (if (> (car recut-result) 0)
                          (prompt (strcat "\n" (itoa (car recut-result))
                            " anden(es) recortado(s) por el contenedor."
                            (if (> (cadr recut-result) 0)
                              (strcat " Movimiento de tierras pendiente de recalculo en "
                                (itoa (cadr recut-result)) " anden(es).") ""))))
                        (if (> (caddr recut-result) 0)
                          (prompt (strcat "\nNo se pudieron actualizar "
                            (itoa (caddr recut-result))
                            " anden(es); se conservaron sus bloques anteriores.")))))
                    (vl-catch-all-apply
                      '(lambda ()
                        (command "_.DRAWORDER" ref-ename "" "_Front")))))
                (setq n (1+ n)))))
          (prompt (strcat "\n" (itoa n) " pieza(s) de " (nth 1 entry)
            " insertada(s). Cuentan solas al exportar el presupuesto."))))))
  (princ))

;; ---------- SENDEROS, CICLORRUTA, PLAZOLETA Y RAMPA ----------
;; (2026-08-21, pedido del usuario) Elementos modelados IGUAL que una via
;; o un anden: se CIERRA EL POLIGONO del contorno (nada de eje + ancho,
;; correccion explicita del usuario). Cada tipo lleva su receta de
;; actividades con textos del presupuesto real:
;;   modo AREA -> cantidad = area x factor (espesores, kg/m2, m2)
;;   modo PER  -> cantidad = perimetro x factor (bordillos, drenes)
;; La ciclorruta usa su capitulo propio CICLORRUTA; senderos y plazoleta
;; viven en los capitulos de parques (marcar con Zona parque). El HINT es
;; la palabra de la SECCION preferida dentro del parque: una ciclorruta
;; en PQ10A cae en su seccion CICLORUTA, un sendero en SENDEROS
;; PEATONALES.
;; 2026-08-24 (pedido del usuario): el BIOSWALE salio de este catalogo --
;; es un elemento de la RED PLUVIAL, no de senderos/parques. Vive ahora
;; como su propio boton en Crear -> Redes humedas -> Pluvial (ver
;; "BIOSWALE (red pluvial)" mas abajo), con el mismo motor de contorno
;; cerrado + receta pero SIN el catalogo de tipos (solo hay uno).
;; catalogo: (codigo etiqueta red color hint receta capa espesor-estructura)
;; capa: cada tipo dibuja en SU capa (pedido del usuario 2026-08-21);
;; espesor-estructura: profundidad de excavacion (area x espesor); desde
;; 2026-08-24 el usuario lo edita en Ajustes en vez de verlo en la
;; ventana de creacion (urb:send-espesor-de aplica el valor efectivo).
(setq *urb-send-tipos*
  '(;; 2026-09-07 (rediseño del dialogo): ANDEN EN CONCRETO -- variante
    ;; del anden nativo cuando el material no es loseta; su presupuesto
    ;; va a la red ANDEN (o al capitulo del parque si se dibuja adentro)
    ("ANDEN-CONC" "Anden en concreto" "ANDEN" 9 ""
      (("Compactación de subrasante (Incluye nivelación)" "M2" "AREA" 1.0)
       ("Concreto 3000 psi" "M3" "AREA" 0.10)
       ("Malla electrosoldada" "KG" "AREA" 2.36)
       ("Subbase granular SBG" "M3" "AREA" 0.30)
       ("Geotextil tejido 2100" "M2" "AREA" 1.0)
       ("MO Escobillado concreto" "M2" "AREA" 1.0)
       ("Excavación en material común (incluye cargue, transporte y disposición final)"
         "M3" "AREA" 0.40))
      "URB-ANDEN-CONCRETO" 0.40)
    ("SEND-TROTE" "Sendero de trote" "SENDERO" 40 "TROTE"
      (("Concreto 3000 psi" "M3" "AREA" 0.10)
       ("Malla electrosoldada" "KG" "AREA" 2.36)
       ("Subabase granular SBG-B" "M3" "AREA" 0.30)
       ("Bordillo de confinamiento" "ML" "PER" 1.0)
       ("MO Escobillado concreto" "M2" "AREA" 1.0)
       ("Excavación en material común (incluye cargue, transporte y disposición final)"
         "M3" "AREA" 0.40))
      "URB-SENDERO-TROTE" 0.40)
    ("SEND-ECO" "Sendero ecologico" "SENDERO" 74 "SENDERO"
      (("Concreto 3000 psi" "M3" "AREA" 0.10)
       ("Malla electrosoldada" "KG" "AREA" 2.36)
       ("Subabase granular SBG-B" "M3" "AREA" 0.30)
       ("Bordillo de confinamiento" "ML" "PER" 1.0)
       ("MO Escobillado concreto" "M2" "AREA" 1.0)
       ("Excavación en material común (incluye cargue, transporte y disposición final)"
         "M3" "AREA" 0.40))
      "URB-SENDERO-ECOLOGICO" 0.40)
    ;; ---------- 5.6.2 MATERIALES DE SENDERO de la convencion del plano
    ;; (pedido del usuario, con la leyenda B2-A..B7): cada uno con su COLOR
    ;; propio que no se repite (el relleno sale solido con transparencia,
    ;; como la zona verde). Actividades con el nombre EXACTO que ya trae el
    ;; presupuesto cuando existe (mulch, caucho reciclado, ecopavimento,
    ;; demarcacion de ciclorruta); el deck no tiene fila y sale huerfano
    ;; visible. Espesores de estructura REVISAR con el diseno de pavimentos:
    ;; son el fondo del corte/relleno de cada material.
    ;; Los codigos viejos SEND-TROTE / SEND-ECO se conservan arriba para que
    ;; los senderos ya dibujados sigan cuantificando.
    ("SEND-MULCH-ECO" "Sendero ecologico en mulch (B2-A)" "SENDERO" 96 "SENDERO"
      (("Compactación de subrasante (Incluye nivelación)" "M2" "AREA" 1.0)
       ("Geotextil tejido 2100" "M2" "AREA" 1.0)
       ("Piso en mulch de madera inorganico" "M2" "AREA" 1.0)
       ("Bordillo de confinamiento" "ML" "PER" 1.0)
       ("Excavación en material común (incluye cargue, transporte y disposición final)"
         "M3" "AREA" 0.15))
      "URB-SENDERO-MULCH-ECOLOGICO" 0.15)
    ("SEND-MULCH-TROTE" "Sendero de trote en mulch (B2-B)" "SENDERO" 74 "TROTE"
      (("Compactación de subrasante (Incluye nivelación)" "M2" "AREA" 1.0)
       ("Geotextil tejido 2100" "M2" "AREA" 1.0)
       ("Piso en mulch de madera inorganico" "M2" "AREA" 1.0)
       ("Bordillo de confinamiento" "ML" "PER" 1.0)
       ("Excavación en material común (incluye cargue, transporte y disposición final)"
         "M3" "AREA" 0.15))
      "URB-SENDERO-MULCH-TROTE" 0.15)
    ("SEND-CONC-OCRE" "Sendero en concreto ocre (B3)" "SENDERO" 40 "SENDERO"
      (("Concreto 3000 psi" "M3" "AREA" 0.10)
       ("Malla electrosoldada" "KG" "AREA" 2.36)
       ("Subabase granular SBG-B" "M3" "AREA" 0.30)
       ("Bordillo de confinamiento" "ML" "PER" 1.0)
       ("MO Escobillado concreto" "M2" "AREA" 1.0)
       ("Excavación en material común (incluye cargue, transporte y disposición final)"
         "M3" "AREA" 0.40))
      "URB-SENDERO-CONCRETO-OCRE" 0.40)
    ("SEND-ECOPAV" "Ecopavimento (B4)" "SENDERO" 9 "SENDERO"
      (("Compactación de subrasante (Incluye nivelación)" "M2" "AREA" 1.0)
       ("Subbase granular SBG" "M3" "AREA" 0.20)
       ("superficie en ecopavimento" "M2" "AREA" 1.0)
       ("Excavación en material común (incluye cargue, transporte y disposición final)"
         "M3" "AREA" 0.30))
      "URB-SENDERO-ECOPAVIMENTO" 0.30)
    ("BICICARRIL" "Bicicarril propuesto (B5-B)" "CICLORRUTA" 170 "CICLOR"
      (("Demarcacion cicloruta" "ML" "PER" 1.0))
      "URB-BICICARRIL" 0.0)
    ("SEND-CAUCHO" "Superficie en caucho reciclado (B6)" "SENDERO" 32 "SENDERO"
      (("Compactación de subrasante (Incluye nivelación)" "M2" "AREA" 1.0)
       ("Subbase granular SBG" "M3" "AREA" 0.20)
       ("Concreto 3000 psi" "M3" "AREA" 0.08)
       ("superficie en caucho reciclado" "M2" "AREA" 1.0)
       ("Excavación en material común (incluye cargue, transporte y disposición final)"
         "M3" "AREA" 0.35))
      "URB-SENDERO-CAUCHO" 0.35)
    ("SEND-DECK" "Superficie en deck de madera plastica (B7)" "SENDERO" 22 "SENDERO"
      (("Compactación de subrasante (Incluye nivelación)" "M2" "AREA" 1.0)
       ("Superficie en deck de madera plastica" "M2" "AREA" 1.0)
       ("Excavación en material común (incluye cargue, transporte y disposición final)"
         "M3" "AREA" 0.20))
      "URB-SENDERO-DECK" 0.20)
    ("PLAZOLETA" "Plazoleta en concreto" "SENDERO" 253 "SENDERO"
      (("Concreto 3000 psi" "M3" "AREA" 0.10)
       ("Malla electrosoldada" "KG" "AREA" 2.36)
       ("Subabase granular SBG-B" "M3" "AREA" 0.30)
       ("Bordillo de confinamiento" "ML" "PER" 1.0)
       ("MO Escobillado concreto" "M2" "AREA" 1.0)
       ("Excavación en material común (incluye cargue, transporte y disposición final)"
         "M3" "AREA" 0.40))
      "URB-PLAZOLETA" 0.40)
    ("CICLORRUTA" "Ciclorruta" "CICLORRUTA" 150 "CICLOR"
      (("Descapote mecánico de material vegetal (Incluye cargue y retiro externo)"
         "M2" "AREA" 1.0)
       ("Compactación de subrasante (Incluye nivelación)" "M2" "AREA" 1.0)
       ("Suministro, extendida y compactación de Rodadura Asfáltica MD-13"
         "M3" "AREA" 0.08)
       ("Subbase granular SBG" "M3" "AREA" 0.30)
       ("Geotextil tejido 2100" "M2" "AREA" 1.0)
       ("Excavación en material común (incluye cargue, transporte y disposición final)"
         "M3" "AREA" 0.38)
       ("Bordillo prefabricado A-80" "UN" "PER" 1.25)
       ("M.O. instalación de bordillo prefabricado" "ML" "PER" 1.0))
      "URB-CICLORRUTA" 0.38)
    ("RAMPA-CONC" "Rampa en concreto (ancho variable)" "RAMPA-PEATONAL" 31 ""
      (("Compactación de subrasante (Incluye nivelación)" "M2" "AREA" 1.0)
       ("Suministro y construcción de remate de rampa en concreto fundido en sitio"
         "M2" "AREA" 1.0)
       ("Subbase granular SBG" "M3" "AREA" 0.30)
       ("Geotextil tejido 2100" "M2" "AREA" 1.0)
       ("Excavación en material común (incluye cargue, transporte y disposición final)"
         "M3" "AREA" 0.40))
      "URB-RAMPA-CONCRETO" 0.40)
    ;; ---------- EQUIPAMIENTOS DE PARQUE (2026-09-06, pedido del
    ;; usuario: mismo comando/icono que anden-senderos, solo cambiar el
    ;; material). Recetas con las actividades EXACTAS del presupuesto
    ;; nuevo (capitulos por parque -- el redireccionamiento por zona las
    ;; apunta al parque donde se dibujen). Factores marcados REVISAR son
    ;; de dimensionamiento estandar y se ajustan en el catalogo.
    ("CANCHA-SINT" "Cancha sintetica" "CANCHA-SINTETICA" 92 "CANCHA SINTETICA"
      (("Localizacion y replanteo" "M2" "AREA" 1.0)
       ("Descapote con botadero certificado" "M2" "AREA" 1.0)
       ("Excavacion y retiro a maquina con batadero certificado" "M3" "AREA" 0.45)
       ("Geotextil tejido 1600" "M2" "AREA" 1.0)
       ("Geomembrana impermable HDPE 1mm" "M2" "AREA" 1.0)
       ("Mejoramiento en gravilla(material de filtro)" "M3" "AREA" 0.15)
       ("Subbase granular 0,20m idu" "M3" "AREA" 0.20)
       ("Acabado sintetico" "M2" "AREA" 1.0)
       ("Riego de arena y caucho" "M2" "AREA" 1.0)
       ("Pintura de trafico peatonal y deportivo antideslizante Demarcacion de cancha" "ML" "PER" 1.2)
       ("Excavacion manual de vigas cerramiento y zanjas filto perimetral" "M3" "PER" 0.06)
       ("Concreto 3000psi impermeabilzado" "M3" "PER" 0.05)
       ("Hierro 60000 psi - losa y vigas" "KG" "PER" 4.0)
       ("Alambre negro" "KG" "PER" 0.06)
       ("MO Dados cerramiento" "M3" "PER" 0.012)
       ("MO Vigas corridas cimentacion cerramiento" "M3" "PER" 0.045)
       ("Sum + Inst malla eslabonada cerramiento de altura 5m -" "M2" "PER" 5.0)
       ("Arcos metalicos de futbol(incluyen malla)" "UN" "UN" 2.0))
      "URB-CANCHA-SINTETICA" 0.45)
    ("CANCHA-MULT" "Cancha multiple" "CANCHA-MULTIPLE" 32 "CANCHA MULTIPLE"
      (("Localizacion y replanteo" "M2" "AREA" 1.0)
       ("Descapote con botadero certificado" "M2" "AREA" 1.0)
       ("Excavacion y retiro a maquina con batadero certificado" "M3" "AREA" 0.70)
       ("Geotextil tejido 2400" "M2" "AREA" 1.0)
       ("Mejoramiento en rajon 0,25m" "M3" "AREA" 0.25)
       ("base granular 0,20m idu" "M3" "AREA" 0.20)
       ("Subbase granular 0,20m idu" "M3" "AREA" 0.20)
       ("Rodadura asfaltica MDC-II de 5.5cm" "M2" "AREA" 1.0)
       ("Excavacion manual de vigas cerramiento y zanjas filto perimetral" "M3" "PER" 0.06)
       ("Concreto 3000psi impermeabilzado" "M3" "PER" 0.05)
       ("Hierro 60000 psi - losa y vigas" "KG" "PER" 4.0)
       ("Alambre negro" "KG" "PER" 0.06)
       ("MO Dados cerramiento" "M3" "PER" 0.012)
       ("MO Vigas corridas cimentacion cerramiento" "M3" "PER" 0.045)
       ("Sum + MO Bordillo de confinamiento" "ML" "PER" 1.0)
       ("Filtro perimetral a todo costo" "ML" "PER" 1.0)
       ("Sum + Inst malla eslabonada cerramiento de altura 5m -" "M2" "PER" 5.0)
       ("Arcos metalicos de microfutbol altura 1,80 x 2,5 ancho" "UN" "UN" 2.0)
       ("Tableros para baloncesto" "UN" "UN" 2.0))
      "URB-CANCHA-MULTIPLE" 0.70)
    ("SKATEPARK" "Skatepark" "SKATEPARK" 210 "SKATEPARK"
      (("Localizacion y replanteo" "M2" "AREA" 1.0)
       ("Descapote con botadero certificado" "M2" "AREA" 1.0)
       ("Geotextil tejido 2400" "M2" "AREA" 1.0)
       ("base granular 0,20m idu" "M3" "AREA" 0.20)
       ("Excavacion manual de muro contencion con zarpa" "M3" "PER" 0.15)
       ("Concreto 3000psi impermeabilzado" "M3" "AREA" 0.15)
       ("Hierro 60000 psi - losa y vigas" "KG" "AREA" 12.0)
       ("Alambre negro" "KG" "AREA" 0.18)
       ("MO Muro contencion con zarpa" "M3" "PER" 0.15)
       ("MO Placa de contrapiso" "M3" "AREA" 0.15)
       ("MO Pulida de concreto con helicoptero" "M2" "AREA" 1.0)
       ("Sum + MO Tuberia en acero galvanizado 2\"" "ML" "PER" 0.5)
       ("Sum + MO Baranda M-18 tipo idu" "ML" "PER" 0.3))
      "URB-SKATEPARK" 0.35)
    ("ESCALERA" "Escaleras en concreto" "ESCALERAS" 40 "ESCALERAS"
      (("Localizacion y replanteo" "M2" "AREA" 1.0)
       ("Descapote con botadero certificado" "M2" "AREA" 1.0)
       ("Excavacion y retiro a maquina con batadero certificado" "M3" "AREA" 0.30)
       ("Geotextil tejido 2400" "M2" "AREA" 1.0)
       ("base granular 0,20m idu" "M3" "AREA" 0.20)
       ("Concreto 3000psi impermeabilzado" "M3" "AREA" 0.20)
       ("Hierro 60000 psi - losa y vigas" "KG" "AREA" 16.0)
       ("Alambre negro" "KG" "AREA" 0.24)
       ("MO escalera" "M3" "AREA" 0.20))
      "URB-ESCALERA" 0.30)
    ("GRADERIA" "Graderia en concreto" "GRADERIA" 30 "GRADERIA"
      (("Localizacion y replanteo" "M2" "AREA" 1.0)
       ("Descapote con botadero certificado" "M2" "AREA" 1.0)
       ("Geotextil tejido 2400" "M2" "AREA" 1.0)
       ("base granular 0,20m idu" "M3" "AREA" 0.20)
       ("Excavacion manual de muro contencion con zarpa" "M3" "PER" 0.12)
       ("Concreto 3000psi impermeabilzado" "M3" "AREA" 0.12)
       ("Hierro 60000 psi - losa y vigas" "KG" "AREA" 10.0)
       ("Sc-bloque de concreto graderia" "ML" "AREA" 2.5)
       ("Alambre negro" "KG" "AREA" 0.15)
       ("MO Muro contencion con zarpa" "M3" "PER" 0.12))
      "URB-GRADERIA" 0.25)
    ("PISTA-CAUCHO" "Pista de trote (caucho)" "PISTA-TROTE" 12 "PISTA DE TROTE"
      (("Localizacion y replanteo" "M2" "AREA" 1.0)
       ("Excavacion y retiro a maquina con batadero certificado" "M3" "AREA" 0.35)
       ("Subabase granular SBG-B" "M3" "AREA" 0.20)
       ("Geotextil tejido 2100" "M2" "AREA" 1.0)
       ("mortero de nivelacion" "M3" "AREA" 0.04)
       ("superficie en caucho reciclado" "M2" "AREA" 1.0))
      "URB-PISTA-CAUCHO" 0.35)
    ("PARQUE-NINOS" "Parque de niños (piso)" "PARQUE-NINOS" 41 "PARQUE DE NI"
      (("Localizacion y replanteo" "M2" "AREA" 1.0)
       ("Excavacion y retiro a maquina con batadero certificado" "M3" "AREA" 0.40)
       ("Subabase granular SBG-B" "M3" "AREA" 0.20)
       ("base granular BG" "M3" "AREA" 0.15)
       ("Geotextil tejido 2100" "M2" "AREA" 1.0)
       ("Concreto 3000 psi" "M3" "AREA" 0.10)
       ("Malla electrosoldada" "KG" "AREA" 2.36)
       ("Mano de obra losa contrapiso" "M2" "AREA" 1.0)
       ("Separadores losa" "UN" "AREA" 3.0)
       ("Piso en mulch de madera inorganico" "M2" "AREA" 1.0))
      "URB-PARQUE-NINOS" 0.40)
    ("ZONA-GYM" "Zona gym biosaludable (piso)" "ZONA-GYM" 96 "GYM"
      (("Localizacion y replanteo" "M2" "AREA" 1.0)
       ("Excavacion y retiro a maquina con batadero certificado" "M3" "AREA" 0.40)
       ("Subabase granular SBG-B" "M3" "AREA" 0.20)
       ("base granular BG" "M3" "AREA" 0.15)
       ("Geotextil tejido 2100" "M2" "AREA" 1.0)
       ("Concreto 3000 psi" "M3" "AREA" 0.10)
       ("Malla electrosoldada" "KG" "AREA" 2.36)
       ("Mano de obra losa contrapiso" "M2" "AREA" 1.0)
       ("Separadores losa" "UN" "AREA" 3.0)
       ("superficie en caucho reciclado" "M2" "AREA" 1.0))
      "URB-ZONA-GYM" 0.40)
    ("BICIPARQUEO" "Biciparqueo (piso)" "BICIPARQUEO" 150 "BICIPARQUEO"
      (("Localizacion y replanteo" "M2" "AREA" 1.0)
       ("Excavacion y retiro a maquina con batadero certificado" "M3" "AREA" 0.30)
       ("Subabase granular SBG-B" "M3" "AREA" 0.20)
       ("Geotextil tejido 2100" "M2" "AREA" 1.0)
       ("mortero de nivelacion" "M3" "AREA" 0.04)
       ("superficie en ecopavimento" "M2" "AREA" 1.0))
      "URB-BICIPARQUEO" 0.30)))

;; ---------- BIOSWALE (red pluvial, 2026-08-24) ----------
;; Mismo catalogo (codigo etiqueta red color hint receta capa
;; espesor-estructura) que *urb-send-tipos*, pero con un unico tipo y su
;; propio comando/boton en Crear -> Pluvial -- ya no es un tipo de
;; Sendero (el usuario aclaro que el bioswale/biorretenedor es un
;; elemento de la red pluvial, no de parques).
;; 2026-09-06: receta actualizada a la CARTILLA real (planchas D B-5 /
;; D B-6): gravilla 25-40 mm (capa drenante, min 0.12 m) + gravilla
;; 10-15 mm (capa filtrante, min 0.15 m) + relleno organico + base de
;; gravilla permeable en la caja + tuberia perforada 6" por el eje
;; (~ perimetro/2) + rejilla por elemento. SIN geotextil (nota expresa
;; de la cartilla). Actividades EXACTAS del capitulo 2.5.3.7 del ppto.
(setq *urb-bioswale-tipo*
  '("BIOSWALE" "Bioswale / biorretenedor" "ALC-PLUVIAL" 140 "BIORETENEDORES"
     (("Excavación manual para bioswale/bioretenedor" "M3" "AREA" 0.60)
      ("Cargue, transporte y disposición de sobrantes" "M3" "AREA" 0.60)
      ("Base de gravilla permeable para bioretenedor" "M3" "AREA" 0.20)
      ("Suministro y colocación de gravilla 25-40 mm (capa drenante)" "M3" "AREA" 0.12)
      ("Suministro y colocación de gravilla 10-15 mm (capa filtrante)" "M3" "AREA" 0.15)
      ("Relleno con material orgánico para bioretenedor" "M3" "AREA" 0.13)
      ("Tubería perforada PVC Ø6\" para drenaje de bioswale" "ML" "PER" 0.5)
      ("Rejilla de drenaje para bioswale" "UN" "UN" 1.0)
      ("Jardineria" "M2" "AREA" 1.0))
     "URB-BIOSWALE" 0.60))

;; 2026-08-24 (pedido del usuario): el espesor de estructura de cada tipo
;; (antes fijo en el catalogo y solo visible en la ventana de creacion)
;; se edita ahora en Ajustes -- se guarda en la config del dibujo
;; (URB_SEND_ESP_<codigo>) y esta funcion devuelve el valor EFECTIVO
;; (config si el usuario lo edito, si no el del catalogo). Aplica tanto
;; al texto de la excavacion (fila de la receta) como a cualquier lectura
;; futura del espesor.
(defun urb:send-espesor-de (entry / v)
  (setq v
    (urb:parse-real
      (urb:safe-string
        (urb:config-read (strcat "URB_SEND_ESP_" (nth 0 entry))) "")))
  (if (and v (> v 0.0)) v (nth 7 entry)))

;; igual para el ancho por defecto de cada tipo de prefabricado perimetral
;; (Bordillo/Sardinel/Canuela): ya no se pide por ventana (las piezas
;; prefabricadas tienen dimension predeterminada); editable en Ajustes,
;; 0.20 si nunca se ha configurado.
(defun urb:prefab-default-ancho (prefab / v)
  (setq v
    (urb:parse-real
      (urb:safe-string
        (urb:config-read (strcat "URB_PREFAB_ANCHO_" (strcase prefab))) "")))
  (if (and v (> v 0.0)) v 0.20))

;; 2026-09-10 (pedido del usuario): ALTURA vista del bordillo/sardinel, o
;; sea cuanto queda el anden POR ENCIMA de la rasante de la via. Se usa
;; para las cotas de diseno de anden y zona verde cuando la referencia que
;; se clickea es una via: la cota no es la rasante, es la rasante mas esta
;; altura. Configurable en Ajustes; por defecto 0.20 m (bordillo A-80 del
;; proyecto, el mismo valor que ya trae el ancho por defecto).
(defun urb:prefab-default-alto (prefab / v)
  (setq v
    (urb:parse-real
      (urb:safe-string
        (urb:config-read (strcat "URB_PREFAB_ALTO_" (strcase prefab))) "")))
  (if (and v (> v 0.0)) v 0.20))

;; 2026-09-01 (pedido del usuario): tamano del texto y espesor de los
;; tramos de red ESTANDARIZABLES en Ajustes. Aplican a los bloques de
;; tramo que se creen/renormalicen de ahi en adelante (la definicion es
;; compartida por longitud). ACU conserva su hairline aunque haya ancho
;; configurado (calco fiel del plano).
(defun mp:cfg-tramo-text (default)
  (mp:configured-tramo-value
    "MP_TRAMO_TEXT_HEIGHT" "URB_MP_TEXTO_TRAMO" default 0.10 50.0))

(defun mp:cfg-tramo-width (default)
  (mp:configured-tramo-value
    "MP_TRAMO_LINE_WIDTH" "URB_MP_ANCHO_TRAMO" default 0.01 20.0))

;; 5.6.0: separacion texto-tramo configurable (Ajustes > Apariencia).
(defun mp:cfg-tramo-text-gap (default)
  (mp:configured-tramo-value
    "MP_TRAMO_TEXT_GAP" "MP_TRAMO_TEXT_GAP" default 0.0 50.0))

;; Distancia del EJE del tramo al CENTRO del texto. Los atributos visibles
;; van con alineacion centro-medio, asi que el borde del texto queda a
;; media altura del centro: media linea + separacion libre + media altura.
;; UNICA fuente de la posicion vertical de ETIQUETA / PENDIENTE_VIS /
;; LONG_VIS (antes eran 7 copias de "th x 0.75" repartidas en el archivo).
(defun mp:tramo-label-offset (th)
  (+ (/ (max 0.01 (mp:cfg-tramo-width *mp-vis-width*)) 2.0)
     (mp:cfg-tramo-text-gap *mp-vis-tramo-text-gap*)
     (/ th 2.0)))

;; 2026-08-24 (pedido del usuario): prefabricado por COSTADOS -- distinto
;; de urb:build-prefab-anillo (que envuelve TODO el contorno incluidas
;; las puntas). v2 del mismo dia: el usuario NO quiere trazar los
;; costados a mano -- el programa debe entender solo cuales son los dos
;; lados largos del poligono (como pasa en los andenes) y construir ahi
;; el prefabricado, cada costado como BLOQUE independiente (la misma
;; tuberia probada del boton Prefabricado: urb:build-prefab-from-
;; reference, que ya empaqueta arista+relleno+remates en un bloque que
;; se borra de un solo golpe). El usuario solo decide Externo/Interno.
(defun urb:send-costado-de (n / v)
  (setq v (urb:config-read (strcat "URB_SEND_COSTADO" (itoa n))))
  (if (and v (member v *urb-anillo-prefab-list*)) v "Ninguno"))

(defun urb:send-costpos-de (/ v)
  (setq v (urb:config-read "URB_SEND_COSTPOS"))
  (if (and v (member v *urb-anillo-pos-list*)) v "Externo"))

;; Puntas (los dos segmentos que separan los costados largos) de un
;; contorno ya leido como lista de puntos (x y bulge). Funcion PURA para
;; poder probarla sin crear entidades.
;; 2026-09-08 (reporte del usuario con foto: prefabricados sueltos junto
;; al contenedor de raices): las puntas se eligen por POSICION sobre el
;; eje dominante, no por longitud. Cuando el usuario dibuja un ENTRANTE
;; para rodear un contenedor, ese entrante aporta aristas MAS CORTAS que
;; las puntas reales del anden; la heuristica vieja las tomaba por
;; puntas y partia el contorno en una cadena basura (el fondo del
;; entrante, que salia como prefabricado suelto) y otra que mezclaba los
;; dos costados. Las puntas REALES caen en los extremos del eje largo;
;; el entrante siempre queda en el medio. Sin eje dominante (contorno
;; todo en arcos) se conserva la heuristica anterior.
(defun urb:costado-tip-segments (pts axis-angle / n i ux uy proj minproj
                                 maxproj p1p p2p midp dist best-min
                                 best-max s1 s2 segs)
  (setq n (length pts))
  (if (< n 4)
    nil
    (progn
      (if axis-angle
        (progn
          (setq ux (cos axis-angle) uy (sin axis-angle))
          (setq proj
            (mapcar
              '(lambda (p) (+ (* (car p) ux) (* (cadr p) uy)))
              pts))
          (setq minproj (apply 'min proj) maxproj (apply 'max proj))
          (setq i 0)
          (repeat n
            (setq p1p (nth i proj)
                  p2p (nth (rem (1+ i) n) proj)
                  midp (* 0.5 (+ p1p p2p)))
            (setq dist (abs (- midp minproj)))
            (if (or (null best-min) (< dist best-min))
              (setq best-min dist s1 i))
            (setq dist (abs (- midp maxproj)))
            (if (or (null best-max) (< dist best-max))
              (setq best-max dist s2 i))
            (setq i (1+ i)))))
      ;; respaldo: sin eje dominante o si los extremos colapsan en el
      ;; mismo segmento (o en dos adyacentes, que no separan cadenas)
      (if (or (null s1) (null s2) (= s1 s2)
              (= (rem (1+ s1) n) s2) (= (rem (1+ s2) n) s1))
        (progn
          (setq segs nil i 0)
          (repeat n
            (setq segs
              (cons (cons i (distance
                              (list (car (nth i pts)) (cadr (nth i pts)))
                              (list (car (nth (rem (1+ i) n) pts))
                                    (cadr (nth (rem (1+ i) n) pts)))))
                segs))
            (setq i (1+ i)))
          (setq segs (vl-sort segs '(lambda (x y) (< (cdr x) (cdr y)))))
          (setq s1 (car (nth 0 segs)) s2 (car (nth 1 segs)))
          ;; si las dos mas cortas son adyacentes no separan dos cadenas:
          ;; probar con la siguiente mas corta
          (setq i 2)
          (while (and (< i n)
                      (or (= (rem (1+ s1) n) s2) (= (rem (1+ s2) n) s1)))
            (setq s2 (car (nth i segs)) i (1+ i)))))
      (if (or (= s1 s2) (= (rem (1+ s1) n) s2) (= (rem (1+ s2) n) s1))
        nil
        (list s1 s2))))
)

;; 5.6.2 (anden curvo real DD2CA, 251 vertices): en una punta OBLICUA la
;; proyeccion sobre el eje elige un segmento diminuto vecino (0.22 m) en vez
;; de la punta real (3.80 m = ancho). El segundo costado arrastraba la punta
;; doblada, su OFFSET fallaba y el anden recortado perdia el sobreancho.
;; Si la punta elegida mide menos de medio ancho (ancho = 2 area/perimetro),
;; se toma el vecino (hasta 4 segmentos) cuya longitud mas se acerca al ancho.
(defun urb:costado-tips-refine (pts tips / n i a b area per w lens rest best bd d out k other s)
  ;; longitudes y area en UNA pasada (sin nth dentro del ciclo)
  (setq n (length pts) area 0.0 per 0.0 rest (append pts (list (car pts))))
  (while (cdr rest)
    (setq a (car rest) b (cadr rest)
          d (distance (list (car a) (cadr a)) (list (car b) (cadr b)))
          lens (cons d lens) per (+ per d)
          area (+ area (- (* (car a) (cadr b)) (* (car b) (cadr a))))
          rest (cdr rest)))
  (setq lens (reverse lens)
        w (if (> per 0.0) (/ (abs area) per) 0.0))
  (if (or (null tips) (<= w 1e-6) (/= (length tips) 2))
    tips
    (progn
      (setq out tips)
      (foreach s tips
        (if (< (nth s lens) (* 0.5 w))
          (progn
            (setq other (if (= s (car out)) (cadr out) (car out)) best nil bd nil k -4)
            (while (<= k 4)
              (setq i (rem (+ s k n) n))
              (if (and (/= i other)
                       (/= (rem (1+ i) n) other) (/= (rem (1+ other) n) i)
                       (>= (nth i lens) (* 0.5 w)) (<= (nth i lens) (* 2.0 w)))
                (progn
                  (setq d (abs (- (nth i lens) w)))
                  (if (or (null bd) (< d bd)) (setq bd d best i))))
              (setq k (1+ k)))
            (if best
              (setq out (subst best s out))))))
      out)))

;; divide el contorno CERRADO en sus dos costados: quitando las dos
;; PUNTAS (urb:costado-tip-segments) quedan dos cadenas de vertices (los
;; lados largos). Devuelve (cadena-a cadena-b) -- cada una lista de
;; puntos 2D -- o nil si el poligono no da para separar dos cadenas
;; (triangulo, forma muy irregular).
;; 2026-08-26 (reporte del usuario con pantallazo: en contornos CURVOS
;; el costado salia RECTO cruzando el area): las cadenas conservan el
;; BULGE de cada segmento -- cada vertice es (x y bulge), donde bulge es
;; el del segmento que SALE de ese vertice. Antes solo se leian los
;; codigos 10 y el prefabricado se construia con segmentos rectos.
(defun urb:poly-costado-chains (ename / ed pts cur n i tips s1 s2 tmp a b
                                idx last-a last-b)
  (setq ed (entget ename) pts nil cur nil)
  (foreach itm ed
    (cond
      ((= (car itm) 10)
        (if cur (setq pts (cons cur pts)))
        (setq cur (list (car (cdr itm)) (cadr (cdr itm)) 0.0)))
      ((= (car itm) 42)
        (if cur
          (setq cur (list (car cur) (cadr cur) (cdr itm)))))))
  (if cur (setq pts (cons cur pts)))
  (setq pts (reverse pts) n (length pts))
  (if (< n 4)
    nil
    (progn
      ;; 2026-09-08 (foto del usuario: bordillos recorriendo las puntas):
      ;; un entrante profundo suma dos caras transversales y puede hacer que
      ;; la familia de aristas transversales pese mas que los dos costados.
      ;; El eje de la envolvente orientada conserva la direccion LONGITUDINAL
      ;; del anden aunque el contorno rodee un contenedor.
      (setq tips
        (urb:costado-tips-refine pts
          (urb:costado-tip-segments pts (urb:anden-axis-angle pts))))
      (if (null tips)
        nil
        (progn
          (setq s1 (car tips) s2 (cadr tips))
          (if (> s1 s2) (setq tmp s1 s1 s2 s2 tmp))
          (setq a nil idx (1+ s1))
          (while (<= idx s2)
            (setq a (cons (nth idx pts) a) idx (1+ idx)))
          (setq b nil idx (1+ s2))
          (while (<= idx (+ s1 n))
            (setq b (cons (nth (rem idx n) pts) b) idx (1+ idx)))
          (setq a (reverse a) b (reverse b))
          ;; el bulge del ULTIMO vertice de cada cadena pertenece al
          ;; segmento de la punta cortada -- se anula
          (if a
            (progn
              (setq last-a (last a))
              (setq a (append (reverse (cdr (reverse a)))
                (list (list (car last-a) (cadr last-a) 0.0))))))
          (if b
            (progn
              (setq last-b (last b))
              (setq b (append (reverse (cdr (reverse b)))
                (list (list (car last-b) (cadr last-b) 0.0))))))
          (if (and (>= (length a) 2) (>= (length b) 2))
            (list a b)
            nil))))))

;; longitud REAL de la cadena, arcos incluidos: cuerda c con bulge b ->
;; theta = 4*atan|b|, arco = c * theta / (2*sin(theta/2))
(defun urb:poly-chain-length (pts / l i c b theta)
  (setq l 0.0 i 0)
  (while (< i (1- (length pts)))
    (setq c (distance
              (list (car (nth i pts)) (cadr (nth i pts)))
              (list (car (nth (1+ i) pts)) (cadr (nth (1+ i) pts)))))
    (setq b (abs (if (caddr (nth i pts)) (caddr (nth i pts)) 0.0)))
    (if (> b 1e-8)
      (progn
        (setq theta (* 4.0 (atan b)))
        (setq l (+ l (/ (* c theta) (* 2.0 (sin (/ theta 2.0)))))))
      (setq l (+ l c)))
    (setq i (1+ i)))
  l)

(defun urb:poly-chain-mid (pts / p0 pn)
  (setq p0 (car pts) pn (last pts))
  (list (/ (+ (car p0) (car pn)) 2.0) (/ (+ (cadr p0) (cadr pn)) 2.0)))

(defun urb:poly-chain-polyline (pts / data i p)
  (setq data
    (list '(0 . "LWPOLYLINE") '(100 . "AcDbEntity")
      '(100 . "AcDbPolyline") (cons 90 (length pts)) '(70 . 0)))
  (setq i 0)
  (repeat (length pts)
    (setq p (nth i pts))
    (setq data
      (append data
        (list (cons 10 (list (car p) (cadr p)))
              (cons 42 (if (caddr p) (caddr p) 0.0)))))
    (setq i (1+ i)))
  (entmakex data))

;; ---------- 2026-09-08 (pedido del usuario: "alrededor del contenedor
;; de raices no va ningun prefabricado"): el costado se INTERRUMPE donde
;; se cruza con un contenedor. Sirve igual si el usuario dibujo un
;; entrante para rodearlo (la cadena entra al hueco) que si dibujo el
;; contorno derecho (la cadena pasa por encima del contenedor): en los
;; dos casos el tramo cubierto por el contenedor se quita y el
;; prefabricado queda partido en los tramos utiles.

;; esquinas en MUNDO de un contenedor insertado. El bloque se define con
;; la esquina de insercion en (0,0), el LARGO sobre el eje X local y el
;; ANCHO hacia +Y o -Y segun el lado elegido (xdata URB_MOBILIARIO:
;; codigo lado angulo). Sin xdata o sin catalogo devuelve nil y el
;; contenedor simplemente no recorta (comportamiento anterior).
(defun urb:contenedor-corners (be / d entry obj ins ang a l y0 y1 c s)
  (setq d (urb:get-xdata-strings be "URB_MOBILIARIO"))
  (setq entry (if d (assoc (car d) *urb-mob-tipos*) nil))
  (setq obj (urb:as-vla-object be))
  (if (and entry obj (= (nth 3 entry) "CONTEN"))
    (progn
      (setq ins
        (vl-catch-all-apply
          '(lambda ()
            (vlax-safearray->list
              (vlax-variant-value (vla-get-InsertionPoint obj))))))
      (setq ang (vl-catch-all-apply '(lambda () (vla-get-Rotation obj))))
      (if (or (vl-catch-all-error-p ins) (vl-catch-all-error-p ang))
        nil
        (progn
          (setq a (nth 4 entry) l (nth 5 entry))
          (setq y0 (if (and (> (length d) 1)
                            (urb:string-equal-p (nth 1 d) "IZQUIERDA"))
                     (- a) 0.0))
          (setq y1 (if (and (> (length d) 1)
                            (urb:string-equal-p (nth 1 d) "IZQUIERDA"))
                     0.0 a))
          (setq c (cos ang) s (sin ang))
          (mapcar
            '(lambda (p)
              (list (+ (car ins) (- (* c (car p)) (* s (cadr p))))
                    (+ (cadr ins) (+ (* s (car p)) (* c (cadr p))))))
            (list (list 0.0 y0) (list l y0) (list l y1) (list 0.0 y1))))))
    nil))

(defun urb:contenedor-polys (/ ss i poly out)
  (setq ss (ssget "_X" '((0 . "INSERT") (2 . "URB_MOB_CONT*"))) i 0)
  (if ss
    (repeat (sslength ss)
      (setq poly (urb:contenedor-corners (ssname ss i)))
      (if poly (setq out (cons poly out)))
      (setq i (1+ i))))
  out)

;; parametros t (0..1) donde el segmento p1->p2 cruza las aristas del
;; poligono. Funcion PURA.
(defun urb:segment-poly-cuts (p1 p2 poly / n i q1 q2 rx ry sx sy den t1 t2 out)
  (setq n (length poly) i 0
        rx (- (car p2) (car p1)) ry (- (cadr p2) (cadr p1)))
  (repeat n
    (setq q1 (nth i poly) q2 (nth (rem (1+ i) n) poly))
    (setq sx (- (car q2) (car q1)) sy (- (cadr q2) (cadr q1)))
    (setq den (- (* rx sy) (* ry sx)))
    (if (> (abs den) 1e-12)
      (progn
        (setq t1 (/ (- (* (- (car q1) (car p1)) sy)
                       (* (- (cadr q1) (cadr p1)) sx)) den))
        (setq t2 (/ (- (* (- (car q1) (car p1)) ry)
                       (* (- (cadr q1) (cadr p1)) rx)) den))
        (if (and (> t1 1e-9) (< t1 (- 1.0 1e-9))
                 (> t2 -1e-9) (< t2 (+ 1.0 1e-9)))
          (setq out (cons t1 out)))))
    (setq i (1+ i)))
  (vl-sort out '<))

;; T si dos poligonos 2D tienen area comun. Se prueban vertices contenidos
;; y cruces de aristas; el contacto tangencial aislado no obliga a regenerar.
;; Funcion pura, usada como filtro preciso antes de explotar un anden.
(defun urb:polygons-overlap-2d-p (first second / n i p1 p2 found)
  (setq found
    (or
      (vl-some '(lambda (p) (urb:point-in-poly-2d p second)) first)
      (vl-some '(lambda (p) (urb:point-in-poly-2d p first)) second)))
  (if (not found)
    (progn
      (setq n (length first) i 0)
      (while (and (< i n) (not found))
        (setq p1 (nth i first)
              p2 (nth (rem (1+ i) n) first))
        (if (urb:segment-poly-cuts p1 p2 second) (setq found T))
        (setq i (1+ i)))))
  found)

;; Andenes empaquetados del dibujo, incluidos los antiguos que solo se
;; reconocen por nombre de bloque. La lista se deduplica por ename.
(defun urb:all-anden-blocks (/ filter ss i en out)
  (foreach filter
    '(((0 . "INSERT") (-3 ("URB_ANDEN_BLOCK")))
      ((0 . "INSERT") (2 . "URB_ANDEN_*")))
    (if (setq ss (ssget "_X" filter))
      (progn
        (setq i 0)
        (repeat (sslength ss)
          (setq en (ssname ss i))
          (if (and (not (member en out)) (urb:anden-block-p en))
            (setq out (cons en out)))
          (setq i (1+ i))))))
  (reverse out))

(defun urb:container-overlaps-anden-p (container anden / co ao boundary region cutter res area)
  (setq co (urb:as-vla-object container)
        ao (urb:as-vla-object anden))
  (if (and co ao (urb:objects-bbox-overlap-p co ao 0.02)
           (setq boundary (urb:explode-anden-block-boundary anden)))
    (progn
      ;; Explode respeta traslacion/rotacion del INSERT; leer la definicion
      ;; directamente comparaba coordenadas locales con puntos del mundo.
      (setq region (urb:add-region-from-object (urb:as-vla-object boundary))
            cutter (urb:block-footprint-region co))
      (if (and region cutter)
        (progn
          (urb:region-align-elevation cutter region)
          (setq res (vl-catch-all-apply 'vla-Boolean (list region 1 cutter)))
          (if (not (vl-catch-all-error-p res))
            (setq area (vl-catch-all-apply 'vla-get-Area (list region))))))
      (if region (urb:safe-delete region))
      (if cutter (urb:safe-delete cutter))
      (urb:cleanup-working-boundary boundary)))
  (and (numberp area) (> area 1e-8)))

;; Reconstruccion transaccional de un anden ya empaquetado. Solo se borra
;; el original cuando el bloque nuevo quedo completo. El movimiento de
;; tierras previo NO se copia: el recorte cambia el area y conservar esos
;; volumenes seria presentar cantidades obsoletas como validas.
;; 5.6.2: movimiento de tierras de un anden SIN interaccion. Solo corre si
;; hay una via creada a <= 10 m (su rasante completa); nunca abre un
;; selector en medio de otro comando. Devuelve T si quedo calculado.
(defun urb:recalc-earthworks-silent (block-ename / pts road r)
  (setq pts (vl-catch-all-apply 'urb:anden-earthwork-points (list block-ename)))
  (if (vl-catch-all-error-p pts) (setq pts nil))
  (setq road (if pts (urb:anden-road-autodetect pts)))
  (if road
    (progn
      (setq r (vl-catch-all-apply 'urb:run-anden-earthworks
                (list block-ename nil 0.0 "SUP_TN" "Via creada")))
      (if (and r (not (vl-catch-all-error-p r)))
        (progn (prompt "\nMovimiento de tierras del anden recortado: recalculado con la via.") T)
        (progn (prompt "\nMovimiento de tierras del anden recortado: no se pudo recalcular (EDITAR).") nil)))
    (progn
      (prompt "\nAnden recortado sin via creada al lado: su movimiento de tierras queda PENDIENTE (EDITAR).")
      nil)))

(defun urb:recut-one-anden-for-container
  (ename / data material etapa sub guia toperol format calculate surface
   grade-source pattern old-h old-mov boundary block-ref new-ename deleted)
  (setq data (urb:anden-block-data ename)
        material (urb:safe-string (nth 1 data) "LOSETA")
        etapa (urb:safe-string (nth 2 data) "1")
        sub (urb:safe-string (nth 3 data) etapa)
        guia (urb:safe-string (nth 7 data) "No")
        toperol (urb:safe-string (nth 8 data) "No")
        format (urb:safe-string (nth 9 data) "40 x 40 cm")
        calculate (urb:safe-string (nth 10 data) "Si")
        surface (urb:safe-string (nth 11 data) "SUP_TN")
        grade-source (urb:safe-string (nth 12 data) "Via creada")
        pattern (urb:anden-pattern-mode ename)
        old-h (cdr (assoc 5 (entget ename)))
        old-mov (urb:get-xdata-strings ename "URB_ANDEN_MOV"))
  (setq boundary
    (urb:call-edit-stage "extraer contorno para contenedor"
      'urb:explode-anden-block-boundary (list ename)))
  (if boundary
    (progn
      (urb:set-anden-pattern-mode boundary pattern)
      (setq block-ref
        (urb:rebuild-working-boundary boundary material etapa sub guia
          toperol format calculate surface grade-source))))
  (if block-ref
    (progn
      (urb:copy-quantity-scope ename block-ref)
      (setq new-ename (urb:as-ename block-ref)
            deleted
              (urb:call-edit-stage "reemplazar anden recortado"
                'urb:delete-anden-block (list ename)))
      (if deleted
        (progn
          (if (and old-h new-ename)
            (urb:relink-anden-anillos old-h
              (cdr (assoc 5 (entget new-ename)))))
          ;; 5.6.2 (pedido del usuario: "que al sobreponer la rampa o el paso
          ;; se corte el anden y se recalcule el movimiento de tierras y el
          ;; resto de cantidades"). Las cantidades ya salian del bloque
          ;; regenerado, pero el corte/relleno se PERDIA: el bloque nuevo
          ;; nacia sin URB_ANDEN_MOV. Se recalcula sin pedir clics cuando
          ;; hay via creada al lado; si no, queda pendiente y se avisa.
          (if (and new-ename (urb:yes-p calculate))
            (urb:recalc-earthworks-silent new-ename))
          (list new-ename (if (urb:valid-anden-earthworks-data-p old-mov) T nil)))
        (progn
          (if new-ename (urb:delete-anden-block new-ename))
          nil)))
    nil))

;; Devuelve (actualizados movimiento-pendiente fallidos). El filtro
;; geometrico evita tocar andenes cuya caja envolvente coincide pero cuya
;; superficie no es atravesada por el contenedor.
;; Poligono(s) de la huella de un bloque CORTADOR. Para un contenedor de
;; raices se conserva el camino exacto por catalogo; para cualquier otro
;; bloque -- un modulo de paso peatonal o de rampa, por ejemplo -- se saca
;; de su huella real. 2026-09-10: sin esto, urb:recut-prefab-for-container
;; le pedia urb:contenedor-corners a un modulo de paso, recibia nil y no
;; recortaba NINGUN sardinel (reporte del usuario con foto).
(defun urb:cutter-polygons (cutter / poly reg polys)
  (setq poly (vl-catch-all-apply 'urb:contenedor-corners (list cutter)))
  (if (and (not (vl-catch-all-error-p poly)) poly)
    (list poly)
    (progn
      (setq reg (vl-catch-all-apply 'urb:block-footprint-region
                  (list (urb:as-vla-object cutter))))
      (if (or (vl-catch-all-error-p reg) (null reg))
        nil
        (progn
          (setq polys (vl-catch-all-apply 'urb:region-polygons (list reg)))
          (urb:safe-delete reg)
          (if (vl-catch-all-error-p polys) nil polys))))))

(defun urb:recut-prefab-for-container
  (en container / data ext ref side pts item parts oldlen newlen piece built
   refs good link elevation result pwidth polys)
  (setq data (urb:prefab-data en)
        ext (urb:extract-prefab-reference en (nth 0 data) (nth 5 data)))
  (if ext
    (progn
      (setq ref (car ext) side (cadr ext)
            elevation (cdr (assoc 38 (entget ref)))
            pwidth (atof (nth 3 data))
            link (urb:get-xdata-strings en "URB_PREFAB_ANILLO"))
      (setq polys (urb:cutter-polygons container))
      (if (null polys)
        (prompt "\nNo se pudo obtener la huella del elemento que corta; el prefabricado queda intacto.")
        (progn
          ;; 2026-09-10: el prefabricado CURVO ya no se salta. Antes se
          ;; avisaba "recorte por contenedor pendiente" y el sardinel de
          ;; una via en curva quedaba entero por debajo del paso peatonal.
          ;; Se recorta sobre el muestreo fino del arco (el mismo que usa
          ;; la franja tactil): la longitud sale de las cuerdas finas, no
          ;; del arco exacto, con error muy por debajo del centimetro.
          (if (urb:lwpoly-has-arcs-p ref)
            (setq pts
              (mapcar '(lambda (p) (list (car p) (cadr p) 0.0))
                (urb:lwpoly-points-with-arcs-fine ref)))
            (progn
              (foreach item (entget ref)
                (if (= (car item) 10)
                  (setq pts (cons (list (cadr item) (caddr item) 0.0) pts))))
              (setq pts (reverse pts))))
          (setq parts (urb:chain-split-por-poligonos pts polys)
                oldlen (urb:poly-chain-length pts) newlen 0.0)
          (foreach piece parts (setq newlen (+ newlen (urb:poly-chain-length piece))))
          (if (< newlen (- oldlen 1e-6))
            (progn
              (setq good T)
              (foreach piece parts
                (setq built (urb:poly-chain-polyline piece))
                (if elevation (vla-put-Elevation (urb:as-vla-object built) elevation))
                (setq built (vl-catch-all-apply 'urb:build-prefab-from-reference
                  (list built side (nth 0 data) pwidth (nth 1 data) (nth 2 data)
                    (nth 5 data) (urb:safe-string (nth 7 data) "Anden"))))
                (if (or (null built) (vl-catch-all-error-p built))
                  (setq good nil)
                  (progn
                    (setq refs (cons built refs))
                    (urb:copy-quantity-scope en built)
                    (if link (urb:set-xdata-strings (urb:as-ename built)
                      "URB_PREFAB_ANILLO" link)))))
              (if (and good (urb:safe-delete (urb:as-vla-object en)))
                (setq result T)
                (foreach built refs (urb:safe-delete built)))))))
      (if (entget ref) (entdel ref))))
  result)

(defun urb:recut-prefabs-for-container (container / ss i en result count)
  (setq ss (ssget "_X" '((0 . "INSERT") (-3 ("URB_PREFAB_BLOCK")))) i 0 count 0)
  (if ss
    (repeat (sslength ss)
      (setq en (ssname ss i) i (1+ i))
      (if (urb:objects-bbox-overlap-p (urb:as-vla-object en)
                                    (urb:as-vla-object container) 0.02)
        (progn
          (setq result (vl-catch-all-apply 'urb:recut-prefab-for-container
                         (list en container)))
          (cond
            ((vl-catch-all-error-p result)
              (prompt (strcat "\nNo se recorto prefabricado: "
                (vl-catch-all-error-message result))))
            (result (setq count (1+ count))))))))
  (if (> count 0) (prompt (strcat "\nPrefabricados recortados: " (itoa count))))
  count)

;;; ---------------------------------------------------------------------
;;; Recorte de lo que queda DEBAJO de un elemento nuevo (2026-09-10, pedido
;;; del usuario: "si dibujo un paso peatonal sobre algo que ya esta
;;; dibujado, que me borre lo que quedaria por debajo, para que no quede
;;; doble area"). Reutiliza la maquinaria que ya existia para los
;;; contenedores de raices: el bloque nuevo entra como CORTADOR en
;;; urb:anden-cutout-blocks y los vecinos se reconstruyen recortados.
;;; La zona verde es la unica pieza que faltaba: aqui va.
;;; ---------------------------------------------------------------------

;; Zonas verdes existentes en el dibujo.
(defun urb:all-green-blocks (/ ss i en out)
  (setq ss (ssget "_X" '((0 . "INSERT") (-3 ("URB_GREEN_BLOCK")))) i 0)
  (if ss
    (repeat (sslength ss)
      (setq en (ssname ss i) i (1+ i))
      (if (not (member en out)) (setq out (cons en out)))))
  (reverse out))

;; Recorta UNA zona verde contra los cortadores vigentes. Devuelve el area
;; nueva, o nil si no se pudo (en ese caso la zona queda intacta).
;; Arma una zona verde nueva a partir de un bucle (punto . bulge) --
;; conservando los ARCOS del contorno original, que es lo que se perdia
;; cuando solo se pasaban los puntos.
(defun urb:build-green-from-points (loop etapa sub esp / en obj hatch ref verts)
  (setq verts nil)
  (foreach v loop
    (setq verts
      (cons (cons 42 (if (numberp (cdr v)) (cdr v) 0.0))
        (cons (cons 10 (list (car (car v)) (cadr (car v)))) verts))))
  (setq verts (reverse verts))
  (setq en
    (entmakex
      (append
        (list '(0 . "LWPOLYLINE") '(100 . "AcDbEntity") '(100 . "AcDbPolyline")
              (cons 90 (length loop)) '(70 . 1) '(8 . "URB-ZONA-VERDE"))
        verts)))
  (if (null en)
    nil
    (progn
      (setq obj (urb:as-vla-object en))
      (vla-put-Color obj 256)
      (setq hatch
        (vl-catch-all-apply 'urb:add-hatch
          (list obj "URB-ZONA-VERDE" "SOLID" 1 "SOLID" 1.0 3)))
      (if (vl-catch-all-error-p hatch) (setq hatch nil))
      (if (and hatch (vlax-property-available-p hatch 'EntityTransparency T))
        (vl-catch-all-apply 'vlax-put-property
          (list hatch 'EntityTransparency "70")))
      (setq ref
        (vl-catch-all-apply 'urb:package-green-zone
          (list en hatch etapa sub esp)))
      (if (or (vl-catch-all-error-p ref) (null ref))
        (progn
          (urb:safe-delete obj)
          (if hatch (urb:safe-delete hatch))
          nil)
        ref))))

;; Recorta UNA zona verde contra los cortadores vigentes. Si el corte la
;; parte en varios pedazos (un paso peatonal que la cruza de lado a lado),
;; se crea UNA zona verde por pedazo -- si se conservara solo el mayor se
;; perderia area en silencio. Devuelve cuantas zonas quedaron, o nil.
;; 5.6.2: corte/relleno de una zona verde sin interaccion (via creada a
;; <= 10 m, su rasante completa hasta el espesor de tierra negra)
(defun urb:green-earthworks-silent (block pts esp / road ref pl mov p)
  (setq road (urb:anden-road-autodetect pts))
  (if road
    (progn
      (setq ref (urb:anden-road-grade-for road))
      (if ref
        (progn
          (entmake (append (list '(0 . "LWPOLYLINE") '(100 . "AcDbEntity") '(100 . "AcDbPolyline")
                                 (cons 90 (length pts)) '(70 . 1))
                           (mapcar '(lambda (p) (cons 10 (list (car p) (cadr p)))) pts)))
          (setq pl (entlast))
          (setq mov (urb:earthworks-from-picks pl
                      (list (list 0.0 (list (car (car pts)) (cadr (car pts))) ref)) esp))
          (entdel pl)
          (if mov
            (progn
              (urb:set-block-attribute block "CORTE_M3" (rtos (car mov) 2 2))
              (urb:set-block-attribute block "RELLENO_M3" (rtos (cadr mov) 2 2))
              (prompt (strcat "\nZona verde recortada: corte " (rtos (car mov) 2 2)
                " m3 | relleno " (rtos (cadr mov) 2 2) " m3 (via adyacente)."))
              mov))))
      nil)
    (progn
      (prompt "\nZona verde recortada sin via al lado: su corte/relleno queda en cero hasta recalcularlo.")
      nil)))

(defun urb:recut-one-green (ename / data etapa sub esp boundary loops refs r)
  (setq data (urb:green-zone-data ename)
        etapa (urb:safe-string (nth 1 data) "1")
        sub (urb:safe-string (nth 2 data) etapa)
        esp (atof (urb:safe-string (nth 5 data) "0.20")))
  (setq boundary (urb:explode-green-block-boundary ename))
  (if (null boundary)
    nil
    (progn
      (setq loops (vl-catch-all-apply 'urb:clip-poly-loops (list boundary 0.05)))
      (urb:safe-delete (urb:as-vla-object boundary))
      (if (or (vl-catch-all-error-p loops) (null loops))
        nil
        (progn
          (foreach pts loops
            (setq r (urb:build-green-from-points pts etapa sub esp))
            (if r
              (progn
                ;; 5.6.2: el corte/relleno de la zona recortada se perdia;
                ;; se recalcula sobre la zona nueva si hay via al lado
                (vl-catch-all-apply 'urb:green-earthworks-silent (list r pts esp))
                (setq refs (cons r refs)))))
          (if (null refs)
            nil
            (progn
              (foreach r refs (urb:copy-quantity-scope ename r))
              (if (urb:delete-anden-block ename)
                (length refs)
                (progn
                  (foreach r refs (urb:delete-anden-block (urb:as-ename r)))
                  nil)))))))))

;; Desempaca una zona verde: devuelve su contorno crudo. Mismo criterio de
;; la via y el anden -- la polilinea CERRADA de mayor area, no la ultima.
(defun urb:explode-green-block-boundary (ename / obj exploded objects item
                                         boundary candidatos)
  (setq obj (urb:as-vla-object ename))
  (setq exploded (vl-catch-all-apply 'vla-Explode (list obj)))
  (if (vl-catch-all-error-p exploded)
    nil
    (progn
      (setq objects (urb:variant-object-list exploded))
      (foreach item objects
        (if (member (vla-get-ObjectName item)
                    '("AcDbPolyline" "AcDb2dPolyline"))
          (setq candidatos (cons item candidatos))))
      (setq boundary (urb:largest-closed-polyline (reverse candidatos)))
      (foreach item objects
        (if (not (eq item boundary)) (urb:safe-delete item)))
      (if boundary (vlax-vla-object->ename boundary)))))

;; Recorta TODO lo que quede debajo del bloque recien creado: andenes,
;; zonas verdes y prefabricados. Devuelve (andenes zonas prefabricados).
(defun urb:recut-vecinos-bajo (cutter / co n-and n-green res)
  (setq co (urb:as-vla-object cutter) n-and 0 n-green 0)
  (if (null co)
    (list 0 0 0)
    (progn
      (urb:recut-prefabs-for-container cutter)
      (foreach en (urb:all-anden-blocks)
        (if (urb:container-overlaps-anden-p cutter en)
          (progn
            (setq res (vl-catch-all-apply 'urb:recut-one-anden-for-container
                        (list en)))
            (if (and (not (vl-catch-all-error-p res)) res)
              (setq n-and (1+ n-and))))))
      (foreach en (urb:all-green-blocks)
        (if (and (urb:as-vla-object en)
                 (urb:objects-bbox-overlap-p co (urb:as-vla-object en) 0.02))
          (progn
            (setq res (vl-catch-all-apply 'urb:recut-one-green (list en)))
            (if (and (not (vl-catch-all-error-p res)) res)
              (setq n-green (1+ n-green))))))
      (list n-and n-green 0))))

(defun urb:recut-andenes-for-container (container / en result updated pending failed)
  (setq updated 0 pending 0 failed 0)
  (urb:recut-prefabs-for-container container)
  (foreach en (urb:all-anden-blocks)
    (if (urb:container-overlaps-anden-p container en)
      (progn
        (setq result
          (vl-catch-all-apply 'urb:recut-one-anden-for-container (list en)))
        (if (or (vl-catch-all-error-p result) (null result))
          (setq failed (1+ failed))
          (progn
            (setq updated (1+ updated))
            (if (cadr result) (setq pending (1+ pending))))))))
  (list updated pending failed))

;; T si el punto cae DENTRO del poligono o a menos de tol de su borde.
;; La tolerancia es la que hace que un costado que corre TANGENTE al
;; contenedor (su borde coincide con el del anden) tambien se recorte:
;; sin ella el punto medio queda justo sobre la arista y el test de
;; interior lo da por afuera. Funcion PURA.
(defun urb:point-near-poly-p (pt poly tol / n i q1 q2 cerca)
  (if (urb:point-in-poly-2d pt poly)
    T
    (progn
      (setq n (length poly) i 0)
      (while (and (< i n) (null cerca))
        (setq q1 (nth i poly) q2 (nth (rem (1+ i) n) poly))
        (if (<= (urb:dist-point-seg pt q1 q2) tol) (setq cerca T))
        (setq i (1+ i)))
      cerca)))

;; corta una cadena (lista de (x y bulge)) quitando los tramos cubiertos
;; por alguno de los poligonos. Devuelve una LISTA de cadenas. Funcion
;; PURA (no toca el dibujo) para poder probarla sin crear entidades.
;; Los segmentos en ARCO (bulge) no se cortan: se conservan enteros.
(defun urb:chain-split-por-poligonos (pts polys / out cur i p1 p2 b cuts
                                      prev tt mid pa pb dentro)
  (defun urb:--pt-at (p1 p2 tt)
    (list (+ (car p1) (* tt (- (car p2) (car p1))))
          (+ (cadr p1) (* tt (- (cadr p2) (cadr p1))))
          0.0))
  (defun urb:--push (p)
    (if (or (null cur)
            (not (urb:point-near-2d-p p (car cur) 1e-8)))
      (setq cur (cons p cur))))
  (defun urb:--close ()
    (if (and cur (>= (length cur) 2)) (setq out (cons (reverse cur) out)))
    (setq cur nil))
  (setq i 0)
  (while (< i (1- (length pts)))
    (setq p1 (nth i pts) p2 (nth (1+ i) pts)
          b (if (caddr p1) (caddr p1) 0.0))
    (if (or (null polys) (> (abs b) 1e-8))
      ;; arco o sin contenedores: el segmento va completo
      (progn (urb:--push p1) (urb:--push p2))
      (progn
        (setq cuts nil)
        (foreach poly polys
          (setq cuts (append cuts (urb:segment-poly-cuts p1 p2 poly))))
        (setq cuts (vl-sort (append '(0.0) cuts '(1.0)) '<))
        (setq prev nil)
        (foreach tt cuts
          (if prev
            (progn
              (setq mid (* 0.5 (+ prev tt)))
              (setq pa (urb:--pt-at p1 p2 prev)
                    pb (urb:--pt-at p1 p2 tt))
              (setq dentro
                (vl-some
                  '(lambda (poly)
                    (urb:point-near-poly-p
                      (list (car (urb:--pt-at p1 p2 mid))
                            (cadr (urb:--pt-at p1 p2 mid)))
                      poly 0.02))
                  polys))
              (if dentro
                (urb:--close)
                (progn (urb:--push pa) (urb:--push pb)))))
          (setq prev tt))))
    (setq i (1+ i)))
  (urb:--close)
  (reverse out))

;; construye el prefabricado de UN costado como bloque (uno por cada
;; tramo util si un contenedor lo parte). El lado de crecimiento se
;; decide con la tangente local y el sentido del contorno, sin depender
;; de un centroide global que puede caer fuera de un sendero concavo.
;; Devuelve (longitud-total lista-de-referencias) o nil
;; (2026-08-24 v2: la referencia la necesita el anden para el vinculo de
;; descuento URB_PREFAB_ANILLO).
(defun urb:chain-slice-exact (en d1 d2 / vb start finish cursor next idx p b a out len)
  ;; Cortar por estacion conservando vertices y bulges originales. Un arco
  ;; de 565 m sigue siendo un arco; antes se convertia en 2260 segmentos.
  (setq len (urb:curve-length en)
        d1 (max 0.0 (min len d1)) d2 (max 0.0 (min len d2)))
  (if (> (- d2 d1) 1e-7)
    (progn
      (setq vb (urb:lwpoly-vertex-bulges en)
            start (vlax-curve-getParamAtDist en d1)
            finish (vlax-curve-getParamAtDist en d2)
            cursor start)
      (while (< cursor (- finish 1e-10))
        (setq idx (fix cursor) next (min finish (float (1+ idx)))
              p (vlax-curve-getPointAtParam en cursor)
              b (nth idx (cadr vb))
              a (* (atan b) (- next cursor)))
        (setq out (cons (list (car p) (cadr p) (/ (sin a) (cos a))) out)
              cursor next))
      (setq p (vlax-curve-getPointAtDist en d2))
      (reverse (cons (list (car p) (cadr p) 0.0) out)))))

(defun urb:prefab-split-exact (pts polys / en obj poly pe po hits cuts hit st len
                                    prev cur mid out result)
  ;; Intersecciones nativas con los contenedores: las partes utiles siguen
  ;; siendo arcos exactos, incluso si un contenedor corta en mitad del arco.
  (if (null polys) (list pts)
    (progn
      (setq en (urb:poly-chain-polyline pts) obj (urb:as-vla-object en)
            len (urb:curve-length en) cuts (list 0.0 len))
      (setq result (vl-catch-all-apply
        '(lambda ()
          (foreach poly polys
            (setq pe (urb:poly-chain-polyline
              (mapcar '(lambda (p) (list (car p) (cadr p) 0.0)) poly))
                  po (urb:as-vla-object pe))
            (vla-put-Closed po :vlax-true)
            (if (urb:objects-bbox-overlap-p obj po 0.02)
              (progn
                (setq hits (vlax-invoke obj 'IntersectWith po 0))
                (while hits
                  (setq hit (list (car hits) (cadr hits) (caddr hits))
                        st (vlax-curve-getDistAtPoint en
                          (vlax-curve-getClosestPointTo en hit)))
                  (if st (setq cuts (cons st cuts)))
                  (setq hits (cdddr hits)))))
            (urb:safe-delete po) (setq po nil))
          (setq cuts (vl-sort cuts '<) prev (car cuts))
          (foreach cur (cdr cuts)
            (if (> (- cur prev) 1e-7)
              (progn
                (setq mid (urb:curve-pt en (* 0.5 (+ prev cur))))
                (if (not (vl-some '(lambda (poly)
                      (urb:point-near-poly-p mid poly 0.02)) polys))
                  (setq out (cons (urb:chain-slice-exact en prev cur) out)))))
            (setq prev cur))
          (reverse out))))
      (urb:safe-delete po)
      (urb:safe-delete obj)
      (if (vl-catch-all-error-p result)
        (vl-exit-with-error (vl-catch-all-error-message result)) result))))

(defun urb:poly-costado-build (pts tipo posicion etapa sub winding destino
                               / tramos en mid side ancho ref len total refs normal)
  (setq tramos
    (vl-catch-all-apply
      '(lambda () (urb:prefab-split-exact pts (urb:contenedor-polys)))))
  (if (vl-catch-all-error-p tramos)
    (progn
      (urb:bb-log (strcat "prefabricado: fallo al recortar contenedores: "
        (vl-catch-all-error-message tramos)))
      (setq tramos nil)))
  (setq total 0.0 refs nil ancho (urb:prefab-default-ancho tipo))
  (foreach pts tramos
    (setq en (urb:poly-chain-polyline pts))
    (if en
      (progn
        (setq len (urb:poly-chain-length pts))
        ;; Las cadenas conservan el sentido del contorno. En CCW el
        ;; interior queda a la izquierda de la tangente LOCAL, incluso
        ;; con concavidades o anchos variables. Un centroide/espejo global
        ;; puede caer del lado equivocado de un arco.
        (setq mid (* 0.5 (urb:curve-length en))
              normal (+ (urb:curve-tangent en mid)
                (* 0.5 pi winding (if (urb:string-equal-p posicion "Interno") 1.0 -1.0)))
              side (polar (urb:curve-pt en mid) normal (* 0.5 ancho)))
        (setq ref
          (vl-catch-all-apply 'urb:build-prefab-from-reference
            (list en side tipo ancho etapa sub
              (if (urb:string-equal-p posicion "Interno")
                "Interior" "Exterior") destino)))
        (if (or (vl-catch-all-error-p ref) (null ref))
          (if (and en (entget en))
            (urb:safe-delete (vlax-ename->vla-object en)))
          (setq total (+ total len) refs (cons ref refs))))))
  (if refs (list total (reverse refs)) nil))

;; ---------- 5.6.2 PREFABRICADO POR COSTADO, INTERACTIVO (andenes y senderos) ----------
;; Pedido del usuario: "quiero que me quites la parte de prefabricados de la
;; ventana y que hagas como vias: que me seleccione cada costado y si lleva
;; prefabricado, que prefabricado, que me permita elegir el sentido y cortar
;; cuando no lo necesitan". Mismo patron de urb:create-road-sardineles:
;; se resalta cada costado largo del contorno, se pregunta el tipo, el
;; sentido (Interno = crece hacia dentro del elemento y descuenta area,
;; Externo = hacia afuera) y se marcan pares INICIO/FIN de los tramos SIN
;; prefabricado. Cada tramo util se construye con urb:poly-costado-build (el
;; mismo motor probado, que ademas se interrumpe en los contenedores).
;; Devuelve (descuento refs tipo-costado1 tipo-costado2 posicion ref-pos):
;;   refs      referencias de bloque creadas
;;   ref-pos   lista (ref . "Interno"/"Externo") para el vinculo con el anden
;;   posicion  "Interno" si algun tramo quedo interno (para el colector)
(defun urb:poly-costados-interactive (ename etapa sub destino
                                     / chains winding descuento refs ref-pos tipos
                                     pts en len kw tipo sentido gaps g1 g2 c1 c2
                                     tt1 tt2 swap kept prev item seg sub-en sub-pts
                                     r interno ed x)
  (setq chains (urb:poly-costado-chains ename))
  (if (null chains)
    (progn
      (prompt "\nNo se pudieron identificar los costados del contorno: sin prefabricado (use el boton Prefabricado si lo necesita).")
      (list 0.0 nil "Ninguno" "Ninguno" "Externo" nil))
    (progn
      (setq winding
        (if (< (urb:loop-signed-area
                  (mapcar '(lambda (p) (cons p 0.0))
                    (urb:lwpoly-points-with-arcs-fine ename))) 0.0) -1.0 1.0))
      (setq descuento 0.0 refs nil ref-pos nil tipos nil interno nil)
      (foreach pts chains
        (setq en (urb:poly-chain-polyline pts) tipo "Ninguno")
        (if en
          (progn
            (setq len (urb:highlight-chain en))
            (initget "Bordillo Sardinel Canuela Ninguno")
            (setq kw
              (getkword
                (strcat "\nPrefabricado en el costado resaltado ("
                        (rtos len 2 2) " m)? [Bordillo/Sardinel/Canuela/Ninguno] <Ninguno>: ")))
            (if (member kw '("Bordillo" "Sardinel" "Canuela")) (setq tipo kw))
            (if (/= tipo "Ninguno")
              (progn
                (initget "Interno Externo")
                (setq sentido
                  (getkword
                    (strcat "\n  Sentido del " tipo
                            ": hacia dentro del elemento o hacia afuera? [Interno/Externo] <Interno>: ")))
                (if (null sentido) (setq sentido "Interno"))
                ;; tramos SIN prefabricado (cruces, accesos): pares inicio/fin
                (setq gaps nil g1 T)
                (while g1
                  (setq g1 (getpoint "\n  INICIO de tramo SIN prefabricado (Enter si no hay mas): "))
                  (if g1
                    (progn
                      (setq g2 (getpoint g1 "\n  FIN del tramo sin prefabricado: "))
                      (if g2
                        (progn
                          (setq c1 (vl-catch-all-apply 'vlax-curve-getClosestPointTo (list en g1))
                                c2 (vl-catch-all-apply 'vlax-curve-getClosestPointTo (list en g2)))
                          (if (and (not (vl-catch-all-error-p c1)) (not (vl-catch-all-error-p c2)))
                            (progn
                              (setq tt1 (vlax-curve-getDistAtPoint en c1)
                                    tt2 (vlax-curve-getDistAtPoint en c2))
                              (if (and tt1 tt2)
                                (progn
                                  (if (> tt1 tt2) (setq swap tt1 tt1 tt2 tt2 swap))
                                  (setq gaps (cons (list tt1 tt2) gaps)))))))))))
                (setq gaps (vl-sort gaps '(lambda (a b) (< (car a) (car b)))))
                (setq kept nil prev 0.0)
                (foreach item gaps
                  (if (> (- (car item) prev) 0.10) (setq kept (cons (list prev (car item)) kept)))
                  (setq prev (max prev (cadr item))))
                (if (> (- len prev) 0.10) (setq kept (cons (list prev len) kept)))
                (foreach seg (reverse kept)
                  ;; sub-cadena en el MISMO sentido del contorno (la regla del
                  ;; lado interior de urb:poly-costado-build depende de eso)
                  (urb:bb-log (strcat "INICIA prefabricado exacto " tipo " "
                    (rtos (- (cadr seg) (car seg)) 2 2) " m"))
                  (setq sub-pts (urb:chain-slice-exact en (car seg) (cadr seg)))
                  (setq sub-en (if sub-pts (urb:poly-chain-polyline sub-pts)))
                  (if sub-en
                    (progn
                      (entdel sub-en)
                      (setq r (vl-catch-all-apply 'urb:poly-costado-build
                                (list sub-pts tipo sentido etapa sub winding destino)))
                      (urb:bb-log (strcat "TERMINA prefabricado exacto "
                        (if (and r (not (vl-catch-all-error-p r))) "OK" "FALLO")))
                      (if (and r (not (vl-catch-all-error-p r)))
                        (progn
                          (setq refs (append refs (cadr r)))
                          (foreach x (cadr r) (setq ref-pos (cons (cons x sentido) ref-pos)))
                          (if (urb:string-equal-p sentido "Interno")
                            (setq interno T
                                  descuento (+ descuento (* (car r) (urb:prefab-default-ancho tipo))))))
                        (prompt (strcat "\n  No fue posible crear un tramo de " tipo "."))))))
                (prompt (strcat "\n  " tipo " " sentido ": " (itoa (length kept)) " tramo(s)."))))
            (urb:set-chain-highlight en nil)
            (redraw)
            (if (entget en) (entdel en))))
        (setq tipos (append tipos (list tipo))))
      (list descuento refs
        (urb:safe-string (nth 0 tipos) "Ninguno")
        (urb:safe-string (nth 1 tipos) "Ninguno")
        (if interno "Interno" "Externo")
        (reverse ref-pos)))))

;; construye los costados configurados de un poligono recien dibujado.
;; Devuelve (descuento refs): descuento = suma longitud x ancho de los
;; costados INTERNOS (0.0 si Externo), refs = lista de referencias de
;; bloque creadas. Derecha/Izquierda se asignan por el lado geometrico
;; respecto a la direccion de la primera cadena.
(defun urb:poly-costados-build (ename lado-der lado-izq posicion etapa sub destino
                                / chains ed pts n cx cy centroid ca cb
                                d ma va cruz chain-der chain-izq
                                descuento r len refs winding)
  (setq chains (urb:poly-costado-chains ename))
  (if (null chains)
    (progn
      (prompt "\nNo se pudieron identificar los dos costados del contorno -- prefabricado omitido (use el boton Prefabricado para trazarlo a mano).")
      (list 0.0 nil))
    (progn
      ;; centroide simple = promedio de vertices del contorno
      (setq ed (entget ename) pts nil)
      (foreach itm ed (if (= (car itm) 10) (setq pts (cons (cdr itm) pts))))
      (setq n (length pts) cx 0.0 cy 0.0)
      (foreach p pts (setq cx (+ cx (car p)) cy (+ cy (cadr p))))
      (setq centroid (list (/ cx n) (/ cy n)))
      (setq ca (car chains) cb (cadr chains))
      ;; derecha = la cadena que queda al lado derecho de la direccion de
      ;; la cadena A (cruz z negativa del vector centroide->medio)
      (setq d (list (- (car (last ca)) (car (car ca)))
                    (- (cadr (last ca)) (cadr (car ca)))))
      (setq ma (urb:poly-chain-mid ca))
      (setq va (list (- (car ma) (car centroid))
                     (- (cadr ma) (cadr centroid))))
      (setq cruz (- (* (car d) (cadr va)) (* (cadr d) (car va))))
      (if (< cruz 0.0)
        (setq chain-der ca chain-izq cb)
        (setq chain-der cb chain-izq ca))
      (setq winding
        (if (< (urb:loop-signed-area
                  (mapcar '(lambda (p) (cons p 0.0))
                    (urb:lwpoly-points-with-arcs-fine ename))) 0.0) -1.0 1.0))
      (setq descuento 0.0 refs nil)
      (if (not (urb:string-equal-p lado-der "Ninguno"))
        (progn
          (setq r
            (urb:poly-costado-build chain-der lado-der posicion etapa sub
              winding destino))
          (if r
            (progn
              (setq len (car r) refs (append (cadr r) refs))
              (prompt (strcat "\nCostado derecho: " lado-der " ("
                (rtos len 2 2) " ML) en " (itoa (length (cadr r)))
                " tramo(s); los contenedores no llevan prefabricado."))
              (if (urb:string-equal-p posicion "Interno")
                (setq descuento
                  (+ descuento
                     (* len (urb:prefab-default-ancho lado-der))))))
            (prompt (strcat "\nNo fue posible crear el " lado-der
              " del costado derecho.")))))
      (if (not (urb:string-equal-p lado-izq "Ninguno"))
        (progn
          (setq r
            (urb:poly-costado-build chain-izq lado-izq posicion etapa sub
              winding destino))
          (if r
            (progn
              (setq len (car r) refs (append (cadr r) refs))
              (prompt (strcat "\nCostado izquierdo: " lado-izq " ("
                (rtos len 2 2) " ML) en " (itoa (length (cadr r)))
                " tramo(s); los contenedores no llevan prefabricado."))
              (if (urb:string-equal-p posicion "Interno")
                (setq descuento
                  (+ descuento
                     (* len (urb:prefab-default-ancho lado-izq))))))
            (prompt (strcat "\nNo fue posible crear el " lado-izq
              " del costado izquierdo.")))))
      (list descuento refs))))

;; dibuja el contorno cerrado + relleno + xdata + prefabricado por
;; costados AUTOMATICO para UN elemento de la familia "poligono cerrado"
;; (senderos o bioswale comparten el mismo motor). appid es la xdata
;; donde vive el tipo (URB_SENDERO o URB_BIOSWALE); su compañera
;; "<appid>_GEN" identifica el hatch de relleno hacia el contorno padre.
;; 2026-08-24 v3 (pedido del usuario): los costados NO se trazan a mano
;; -- el programa identifica solo los dos lados largos del poligono
;; (urb:poly-costado-chains) y construye ahi cada prefabricado como
;; BLOQUE; el usuario solo eligio en la ventana el tipo por lado
;; (Derecha/Izquierda) y la posicion (Externo/Interno). Con posicion
;; Interno la franja de los costados se DESCUENTA del area (descuento
;; guardado en la xdata, pos 6, y aplicado por el colector de filas).
(defun urb:sendero-finish-region (obj refs / region cutter ref result)
  ;; Huella REAL de los prefabricados de este sendero. No usar largo*ancho
  ;; en curvas y no dejar el hatch pintado por debajo del confinamiento.
  (setq region (urb:anden-region-from-object obj))
  (if (vl-catch-all-error-p region) (vl-exit-with-error "SENDERO: contorno no apto para recortar el acabado."))
  (setq result
    (vl-catch-all-apply
      '(lambda ()
        (foreach ref refs
          (setq cutter (urb:block-footprint-region ref))
          (if (null cutter) (vl-exit-with-error "SENDERO: no se pudo medir la huella del prefabricado."))
          (urb:region-align-elevation cutter region)
          (vla-Boolean region 2 cutter)
          (urb:safe-delete cutter)
          (setq cutter nil))
        (if (<= (vla-get-Area region) 1e-8)
          (vl-exit-with-error "SENDERO: los prefabricados ocupan todo el contorno.")))))
  (if (vl-catch-all-error-p result)
    (progn
      (urb:safe-delete cutter) (urb:safe-delete region)
      (vl-exit-with-error (vl-catch-all-error-message result))))
  region)

;; ---------- 5.6.6 SENDERO EN BLOQUE ----------
;; Pedido del usuario: "para senderos si quiero que quede en bloque, que se
;; vean sus respectivas medidas y movimiento de tierras, asi como con
;; andenes y zonas verdes". Antes el sendero eran contorno + relleno en un
;; GRUPO: sus datos solo se veian en la pestaña Extended Data. Ahora se
;; empaqueta igual que la zona verde (urb:package-green-zone), con
;; atributos invisibles legibles en Propiedades. La xdata sigue siendo
;; URB_SENDERO -- con el mismo orden de campos -- para que el colector,
;; EDITAR y el movimiento de tierras seleccionen igual los senderos viejos
;; (polilinea) y los nuevos (bloque).
(defun urb:package-sendero
  (ename hatch entry etapa sub datos mov
   / boundary area per esp vol point handle objects block-name blocks
   block-definition copy-result insert-result block-ref block-ename xdata-result
   descuento neta corte relleno)
  (setq boundary (vlax-ename->vla-object ename)
        area (vla-get-Area boundary)
        per (vla-get-Length boundary)
        esp (urb:send-espesor-de entry)
        descuento (atof (urb:safe-string (nth 6 datos) "0"))
        neta (max 0.0 (- area descuento))
        vol (* neta esp)
        corte (if mov (car mov) 0.0)
        relleno (if mov (cadr mov) 0.0)
        point (if (urb:lwpoly-points ename) (car (urb:lwpoly-points ename)) '(0.0 0.0 0.0))
        handle (vla-get-Handle boundary)
        objects (list boundary))
  (if (and hatch (urb:valid-vla-object-p hatch))
    (setq objects (append objects (list hatch))))
  (setq block-name (strcat "URB_SENDERO_" handle "_" (itoa (getvar "MILLISECS")))
        blocks (vla-get-Blocks (urb:doc))
        block-definition (vla-Add blocks (vlax-3d-point '(0.0 0.0 0.0)) block-name)
        copy-result
          (vl-catch-all-apply 'vla-CopyObjects
            (list (urb:doc) (urb:object-array-variant objects) block-definition)))
  (if (vl-catch-all-error-p copy-result)
    (progn
      (urb:safe-delete block-definition)
      (prompt (strcat "\nERROR al crear el bloque del sendero: "
        (vl-catch-all-error-message copy-result)))
      nil)
    (progn
      (urb:set-block-draw-order block-definition (urb:variant-object-list copy-result))
      (foreach par
        (list (cons "TIPO" (nth 1 entry))
              (cons "CODIGO" (nth 0 entry))
              (cons "ETAPA" etapa)
              (cons "SUBETAPA" sub)
              (cons "AREA_M2" (rtos area 2 2))
              (cons "AREA_NETA_M2" (rtos neta 2 2))
              (cons "PERIMETRO_M" (rtos per 2 2))
              (cons "ESPESOR_M" (rtos esp 2 3))
              (cons "VOLUMEN_ESTRUCTURA_M3" (rtos vol 2 2))
              (cons "PREFABRICADO_DER" (urb:safe-string (nth 3 datos) "Ninguno"))
              (cons "PREFABRICADO_IZQ" (urb:safe-string (nth 4 datos) "Ninguno"))
              (cons "PREFABRICADO_POS" (urb:safe-string (nth 5 datos) "Externo"))
              (cons "DESCUENTO_PREFAB_M2" (rtos descuento 2 2))
              (cons "CORTE_M3" (rtos corte 2 2))
              (cons "RELLENO_M3" (rtos relleno 2 2)))
        (urb:add-invisible-attribute block-definition point
          (car par) (car par) (cdr par)))
      (setq insert-result
        (vl-catch-all-apply 'vla-InsertBlock
          (list (urb:space) (vlax-3d-point '(0.0 0.0 0.0)) block-name 1.0 1.0 1.0 0.0)))
      (if (vl-catch-all-error-p insert-result)
        (progn
          (urb:safe-delete block-definition)
          (prompt (strcat "\nERROR al insertar el sendero: "
            (vl-catch-all-error-message insert-result)))
          nil)
        (progn
          (setq block-ref insert-result block-ename (urb:as-ename block-ref))
          (urb:ensure-layer (nth 6 entry) (nth 3 entry) T)
          (vla-put-Layer block-ref (nth 6 entry))
          (setq xdata-result (urb:set-xdata-strings block-ename "URB_SENDERO" datos))
          (urb:set-xdata-strings block-ename "URB_SEND_BLOCK"
            (list "SENDERO" (rtos area 2 8) (rtos per 2 8) (rtos esp 2 8)
                  (rtos descuento 2 8)))
          (if mov
            (urb:set-xdata-strings block-ename "URB_SEND_MOV"
              (list (rtos corte 2 2) (rtos relleno 2 2))))
          (if xdata-result
            (progn
              (foreach o objects (urb:safe-delete o))
              block-ref)
            (progn
              (urb:safe-delete block-ref)
              (urb:safe-delete block-definition)
              (prompt "\nERROR: no fue posible guardar los datos del sendero.")
              nil)))))))

;; copia temporal del contorno de un sendero en BLOQUE, con sus arcos, para
;; poder medir sobreancho y tierras con las mismas funciones de siempre
(defun urb:send-temp-contour (ename)
  ;; Explode NO borra el INSERT original; devuelve copias en WCS con su
  ;; traslado/rotacion/escala. Copiar la definicion media en la posicion vieja.
  (urb:explode-green-block-boundary ename))

;; contorno de un sendero: la polilinea suelta o la que vive en el bloque
(defun urb:send-contour-points (ename / obj bdef item capa mejor cands)
  (if (= (cdr (assoc 0 (entget ename))) "INSERT")
    (progn
      (setq obj (urb:as-vla-object ename)
            bdef (vl-catch-all-apply 'vla-Item
                   (list (vla-get-Blocks (urb:doc)) (vla-get-Name obj))))
      (if (vl-catch-all-error-p bdef)
        nil
        (progn
          (vlax-for item bdef
            (if (member (vla-get-ObjectName item) '("AcDbPolyline" "AcDb2dPolyline"))
              (setq cands (cons item cands))))
          (setq mejor (urb:largest-closed-polyline (reverse cands)))
          (if mejor (urb:lwpoly-points (vlax-vla-object->ename mejor))))))
    (urb:lwpoly-points ename)))

(defun urb:poly-element-draw (entry etapa sub lado-der lado-izq posicion
                              appid / capa ename obj hatch n con-cost
                              descuento grp kw2 picks2 mov2 over2 costados finish-region
                              datos bloque)
  (setq capa (nth 6 entry))
  (urb:ensure-layer capa (nth 3 entry) T)
  (setq n 0)
  (prompt (strcat "\n" (nth 1 entry)
    ": cierre el poligono del contorno (Enter sin dibujar termina)."))
  (while (setq ename (urb:draw-closed-polyline))
    (setq obj (vlax-ename->vla-object ename))
    (vla-put-Layer obj capa)
    (setq descuento 0.0 finish-region nil con-cost nil mov2 nil picks2 nil)
    ;; 5.6.2 (pedido del usuario): fuera el prefabricado automatico de la
    ;; ventana; como en las vias, se resalta cada costado y se pregunta si
    ;; lleva prefabricado, cual, en que sentido y donde se corta. Solo
    ;; senderos: el bioswale va siempre sin prefabricados.
    (if (= appid "URB_SENDERO")
      (progn
        (setq costados
          (vl-catch-all-apply 'urb:poly-costados-interactive
            (list ename etapa sub "Anden")))
        (if (vl-catch-all-error-p costados) (setq costados nil))
        (if (and costados (cadr costados))
          (progn
            (setq con-cost T
                  lado-der (nth 2 costados) lado-izq (nth 3 costados)
                  posicion (nth 4 costados))
            (setq finish-region (urb:sendero-finish-region obj (cadr costados)))
            (setq descuento (max 0.0 (- (vla-get-Area obj) (vla-get-Area finish-region))))))))
    ;; 5.6.2 (pedido del usuario: "actualmente me esta armando los hatch con
    ;; cuadricula, quiero que cada material tenga su color predeterminado
    ;; que no se repita y con transparencia asi como con zona verde"):
    ;; relleno SOLIDO del color propio del material (catalogo, nth 3) con
    ;; transparencia 60. Reemplaza la reticula NET gris de 2026-09-01.
    (setq hatch
      (vl-catch-all-apply
        '(lambda ()
          (setq hatch (vla-AddHatch (urb:space) 1 "SOLID" (if finish-region :vlax-false :vlax-true)))
          (vla-AppendOuterLoop hatch (urb:make-loop-array (if finish-region finish-region obj)))
          (vla-put-Layer hatch capa)
          (vla-put-Color hatch (nth 3 entry))
          (vl-catch-all-apply 'vlax-put-property
            (list hatch 'EntityTransparency "60"))
          (urb:evaluate-render-hatch hatch)
          hatch)))
    (if (not (vl-catch-all-error-p hatch))
      (progn
        (urb:set-xdata-strings
          (vlax-vla-object->ename hatch)
          (strcat appid "_GEN")
          (list (cdr (assoc 5 (entget ename)))))
        (vl-catch-all-apply
          '(lambda ()
            (command "_.DRAWORDER"
              (vlax-vla-object->ename hatch) "" "_Back")))
        ;; 2026-08-24 (pedido del usuario): contorno + relleno como UNA
        ;; unidad de seleccion y borrado -- GRUPO nombrado, no bloque
        ;; (un bloque romperia la lectura directa de area/perimetro y
        ;; el match por xdata de los colectores; el grupo hace que un
        ;; clic seleccione ambos y un Supr borre ambos, que es lo que
        ;; se pidio). Los prefabricados de los costados NO entran al
        ;; grupo: son bloques propios, cada uno se borra por separado.
        ;; 5.6.6: el SENDERO se empaqueta en bloque (ver
        ;; urb:package-sendero); el grupo queda solo para el bioswale.
        (if (/= appid "URB_SENDERO")
          (vl-catch-all-apply
            '(lambda ()
              (setq grp
                (vla-Add (vla-get-Groups (urb:doc))
                  (strcat appid "_" (cdr (assoc 5 (entget ename))))))
              (vla-AppendItems grp
                (urb:object-array-variant (list obj hatch))))))))
    (if finish-region (urb:safe-delete finish-region))
    (setq datos
      (if con-cost
        (list (nth 0 entry) etapa sub lado-der lado-izq posicion
          (rtos descuento 2 6))
        (list (nth 0 entry) etapa sub)))
    (urb:set-xdata-strings ename appid datos)
    ;; 5.7.16: empaquetar ANTES del MT, tambien al elegir Sin o cancelar.
    (setq bloque nil)
    (if (= appid "URB_SENDERO")
      (progn
        (setq bloque
          (vl-catch-all-apply 'urb:package-sendero
            (list ename (if (vl-catch-all-error-p hatch) nil hatch)
                  entry etapa sub datos nil)))
        (if (or (vl-catch-all-error-p bloque) (null bloque))
          (progn
            (if (vl-catch-all-error-p bloque)
              (prompt (strcat "\nError de empaquetado: " (vl-catch-all-error-message bloque))))
            (setq bloque nil)
            (if (not (vl-catch-all-error-p hatch)) (urb:safe-delete hatch))
            ;; Sin bloque no debe anunciarse/exportarse como sendero nuevo.
            (urb:set-xdata-strings ename appid nil)
            (prompt "\nNo se creo el bloque del sendero. Se conserva el contorno para reintentar; se retira el hatch incompleto."))
          (urb:area-created-earthworks (urb:as-ename bloque) "SENDERO" (urb:send-espesor-de entry)))))
    (if (or (/= appid "URB_SENDERO") bloque)
      (progn
        (setq n (1+ n))
        (prompt (strcat "\n" (nth 1 entry) " " (itoa n) " creado."))))
    (prompt "\nOtro contorno (Enter termina): "))
  (prompt (strcat "\n" (itoa n) " elemento(s) de " (nth 1 entry)
    " creados. Sus cantidades salen solas al exportar."))
  (princ))

;; 2026-09-08 (pedido del usuario): el comando/boton independiente
;; "Sendero" (ventana propia con Tipo=Sendero/Ciclorruta/Plazoleta/...)
;; SALIO -- toda esa lista (*urb-send-tipos*) ya se crea desde ANDEN
;; (Tipo=Sendero/Cancha/Ciclorruta/Equipamiento de parque, v4.72.0) via
;; urb:create-sidewalk-command + urb:poly-element-draw, que sigue siendo
;; el motor de dibujo real. urb:send-write-dcl/urb:sendero-command se
;; eliminaron por quedar sin uso; urb:send-fill-sub sigue viva porque
;; Bioswale la comparte.
(defun urb:send-fill-sub (idx)
  (start_list "subetapa")
  (foreach s (urb:subetapas-for (nth idx *urb-etapa-list*)) (add_list s))
  (end_list)
  (set_tile "subetapa" "0"))

;; ---------- BIOSWALE: comando propio (red pluvial, 2026-08-24) --------
(defun urb:bioswale-write-dcl ()
  (urb:write-dialog-dcl
    "urb_bioswale"
    '*urb-bioswale-dcl-ok*
    (list
      ;; 2026-09-07 (pedido del usuario): el bioswale va SIN prefabricados
      ;; a los costados -- fuera los popups; el comando fuerza Ninguno.
      "urb_bioswale : dialog { label = \"Bioswale / biorretenedor\";"
      ": boxed_column { label = \"Datos del elemento\";"
      ": popup_list { label = \"Etapa\"; key = \"etapa\"; }"
      ": popup_list { label = \"Subetapa\"; key = \"subetapa\"; } }"
      ": text { label = \"Sin prefabricados a los costados (asi va el bioswale).\"; }"
      ": text { label = \"Aceptar y CERRAR EL POLIGONO del contorno (como una via o un anden).\"; }"
      "ok_cancel; }")))

(defun urb:bioswale-command (/ dclfile dcl done entry etapa sub subs
                              lado-der lado-izq costpos)
  (vl-load-com)
  (setq entry *urb-bioswale-tipo*)
  (setq dclfile (urb:bioswale-write-dcl))
  (if (null dclfile)
    (alert "No se pudo preparar la ventana de bioswale (revise permisos de la carpeta temporal de Windows).")
    (progn
      (setq dcl (load_dialog dclfile))
      (if (and dcl (> dcl 0) (new_dialog "urb_bioswale" dcl))
        (progn
          (start_list "etapa")
          (foreach e *urb-etapa-list* (add_list e))
          (end_list)
          (set_tile "etapa" "0")
          (urb:send-fill-sub 0)
          (action_tile "etapa" "(urb:send-fill-sub (atoi $value))")
          (setq *urb-send-etapa* "0" *urb-send-sub* "0")
          (action_tile "accept"
            (strcat
              "(setq *urb-send-etapa* (get_tile \"etapa\")"
              " *urb-send-sub* (get_tile \"subetapa\"))"
              "(done_dialog 1)"))
          (setq done (start_dialog))))
      (if (and dcl (> dcl 0)) (unload_dialog dcl))
      (if (= done 1)
        (progn
          (setq etapa
            (urb:safe-string
              (nth (atoi (urb:safe-string *urb-send-etapa* "0"))
                *urb-etapa-list*) "1"))
          (setq subs (urb:subetapas-for etapa))
          (setq sub
            (urb:safe-string
              (nth (atoi (urb:safe-string *urb-send-sub* "0")) subs)
              etapa))
          ;; 2026-09-07 (pedido del usuario): el bioswale va SIN
          ;; prefabricados a los costados, siempre (y sin tocar los
          ;; defaults de costados que usan anden/senderos)
          (setq lado-der "Ninguno" lado-izq "Ninguno" costpos "Externo")
          (urb:poly-element-draw entry etapa sub lado-der lado-izq
            costpos "URB_BIOSWALE")))))
  (princ))

;; ---------- 5.6.0 CANUELA PLUVIAL (por ML, recorrido dibujado) ----------
;; Pedido del usuario: "agregame la opcion de canuela, es la gris de la
;; cuarta foto y es por ml, asi que me toca dibujar lo referente al
;; recorrido de la canuela". Distinta del prefabricado "Canuela" de
;; urbanismo (piezas A-? a lo largo de un anden): esta es el canal de
;; drenaje de la red pluvial. Una polilinea ABIERTA en capa gris, con el
;; ancho real como ancho constante (se ve como la franja del plano) y
;; XDATA URB_CANUELA_PLU = (codigo etapa subetapa ancho). La cantidad es la
;; longitud de la polilinea, asi que editarla con grips actualiza el ML.
(setq *urb-canuela-plu-capa* "URB-CANUELA-PLUVIAL")

(defun urb:canuela-plu-ancho-default (/ v)
  (setq v (urb:parse-real
            (urb:safe-string (urb:config-read "URB_CANUELA_PLU_ANCHO") "")))
  (if (and v (> v 0.0)) v 0.40))

(defun urb:canuela-plu-write-dcl ()
  (urb:write-dialog-dcl
    "urb_canuela_plu"
    '*urb-canuela-plu-dcl-ok*
    (list
      "urb_canuela_plu : dialog { label = \"Canuela pluvial\";"
      ": boxed_column { label = \"Datos del elemento\";"
      ": popup_list { label = \"Etapa\"; key = \"etapa\"; }"
      ": popup_list { label = \"Subetapa\"; key = \"subetapa\"; }"
      ": edit_box { label = \"Ancho de la canuela (m)\"; key = \"ancho\"; edit_width = 10; } }"
      ": text { label = \"Se cuantifica por metro lineal (ML) sobre el recorrido.\"; }"
      ": text { label = \"Se crea una canuela por vez. Enter termina; Esc cancela.\"; }"
      "ok_cancel; }")))

;; xdata URB_CANUELA_PLU = (codigo etapa subetapa ancho id) -- 5.6.1 agrega el ID
(defun urb:canuela-plu-register (ename etapa sub ancho id / obj)
  (setq obj (vlax-ename->vla-object ename))
  (urb:ensure-layer *urb-canuela-plu-capa* 8 T)
  (vla-put-Layer obj *urb-canuela-plu-capa*)
  (vla-put-Color obj 256)
  (if (vlax-property-available-p obj 'ConstantWidth T)
    (vla-put-ConstantWidth obj (float ancho)))
  (urb:set-xdata-strings ename "URB_CANUELA_PLU"
    (list "CANUELA_PLU" etapa sub (rtos ancho 2 3) (urb:safe-string id "")))
  (vla-get-Length obj))

(defun urb:canuela-plu-draw-one (etapa sub ancho id / ename len)
  (setq ename (urb:draw-open-polyline "la canuela"))
  (if ename
    (progn
      (setq len (urb:canuela-plu-register ename etapa sub ancho id))
      (prompt (strcat "\nCanuela creada: " (rtos len 2 2)
        " ML | ancho " (rtos ancho 2 2) " m."))
      len)
    (progn
      (prompt "\nCreacion de canuela cancelada.")
      nil)))

(defun urb:canuela-plu-command (/ dclfile dcl done etapa sub subs ancho)
  (vl-load-com)
  (setq dclfile (urb:canuela-plu-write-dcl))
  (if (null dclfile)
    (alert "No se pudo preparar la ventana de canuela (revise permisos de la carpeta temporal de Windows).")
    (progn
      (setq dcl (load_dialog dclfile))
      (if (and dcl (> dcl 0) (new_dialog "urb_canuela_plu" dcl))
        (progn
          (start_list "etapa")
          (foreach e *urb-etapa-list* (add_list e))
          (end_list)
          (set_tile "etapa" "0")
          (urb:send-fill-sub 0)
          (set_tile "ancho" (rtos (urb:canuela-plu-ancho-default) 2 2))
          (action_tile "etapa" "(urb:send-fill-sub (atoi $value))")
          (setq *urb-send-etapa* "0" *urb-send-sub* "0"
                *urb-canuela-plu-ancho* nil)
          (action_tile "accept"
            (strcat
              "(setq *urb-canuela-plu-ancho* (urb:parse-real (get_tile \"ancho\")))"
              "(if (and *urb-canuela-plu-ancho* (> *urb-canuela-plu-ancho* 0.0) (<= *urb-canuela-plu-ancho* 5.0))"
              " (progn (setq *urb-send-etapa* (get_tile \"etapa\")"
              "  *urb-send-sub* (get_tile \"subetapa\")) (done_dialog 1))"
              " (alert \"El ancho debe ser mayor que 0 y hasta 5.00 m.\"))"))
          (setq done (start_dialog))))
      (if (and dcl (> dcl 0)) (unload_dialog dcl))
      (if (= done 1)
        (progn
          (setq ancho *urb-canuela-plu-ancho*)
          (urb:config-write "URB_CANUELA_PLU_ANCHO" (rtos ancho 2 3))
          (setq etapa
            (urb:safe-string
              (nth (atoi (urb:safe-string *urb-send-etapa* "0"))
                *urb-etapa-list*) "1"))
          (setq subs (urb:subetapas-for etapa))
          (setq sub
            (urb:safe-string
              (nth (atoi (urb:safe-string *urb-send-sub* "0")) subs)
              etapa))
          (urb:canuela-plu-draw-one etapa sub ancho "")))))
  (princ))

;; filas de presupuesto: concepto "Canuela" a secas A PROPOSITO. Con el
;; emparejador por palabras (>= 50% dentro del capitulo y la unidad),
;; "Canuela en concreto fundida en sitio" empataba al 75% con "Construccion
;; de cuneta en concreto fundida en sitio" y "Canuela pluvial" al 50% con
;; el carcamo de proteccion "(Red de alcantarillado pluvial)": las dos
;; habrian ido a una actividad equivocada SIN avisar. "Canuela" solo cae en
;; una fila que diga canuela, o queda huerfana visible. Para mandarla a
;; otra actividad (p.ej. la cuneta) esta la familia parametrica CANUELA.
(defun urb:ppto-rows-canuela-plu (/ ss i en obj datos etapa sub ancho len
                                  handle zona rows out r)
  (setq ss (ssget "_X" '((0 . "LWPOLYLINE") (-3 ("URB_CANUELA_PLU"))))
        out nil i 0)
  (if ss
    (repeat (sslength ss)
      (setq en (ssname ss i)
            obj (vlax-ename->vla-object en)
            datos (urb:get-xdata-strings en "URB_CANUELA_PLU")
            etapa (urb:safe-string (nth 1 datos) "1")
            sub (urb:safe-string (nth 2 datos) "GEN")
            ancho (atof (urb:safe-string (nth 3 datos) "0"))
            len (vla-get-Length obj)
            handle (cdr (assoc 5 (entget en)))
            zona (urb:ppto-zona-de en))
      (setq rows
        (cons
          ;; 3er campo = ID (5.6.1); sin ID queda la descripcion con el ancho
          ;; 5.7.24 (pedido del usuario): en el libro la actividad es la
          ;; CUNETA PREFABRICADA (la cuneta fundida en sitio se retiro).
          (urb:ppto-row "ALC-PLUVIAL"
            "Cuneta prefabricada (suministro e instalación)"
            (if (/= (urb:safe-string (nth 4 datos) "") "")
              (nth 4 datos)
              (strcat "Canuela pluvial a=" (rtos ancho 2 2) " m"))
            "" "" etapa sub "ML" len handle)
          (urb:ppto-param-rows "CANUELA" "ALC-PLUVIAL"
            (list (cons "LONGITUD" len)
                  (cons "AREA" (* len ancho))
                  (cons "UNIDAD" 1.0))
            "" "" "" etapa sub handle)))
      (setq rows (urb:ppto-rows+zona rows zona))
      (foreach r rows (if r (setq out (cons r out))))
      (setq i (1+ i))))
  out)

;; senderos/bioswale dentro de una seleccion (contorno directo o su
;; relleno) -- generico por appid, 2026-08-24
(defun urb:poly-elemento-selected (selection appid / i be out datos parent)
  (setq out nil i 0)
  (if selection
    (repeat (sslength selection)
      (setq be (ssname selection i))
      (cond
        ((urb:get-xdata-strings be appid)
          (setq out (cons be out)))
        ((setq datos (urb:get-xdata-strings be (strcat appid "_GEN")))
          (setq parent
            (vl-catch-all-apply 'handent
              (list (urb:safe-string (car datos) ""))))
          (if (and (not (vl-catch-all-error-p parent)) parent)
            (setq out (cons parent out)))))
      (setq i (1+ i))))
  (reverse out))

(defun urb:send-selected (selection)
  (urb:poly-elemento-selected selection "URB_SENDERO"))

;; ---------- 5.6.2 movimiento de tierras de un SENDERO ya dibujado ----------
;; Pedido del usuario: "con ese sendero dime como puedo sacar el movimiento
;; de tierras, no me esta dejando y tampoco tengo las cotas de elevacion".
;; EDITAR no reconocia senderos (solo andenes, vias, zonas verdes y redes),
;; y las cotas solo se pedian al dibujarlo. Ahora, desde EDITAR:
;;  1. si hay una via creada a <= 10 m, se usa su rasante en TODO el
;;     alineamiento (+ bordillo), sin pedir nada;
;;  2. si no, se piden cotas de implantacion (pozo, etiqueta o Digitar);
;; y se mide sobre el contorno + 1 m en los costados, hasta el espesor del
;; material. Resultado en URB_SEND_MOV, que el presupuesto ya usa.
;; referencia por ANDEN creado (<= 10 m) cuando no hay via al lado
(defun urb:sendero-picks-por-anden (pts / anden aref)
  (setq anden (vl-catch-all-apply 'urb:anden-near-points (list pts)))
  (if (vl-catch-all-error-p anden) (setq anden nil))
  (if anden
    (progn
      (setq aref (vl-catch-all-apply 'urb:anden-design-reference (list anden)))
      (if (vl-catch-all-error-p aref) (setq aref nil))
    )
  )
  (cond
    (aref
      (prompt "\nAnden creado junto al sendero: se usan sus cotas de diseno (borde mas cercano).")
      (list (list 0.0 (list (car (car pts)) (cadr (car pts))) aref))
    )
    (anden
      (prompt "\nEl anden cercano no tiene via con rasante: no sirve de referencia.")
      (urb:anden-ref-curves-clear)
      nil
    )
    (T (urb:anden-ref-curves-clear) nil)
  )
)

;; corte/relleno de un sendero ya con sus cotas resueltas
(defun urb:sendero-mt-calcular
  (ename contorno picks espesor entry bloque / over mov *urb-picks-base-points*)
  ;; El sobreancho amplia la huella de excavacion, NO mueve el borde que
  ;; gobierna la cota terminada ni su pendiente transversal.
  (setq *urb-picks-base-points* (urb:anden-earthwork-raw-points contorno))
  (setq over (vl-catch-all-apply 'urb:anden-overwidth-contour (list contorno 1.0)))
  (if (vl-catch-all-error-p over) (setq over nil))
  (if (null over)
    (prompt "\nSin dos costados largos claros: tierras sobre contorno exacto, sin sobreancho."))
  (setq mov (vl-catch-all-apply 'urb:earthworks-from-picks
    (list (if over over contorno) picks espesor)))
  (if over (urb:safe-delete (vlax-ename->vla-object over)))
  (urb:anden-ref-curves-clear)
  (if (vl-catch-all-error-p mov) (setq mov nil))
  (if (null mov)
    (prompt "\nNo se pudo calcular: revise que el sendero este dentro de la superficie SUP_TN.")
    (progn
      (urb:set-xdata-strings ename "URB_SEND_MOV"
        (list (rtos (car mov) 2 2) (rtos (cadr mov) 2 2)))
      ;; 5.6.6: en el bloque las cifras quedan tambien en Propiedades
      (if bloque
        (progn
          (urb:set-block-attribute (urb:as-vla-object ename) "CORTE_M3" (rtos (car mov) 2 2))
          (urb:set-block-attribute (urb:as-vla-object ename) "RELLENO_M3" (rtos (cadr mov) 2 2))
        )
      )
      (prompt
        (strcat "\n" (nth 1 entry) ": corte " (rtos (car mov) 2 2)
          " m3 | relleno " (rtos (cadr mov) 2 2) " m3 (estructura "
          (rtos espesor 2 2) " m" (if over ", con sobreancho lateral" "") ")."))
      (prompt
        (strcat "\n  Con coeficientes: corte suelto " (rtos (urb:cut-loose (car mov)) 2 2)
          " m3 | material de relleno " (rtos (urb:fill-material (cadr mov)) 2 2)
          " m3 (" (urb:overexc-text) ")."))
    )
  )
  mov
)

;; EDITAR sobre un sendero: recalcula su corte/relleno. La cota de diseno
;; sale, en orden, de la via creada a <= 10 m, del anden creado a <= 10 m
;; (sus cotas de diseno) o de las cotas que se clickeen. 5.6.6: el sendero
;; puede ser un BLOQUE -- su contorno vive dentro y se mide con una copia
;; temporal que se borra al terminar.
(defun urb:sendero-earthworks (ename)
  (urb:sendero-earthworks-run ename T))

(defun urb:sendero-earthworks-run
  (ename editing / datos entry pts road ref picks mov espesor bloque contorno modo)
  (setq datos (urb:get-xdata-strings ename "URB_SENDERO"))
  (setq entry (assoc (urb:safe-string (car datos) "") *urb-send-tipos*))
  (setq *urb-anden-pts-cache* nil)
  (urb:anden-ref-curves-clear)
  (if (null entry)
    (prompt "\nSendero sin tipo reconocido: no se calcula el movimiento.")
    (progn
      (setq bloque (= (cdr (assoc 0 (entget ename))) "INSERT"))
      (setq contorno (if bloque (urb:send-temp-contour ename) ename))
      (setq espesor (urb:send-espesor-de entry))
      (setq pts (if contorno (urb:lwpoly-points contorno)))
      (if contorno
        (setq picks (vl-catch-all-apply 'urb:area-earthwork-picks (list contorno editing))))
      (if (vl-catch-all-error-p picks) (setq picks nil))
      (if (and picks contorno)
        (progn
          (setq mov (vl-catch-all-apply 'urb:sendero-mt-calcular
            (list ename contorno picks espesor entry bloque)))
          (if (vl-catch-all-error-p mov) (setq mov nil))
          (if (null mov) (urb:area-earthwork-clear ename "URB_SEND_MOV")))
        (prompt "\nMovimiento de tierras cancelado.")
      )
      (if (and bloque contorno (entget contorno)) (entdel contorno))
      (urb:anden-ref-curves-clear)
    )
  )
  mov
)

(defun urb:edit-senderos-movimiento (enames / n e)
  (setq n 0)
  (foreach e enames
    (if (urb:sendero-earthworks e) (setq n (1+ n))))
  (prompt (strcat "\nMovimiento de tierras actualizado en " (itoa n) " de "
    (itoa (length enames)) " sendero(s)."))
  n)

(defun urb:bioswale-selected (selection)
  (urb:poly-elemento-selected selection "URB_BIOSWALE"))

;; filas de presupuesto de la familia "poligono cerrado" (senderos y
;; bioswale comparten el motor -- 2026-08-24, tras separar el bioswale a
;; su propio comando/red pluvial). El espesor de la fila de excavacion
;; usa SIEMPRE el valor EFECTIVO (urb:send-espesor-de: config de Ajustes
;; si el usuario lo edito, si no el del catalogo) -- asi la edicion en
;; Ajustes cambia de verdad la cantidad exportada, no solo un texto.
(defun urb:ppto-rows-poly-elemento (appid tipos familia
                                    / ss i be entry datos codigo etapa sub
                                    area per obj rows out zona handle
                                    receta fila qty con-anillo espesor
                                    factor mov atts bdatos)
  ;; 5.6.6: el sendero nuevo es un BLOQUE con la misma xdata URB_SENDERO;
  ;; area y perimetro salen de sus atributos (el bloque no los expone como
  ;; propiedad). Los senderos viejos (polilinea suelta) siguen igual.
  (setq ss (ssget "_X" (list '(0 . "LWPOLYLINE,INSERT") (list -3 (list appid))))
        out nil i 0)
  (if ss
    (repeat (sslength ss)
      (setq be (ssname ss i)
            datos (urb:get-xdata-strings be appid)
            codigo (urb:safe-string (car datos) "")
            entry (assoc codigo tipos))
      (if entry
        (progn
          (setq etapa (urb:safe-string (cadr datos) "1")
                sub (urb:safe-string (caddr datos) "GEN")
                obj (vlax-ename->vla-object be)
                atts (if (= (cdr (assoc 0 (entget be))) "INSERT")
                       (urb:block-attribute-values obj))
                bdatos (if atts (urb:get-xdata-strings be "URB_SEND_BLOCK"))
                area (if atts
                       (atof (urb:safe-string
                               (if (> (length bdatos) 1) (nth 1 bdatos)
                                 (cdr (assoc "AREA_M2" atts))) "0"))
                       (vla-get-Area obj))
                per (if atts
                      (atof (urb:safe-string
                              (if (> (length bdatos) 2) (nth 2 bdatos)
                                (cdr (assoc "PERIMETRO_M" atts))) "0"))
                      (vla-get-Length obj))
                handle (cdr (assoc 5 (entget be)))
                zona (urb:ppto-zona-de be)
                rows nil)
          ;; 2026-08-24 v3: con prefabricado por COSTADOS (xdata pos 3-6:
          ;; lado-der lado-izq posicion descuento) las filas PER de la
          ;; receta se SALTAN (cada costado es un bloque prefabricado que
          ;; cuenta su propio ML) y si la posicion es Interno el area
          ;; descuenta la franja ya calculada al crear (pos 6). Los
          ;; elementos viejos con el anillo perimetral de v4.50-v4.53.0
          ;; (pos 3 = tipo de anillo) tambien caen aqui: sus filas PER se
          ;; siguen saltando bien, pero el descuento Interno viejo ya no
          ;; se re-aplica (formato de xdata distinto) -- recrear esos
          ;; elementos de prueba si importa el area exacta.
          (setq con-anillo
            (or (and (/= (urb:safe-string (nth 3 datos) "") "")
                     (not (urb:string-equal-p
                       (urb:safe-string (nth 3 datos) "") "Ninguno")))
                (and (/= (urb:safe-string (nth 4 datos) "") "")
                     (not (urb:string-equal-p
                       (urb:safe-string (nth 4 datos) "") "Ninguno"))
                     (member (urb:safe-string (nth 4 datos) "")
                       *urb-anillo-prefab-list*))))
          (if (and con-anillo
                   (urb:string-equal-p
                     (urb:safe-string (nth 5 datos) "") "Interno"))
            (setq area
              (max 0.0
                (- area (atof (urb:safe-string (nth 6 datos) "0"))))))
          (setq espesor (urb:send-espesor-de entry))
          ;; 5.6.2: corte/relleno del sendero (URB_SEND_MOV) SOLO como
          ;; magnitudes parametricas CORTE/RELLENO, opcionales. Aclaracion del
          ;; usuario: el pedido era calcularlo en AutoCAD, no cambiar la
          ;; exportacion -- las filas de la receta (excavacion de caja) se
          ;; quedan como estaban.
          (setq mov (if (= appid "URB_SENDERO")
                      (urb:get-xdata-strings be "URB_SEND_MOV")))
          (if mov
            (setq mov (list (atof (urb:safe-string (car mov) "0"))
                            (atof (urb:safe-string (cadr mov) "0")))))
          (foreach receta (nth 5 entry)
            ;; 2026-08-24: capas de la receta EDITABLES desde la ventana
            ;; Estructura de senderos -- el factor efectivo sale de la
            ;; config si el usuario lo edito, si no del catalogo
            (setq factor
              (cond
                ((urb:string-equal-p (nth 0 receta)
                   "Excavación en material común (incluye cargue, transporte y disposición final)")
                  espesor)
                ((urb:string-equal-p (nth 0 receta) "Concreto 3000 psi")
                  (urb:send-capa-cfg "URB_SEND_CONCRETO" (nth 3 receta)))
                ((urb:string-equal-p (nth 0 receta) "Malla electrosoldada")
                  (urb:send-capa-cfg "URB_SEND_MALLA" (nth 3 receta)))
                ((or (urb:string-equal-p (nth 0 receta)
                       "Subabase granular SBG-B")
                     (urb:string-equal-p (nth 0 receta)
                       "Subbase granular SBG"))
                  (urb:send-capa-cfg "URB_SEND_SBG" (nth 3 receta)))
                ((urb:string-equal-p (nth 0 receta)
                   "Suministro, extendida y compactación de Rodadura Asfáltica MD-13")
                  (urb:send-capa-cfg "URB_SEND_ASFALTO" (nth 3 receta)))
                (T (nth 3 receta))))
            (setq qty
              (* factor
                 (cond
                   ((= (nth 2 receta) "PER") per)
                   ((= (nth 2 receta) "UN") 1.0)
                   (T area))))
            (if (not (and con-anillo (= (nth 2 receta) "PER")))
              (progn
                (setq fila
                  (urb:ppto-row (nth 2 entry) (nth 0 receta)
                    (nth 1 entry) "" "" etapa sub (nth 1 receta) qty
                    handle))
                (if fila (setq rows (cons fila rows))))))
          ;; parametricas de la familia: AREA, PERIMETRO y UNIDAD
          ;; disponibles para actividades del usuario (5.6.2: + CORTE y
          ;; RELLENO cuando el movimiento de tierras esta calculado)
          (setq rows
            (append rows
              (urb:ppto-param-rows familia (nth 2 entry)
                (append
                  (list (cons "AREA" area) (cons "PERIMETRO" per)
                        (cons "UNIDAD" 1.0))
                  (if mov (list (cons "CORTE" (car mov)) (cons "RELLENO" (cadr mov)))))
                (nth 1 entry) "" "" etapa sub handle)))
          (setq rows (urb:ppto-rows+zona rows zona))
          (if (/= zona "")
            (setq rows (urb:ppto-rows+hint rows (nth 4 entry))))
          (foreach r rows (if r (setq out (cons r out))))))
      (setq i (1+ i))))
  out)

(defun urb:ppto-rows-senderos ()
  (urb:ppto-rows-poly-elemento "URB_SENDERO" *urb-send-tipos* "SENDERO"))

(defun urb:ppto-rows-bioswale ()
  (urb:ppto-rows-poly-elemento "URB_BIOSWALE"
    (list *urb-bioswale-tipo*) "BIOSWALE"))

;; ---------- ZONAS VERDES (2026-09-11, reporte del usuario: "revisa que lo
;; correspondiente a zona verde lo dibuje pero no me lo esta trayendo al
;; presupuesto"). Causa: urb:track-collect-rows no tenia ninguna fuente de
;; zonas verdes -- el bloque se creaba con su area, espesor de tierra negra
;; y su corte/relleno, pero nadie los convertia en filas.
;; El vocabulario es el EXACTO del libro y depende del contexto:
;;   sin zona marcada  -> capitulo 2.2.7 ZONA VERDE de perfiles viales, que
;;      SOLO tiene dos actividades: 2.2.7.1.1 Empradizacion y conformacion
;;      (M2) y 2.2.7.2.1 Suministro e instalacion de arbol (UN, la pone el
;;      comando de arborizacion, no la zona). 2026-09-11, segunda ronda del
;;      usuario ("recuerda que quiero que este conectado a la zona verde
;;      del capitulo de 2.2.7"): las filas de excavacion y de recebo que
;;      salian antes NO existen en 2.2.7 y quedaban sin capitulo; el corte
;;      y el relleno de la zona verde van por las parametricas.
;;   con zona marcada  -> "ZONAS VERDES" del parque (2.3.x.2):
;;      Localizacion y replanteo (M2) | Relleno Manual Tierra Negra X 30CM
;;      (M3) | Coberturas Zonas Verdes (M2)
;; Ademas quedan las parametricas de la familia ZONA_VERDE (AREA,
;; PERIMETRO, VOLUMEN, CORTE, RELLENO, UNIDAD).
(defun urb:ppto-rows-zonasverdes (/ ss i be atts data etapa sub area per esp
                                  vol corte relleno handle zona rows out r)
  (setq ss (ssget "_X" '((0 . "INSERT") (-3 ("URB_GREEN_BLOCK")))) out nil i 0)
  (if ss
    (repeat (sslength ss)
      (setq be (ssname ss i)
            data (urb:green-zone-data be)
            atts (urb:block-attribute-values (vlax-ename->vla-object be))
            etapa (urb:safe-string (nth 1 data) "1")
            sub (urb:safe-string (nth 2 data) "GEN")
            area (atof (urb:safe-string (nth 3 data)
                   (urb:safe-string (cdr (assoc "AREA_M2" atts)) "0")))
            per (atof (urb:safe-string (nth 4 data)
                  (urb:safe-string (cdr (assoc "PERIMETRO_M" atts)) "0")))
            esp (atof (urb:safe-string (nth 5 data) "0.20"))
            vol (atof (urb:safe-string (nth 6 data) "0"))
            corte (atof (urb:safe-string (cdr (assoc "CORTE_M3" atts)) "0"))
            relleno (atof (urb:safe-string (cdr (assoc "RELLENO_M3" atts)) "0"))
            handle (cdr (assoc 5 (entget be)))
            zona (urb:ppto-zona-de be))
      (if (<= vol 0.0) (setq vol (* area esp)))
      ;; 5.7.19 (pedido del usuario 2026-09-22): "Empradizacion y
      ;; conformacion" sale del libro en 2.2.7; la zona verde de via
      ;; exporta las mismas tres actividades que la de parque
      ;; (replanteo, tierra negra y cobertura), cada una en su capitulo.
      (setq rows
        (progn
          (list
            (urb:ppto-row "ZONA-VERDE" "Localizacion y replanteo"
              "" "" "" etapa sub "M2" area handle)
            (urb:ppto-row "ZONA-VERDE" "Relleno Manual Tierra Negra X 30CM"
              "" "" "" etapa sub "M3" vol handle)
            (urb:ppto-row "ZONA-VERDE" "Coberturas Zonas Verdes"
              "" "" "" etapa sub "M2" area handle))))
      (setq rows
        (append rows
          (urb:ppto-param-rows "ZONA_VERDE" "ZONA-VERDE"
            (list (cons "AREA" area) (cons "PERIMETRO" per)
                  (cons "VOLUMEN" vol) (cons "CORTE" corte)
                  (cons "RELLENO" relleno) (cons "UNIDAD" 1.0))
            "" "" "" etapa sub handle)))
      (setq rows (urb:ppto-rows+zona rows zona))
      (foreach r rows (if r (setq out (cons r out))))
      (setq i (1+ i))))
  out)

;; ---------- SEÑALIZACION Y DEMARCACION (2026-09-06, pedido del
;; usuario: comando APARTE de anden/senderos). Tres clases:
;;  LINEA   -> polilineas seleccionadas/dibujadas; cantidad = longitud x
;;             factor (factor <1 en discontinuas = ocupacion pintada;
;;             en actividades M2 el factor es M2 por ML de eje).
;;  SIMBOLO -> marcador puntual; cantidad = factor (M2 de plantilla).
;;  SENAL   -> marcador puntual; cantidad = 1 UN (senales verticales,
;;             tachas).
;; Actividades EXACTAS del capitulo 2.2.8 del presupuesto. Factores de
;; plantilla marcados aqui son estandar IDU aproximados -- editarlos en
;; este catalogo si el APU real difiere.
(setq *urb-senal-tipos*
  '(("LC-AM-12" "Linea continua amarilla a=0,12" "LINEA"
      "Línea continua de color amarillo - Pintura de dos componentes metil metacrilato (a=0,12m)" "ML" 1.0)
    ("LC-AM-15" "Linea continua amarilla a=0,15" "LINEA"
      "Línea continua de color amarillo - Pintura de dos componentes metil metacrilato (a=0,15m)" "ML" 1.0)
    ("LC-BL-12" "Linea continua blanca a=0,12" "LINEA"
      "Línea continua de color blanco - Pintura de dos componentes metil metacrilato (a=0,12m)" "ML" 1.0)
    ("LC-BL-CICLO" "Linea continua blanca ciclorruta a=0,10" "LINEA"
      "Línea continua de color blanco para ciclorruta - Pintura acrílica (a=0,10m)" "ML" 1.0)
    ("LD-BL-1X1" "Linea discontinua blanca 1m x 1m" "LINEA"
      "Línea discontinua de color blanco 1m x 1m - Pintura de dos componentes metil metacrilato (a=0,20m)" "ML" 0.5)
    ("LD-BL-3X5" "Linea discontinua blanca 3m x 5m" "LINEA"
      "Línea discontinua de color blanco 3m x 5m - Pintura de dos componentes metil metacrilato (a=0,12m)" "ML" 0.375)
    ("LD-AM-CICLO" "Linea discontinua amarilla ciclorruta 1m x 2m" "LINEA"
      "Línea discontinua de color amarillo para ciclorruta 1m x 2m - Pintura acrílica (a=0,10m)" "ML" 0.3333)
    ("RESALTO" "Resalto en concreto" "LINEA"
      "Suministro e instalación de resalto en concreto" "ML" 1.0)
    ("CEBRA" "Linea cebreada paso peatones (eje del paso)" "LINEA"
      "Línea cebreada para paso de peatones (a=0,4m) - Pintura de dos componentes metil metacrilato" "M2" 2.0)
    ("PARE-06" "Linea de Pare a=0,6 (metil)" "LINEA"
      "Línea de Pare - Pintura de dos componentes metil metacrilato (a=0,6m)" "M2" 0.6)
    ("PARE-02" "Linea de Pare a=0,2 (acrilica)" "LINEA"
      "Línea de Pare - Pintura acrílica (a=0,2m)" "M2" 0.2)
    ("POMPEYANO" "Demarcacion rampas de pompeyano (eje)" "LINEA"
      "Demarcación de rampas de pompeyano (Color amarillo) - Pintura de dos componentes metil metacrilato" "M2" 1.0)
    ("CRUCE-CICLO" "Cruce ciclorruta por calzada (eje)" "LINEA"
      "Cruce ciclorruta por calzada (0,4m x 0,4m) - Pintura de dos componentes metil metacrilato" "M2" 1.2)
    ("CRUCE-CICLO-AZ" "Cruce ciclorruta calzada azul (eje)" "LINEA"
      "Cruce ciclorruta por calzada (Color azul) - Pintura de dos componentes metil metacrilato" "M2" 3.0)
    ("FL-DER" "Flecha a la derecha" "SIMBOLO"
      "Flecha a la derecha - Pintura de dos componentes metil metacrilato" "M2" 1.2)
    ("FL-IZQ" "Flecha a la izquierda" "SIMBOLO"
      "Flecha a la izquierda - Pintura de dos componentes metil metacrilato" "M2" 1.2)
    ("FL-DER-IZQ" "Flecha derecha o izquierda" "SIMBOLO"
      "Flecha a la derecha o a la izquierda - Pintura de dos componentes metil metacrilato" "M2" 1.5)
    ("FL-FRENTE" "Flecha de frente" "SIMBOLO"
      "Flecha de frente - Pintura de dos componentes metil metacrilato" "M2" 1.2)
    ("FL-FR-DER" "Flecha frente o derecha" "SIMBOLO"
      "Flecha de frente o a la derecha - Pintura de dos componentes metil metacrilato" "M2" 1.5)
    ("FL-FR-IZQ" "Flecha frente o izquierda" "SIMBOLO"
      "Flecha de frente o a la izquierda - Pintura de dos componentes metil metacrilato" "M2" 1.5)
    ("FL-FR-DER-IZQ" "Flecha frente, derecha o izquierda" "SIMBOLO"
      "Flecha de frente, a la derecha o a la izquierda - Pintura de dos componentes metil metacrilato" "M2" 1.8)
    ("FL-CICLO" "Flecha de frente ciclocarril" "SIMBOLO"
      "Flecha de frente para ciclocarril - Pintura acrílica" "M2" 0.8)
    ("PICT-BICI" "Pictograma de bicicleta" "SIMBOLO"
      "Pictograma de bicicleta - Pintura acrílica" "M2" 1.0)
    ("PICT-PEATON" "Pictograma cruce peatonal" "SIMBOLO"
      "Pictograma de cruce peatonal - Pintura de dos componentes metil metacrilato" "M2" 1.5)
    ("LETRAS" "Demarcacion de letras" "SIMBOLO"
      "Demarcación de letras - Pintura acrílica" "M2" 1.5)
    ("VEL-20" "Maxima velocidad 20 km/h" "SIMBOLO"
      "Demarcación máxima velocidad permitida (20 km/h) - Pintura de dos componentes metil metacrilato" "M2" 3.0)
    ("TRIANGULOS" "Sentido transito pompeyano (triangulos)" "SIMBOLO"
      "Sentido del tránsito en pompeyanos (Triángulos) - Pintura de dos componentes metil metacrilato" "M2" 0.5)
    ("SV-60" "Senal vertical 0,60x0,60" "SENAL"
      "Señal vertical (0,60mx0,60m)" "UN" 1.0)
    ("SV-CICLO-D" "Senal ciclorruta doble 0,45" "SENAL"
      "Señal vertical ciclorruta doble (0,45m x 0,45m)" "UN" 1.0)
    ("SV-CICLO-S" "Senal ciclorruta sencilla 0,45" "SENAL"
      "Señal vertical ciclorruta sencilla (0,45m x 0,45m)" "UN" 1.0)
    ("SV-CICLO-INI" "Senal Inicio ciclorruta" "SENAL"
      "Señal vertical ciclorruta sencilla \"Inicio ciclorruta\"" "UN" 1.0)
    ("SV-CICLO-FIN" "Senal Fin ciclorruta" "SENAL"
      "Señal vertical ciclorruta sencilla \"Fin ciclorruta\"" "UN" 1.0)
    ("SV-SP46A" "Senal SP-46A / SR-30" "SENAL"
      "Señal vertical SP-46A / SR-30" "UN" 1.0)
    ("SV-SPB03" "Senal SPB-03" "SENAL"
      "Señal vertical SPB-03" "UN" 1.0)
    ("SV-SPB04" "Senal SPB-04" "SENAL"
      "Señal vertical SPB-04" "UN" 1.0)
    ("SV-SPC01" "Senal SPC-01 / SPC-01" "SENAL"
      "Señal vertical SPC-01 / SPC-01" "UN" 1.0)
    ("SV-SPC01R" "Senal SPC-01 / SRC-01" "SENAL"
      "Señal vertical SPC-01 / SRC-01" "UN" 1.0)
    ("SV-SP59A" "Senal cruce ciclistas SP-59A" "SENAL"
      "Señal vertical ubicación de cruce ciclistas SP-59A" "UN" 1.0)
    ("SV-SP46" "Senal cruce peatonal SP-46" "SENAL"
      "Señal vertical ubicación de cruce peatonal SP-46" "UN" 1.0)
    ("SV-SP46B" "Senal cruce peatonal SP-46B" "SENAL"
      "Señal vertical ubicación de cruce peatonal SP-46B" "UN" 1.0)
    ("TACHA-C" "Tacha reflectiva (linea central)" "SENAL"
      "Tacha reflectiva bidireccional (Línea central)" "UN" 1.0)
    ("TACHA-B" "Tacha reflectiva (linea de borde)" "SENAL"
      "Tacha reflectiva bidireccional (Línea de borde)" "UN" 1.0)))

(defun urb:senal-ensure-layer (entry / capa)
  (setq capa (strcat "URB-SENAL-" (nth 0 entry)))
  (urb:ensure-layer capa
    (cond ((= (nth 2 entry) "LINEA") 2)
          ((= (nth 2 entry) "SIMBOLO") 7)
          (T 1))
    T)
  capa)

;; bloque marcador puntual: circulo + codigo como texto (suficiente para
;; ubicar y contar; la geometria real del simbolo vive en los planos)
(defun urb:senal-ensure-block (entry / nombre bdef circ txt)
  (setq nombre (strcat "URB_SEN_" (nth 0 entry)))
  (if (not (tblsearch "BLOCK" nombre))
    (progn
      (setq bdef
        (vla-Add (vla-get-Blocks (urb:doc))
          (vlax-3d-point '(0.0 0.0 0.0)) nombre))
      (setq circ
        (vla-AddCircle bdef (vlax-3d-point '(0.0 0.0 0.0)) 0.35))
      (vla-put-Color circ 256)
      (setq txt
        (vla-AddText bdef (nth 0 entry)
          (vlax-3d-point '(0.0 -0.12 0.0)) 0.22))
      (vla-put-Alignment txt 1)
      (vla-put-TextAlignmentPoint txt (vlax-3d-point '(0.0 -0.12 0.0)))
      (vla-put-Color txt 256)))
  nombre)

;; lista numerada por linea de comandos; Enter = primer valor
(defun urb:senal-pick-lista (titulo lst / i n)
  (if (or (null lst) (= (length lst) 1))
    (car lst)
    (progn
      (prompt (strcat "\n--- " titulo " ---"))
      (setq i 1)
      (foreach e lst
        (prompt (strcat "\n  " (itoa i) ". " e))
        (setq i (1+ i)))
      (initget 4)
      (setq n (getint (strcat "\n" titulo " (1-" (itoa (length lst))
                        ") <1>: ")))
      (if (and n (>= n 1) (<= n (length lst)))
        (nth (1- n) lst)
        (car lst)))))

(defun urb:senal-pick-tipo (clase / lst i sel n)
  (setq lst (vl-remove-if-not
              '(lambda (e) (= (nth 2 e) clase)) *urb-senal-tipos*))
  (prompt (strcat "\n--- Tipos de " clase " ---"))
  (setq i 1)
  (foreach e lst
    (prompt (strcat "\n  " (itoa i) ". " (nth 1 e)))
    (setq i (1+ i)))
  (initget 6)
  (setq n (getint (strcat "\nNumero del tipo (1-" (itoa (length lst)) "): ")))
  (if (and n (>= n 1) (<= n (length lst)))
    (nth (1- n) lst)
    nil))

(defun c:SENALIZACION (/ clase entry etapa sub ss i en obj capa bloque pt
                       ref n)
  (vl-load-com)
  (initget "Linea Simbolo Vertical")
  (setq clase
    (getkword "\nClase de señalizacion [Linea/Simbolo/Vertical] <Linea>: "))
  (if (null clase) (setq clase "Linea"))
  (setq clase
    (cond ((= clase "Linea") "LINEA")
          ((= clase "Simbolo") "SIMBOLO")
          (T "SENAL")))
  (setq entry (urb:senal-pick-tipo clase))
  (if (null entry)
    (prompt "\nTipo invalido.")
    (progn
      (setq etapa "1" sub "GEN")
      (if (urb:etapas-enabled-p)
        (progn
          (setq etapa
            (urb:safe-string
              (urb:senal-pick-lista "Etapa" *urb-etapa-list*) "1"))
          (setq sub
            (urb:safe-string
              (urb:senal-pick-lista "Subetapa"
                (urb:subetapas-for etapa)) "GEN"))))
      (setq capa (urb:senal-ensure-layer entry))
      (if (not (tblsearch "APPID" "URB_SENAL")) (regapp "URB_SENAL"))
      (cond
        ((= clase "LINEA")
          (prompt (strcat "\nSeleccione las polilineas de: " (nth 1 entry)))
          (setq ss (ssget '((0 . "LWPOLYLINE,LINE,ARC,POLYLINE"))))
          (if ss
            (progn
              (setq i 0 n 0)
              (repeat (sslength ss)
                (setq en (ssname ss i)
                      obj (vlax-ename->vla-object en))
                (vla-put-Layer obj capa)
                (urb:set-xdata-strings en "URB_SENAL"
                  (list (nth 0 entry) etapa sub))
                (setq n (1+ n) i (1+ i)))
              (prompt (strcat "\n" (itoa n) " linea(s) marcadas como "
                (nth 1 entry) ".")))
            (prompt "\nNada seleccionado.")))
        (T
          (setq bloque (urb:senal-ensure-block entry))
          (setq n 0)
          (while (setq pt (getpoint (strcat "\nPunto para " (nth 1 entry)
                            " (Enter termina): ")))
            (setq ref
              (vla-InsertBlock (urb:space)
                (vlax-3d-point pt) bloque 1.0 1.0 1.0 0.0))
            (vla-put-Layer ref capa)
            (urb:set-xdata-strings (vlax-vla-object->ename ref) "URB_SENAL"
              (list (nth 0 entry) etapa sub))
            (setq n (1+ n)))
          (prompt (strcat "\n" (itoa n) " " (nth 1 entry) " insertadas.")))))
    )
  (princ))

;; colector: lineas (longitud x factor) + marcadores (factor por unidad)
(defun urb:ppto-rows-senalizacion (/ ss i en datos entry etapa sub qty obj
                                   rows out zona handle fila)
  (setq out nil)
  (if (tblsearch "APPID" "URB_SENAL")
    (progn
      (setq ss (ssget "_X"
        '((-3 ("URB_SENAL")))))
      (setq i 0)
      (if ss
        (repeat (sslength ss)
          (setq en (ssname ss i)
                datos (urb:get-xdata-strings en "URB_SENAL")
                entry (assoc (urb:safe-string (car datos) "")
                        *urb-senal-tipos*))
          (if entry
            (progn
              (setq etapa (urb:safe-string (cadr datos) "1")
                    sub (urb:safe-string (caddr datos) "GEN")
                    handle (cdr (assoc 5 (entget en)))
                    zona (urb:ppto-zona-de en)
                    obj (vlax-ename->vla-object en))
              (setq qty
                (if (= (nth 2 entry) "LINEA")
                  (progn
                    (setq qty
                      (vl-catch-all-apply
                        '(lambda () (vla-get-Length obj))))
                    (if (vl-catch-all-error-p qty)
                      0.0
                      (* (nth 5 entry) qty)))
                  (nth 5 entry)))
              (if (and (numberp qty) (> qty 0.0))
                (progn
                  (setq fila
                    (urb:ppto-row "SENALIZACION" (nth 3 entry)
                      (nth 1 entry) "" "" etapa sub (nth 4 entry) qty
                      handle))
                  (setq rows (list fila))
                  (setq rows (urb:ppto-rows+zona rows zona))
                  (if (/= zona "")
                    (setq rows (urb:ppto-rows+hint rows "SENALIZACION")))
                  (foreach r rows (if r (setq out (cons r out))))))))
          (setq i (1+ i))))))
  out)

;; ---------- configuracion por maquina ----------
(defun urb:ppto-config-file (/ folder)
  (setq folder (strcat (getenv "APPDATA") "\\UrbanismoCantidades"))
  (if (not (vl-file-directory-p folder)) (vl-mkdir folder))
  (strcat folder "\\ppto_libro.txt"))

;; 2026-09-03 MULTI-PC (pregunta del usuario: "¿si actualizo el ppto en
;; varios computadores me reconoce bien la ruta?"): la ruta guardada es
;; absoluta y LOCAL por maquina, y SharePoint monta en bases distintas
;; (C:\Users\<usuario>\colsubsidio.com en un PC, D:\colsubsidio.com en
;; otro). Si la ruta guardada no existe en ESTE PC, se AUTO-RESUELVE:
;;   1) el libro vive AL LADO del master -> carpeta PADRE del DWG abierto
;;      (mismo espiritu de los xrefs relativos .\XREF\);
;;   2) si no, la misma cola "colsubsidio.com\..." probada en las bases
;;      tipicas (%USERPROFILE%, C:\, D:\, E:\, F:\).
;; Al encontrarlo, la config local se re-escribe sola (self-healing): el
;; usuario no tiene que re-apuntar nada al cambiar de computador.
(defun urb:ppto-config-read (/ f line dwgdir parent cand tail pos d)
  (setq line "")
  (if (setq f (open (urb:ppto-config-file) "r"))
    (progn
      (setq line (urb:safe-string (read-line f) ""))
      (close f)))
  (if (and (/= line "") (findfile line))
    line
    (progn
      (setq cand nil)
      ;; 1) junto al master: <padre del DWG> o <carpeta del DWG>.
      ;; 2026-09-07: el NOMBRE del libro ya no va quemado -- se prueba
      ;; primero el nombre de archivo de la ruta guardada (por si el
      ;; usuario renombra el libro) y "urbanismo maipore.xlsx" como
      ;; respaldo.
      (setq dwgdir (urb:safe-string (getvar "DWGPREFIX") ""))
      (if (/= dwgdir "")
        (progn
          (setq parent
            (vl-filename-directory
              (vl-string-right-trim "\\/" dwgdir)))
          (foreach nombre
            (vl-remove nil
              (list
                (if (/= line "")
                  (strcat (vl-filename-base line)
                          (urb:safe-string (vl-filename-extension line)
                            ".xlsx")))
                "urbanismo maipore.xlsx"))
            (if (and (null cand) parent
                     (findfile (strcat parent "\\" nombre)))
              (setq cand (strcat parent "\\" nombre)))
            (if (and (null cand)
                     (findfile (strcat dwgdir nombre)))
              (setq cand (strcat dwgdir nombre))))))
      ;; 2) la cola colsubsidio.com\... de la ruta guardada en otra base
      (if (and (null cand) (/= line "")
               (setq pos (vl-string-search "colsubsidio.com" line)))
        (progn
          (setq tail (substr line (1+ pos)))
          (foreach d (list (strcat (urb:safe-string
                             (getenv "USERPROFILE") "C:\\x") "\\")
                           "C:\\" "D:\\" "E:\\" "F:\\")
            (if (and (null cand) (findfile (strcat d tail)))
              (setq cand (strcat d tail))))))
      (if cand
        (progn
          (urb:ppto-config-write cand)
          (prompt (strcat
            "\nLibro del presupuesto RESUELTO para este PC (multi-PC): "
            cand))
          cand)
        line))))

(defun urb:ppto-config-write (path / f)
  (if (setq f (open (urb:ppto-config-file) "w"))
    (progn (write-line path f) (close f))))

;; ---------- equivalencias manuales (decididas en el dialogo pre-export) ----------
;; Viven DENTRO del libro (pedido del usuario 2026-08-18): hoja MUY OCULTA
;; "URB_EQUIVALENCIAS" (Visible=2, no aparece ni en "Mostrar hojas"), col A
;; = clave "RED|concepto-normalizado", col B = descripcion elegida. Viajan
;; con el libro entre PCs y no agregan nada visible. El match las consulta
;; ANTES de la cascada automatica; si la descripcion elegida ya no existe
;; en el capitulo+UM (ppto renombrado), se ignora y el concepto vuelve a
;; salir como pendiente en el dialogo.
(defun urb:ppto-find-sheet (wb nombre / sheets count i ws nm found)
  (setq sheets (vlax-get-property wb 'Worksheets))
  (setq count
    (vl-catch-all-apply '(lambda () (vlax-get-property sheets 'Count))))
  (if (vl-catch-all-error-p count) (setq count 0))
  (setq i 1 found nil)
  (while (and (<= i count) (null found))
    (setq ws (vl-catch-all-apply
      '(lambda () (urb:ppto-obj (vlax-get-property sheets 'Item i)))))
    (if (not (vl-catch-all-error-p ws))
      (progn
        (setq nm (vl-catch-all-apply
          '(lambda () (vlax-get-property ws 'Name))))
        (if (and (not (vl-catch-all-error-p nm))
                 (= (strcase nm) (strcase nombre)))
          (setq found ws))))
    (setq i (1+ i)))
  found)

(defun urb:ppto-equiv-read (wb / ws rng r clave valor out)
  (setq out nil)
  (setq ws (urb:ppto-find-sheet wb "URB_EQUIVALENCIAS"))
  (if ws
    (progn
      (setq rng (urb:ppto-obj (vlax-get-property ws 'Range "A1:B300")))
      (setq r 1 clave "x")
      (while (and (<= r 300) (/= clave ""))
        (setq clave (urb:ppto-cell-text rng r 1)
              valor (urb:ppto-cell-text rng r 2))
        (if (and (/= clave "") (/= valor ""))
          (setq out (cons (cons clave valor) out)))
        (setq r (1+ r)))
      (vlax-release-object rng)))
  (reverse out))

(defun urb:ppto-equiv-write (wb equiv / ws sheets rng r item)
  (setq ws (urb:ppto-find-sheet wb "URB_EQUIVALENCIAS"))
  (if (null ws)
    (progn
      (setq sheets (vlax-get-property wb 'Worksheets))
      (setq ws (vl-catch-all-apply
        '(lambda () (urb:ppto-obj (vlax-invoke-method sheets 'Add)))))
      (if (vl-catch-all-error-p ws)
        (setq ws nil)
        (vl-catch-all-apply
          '(lambda () (vlax-put-property ws 'Name "URB_EQUIVALENCIAS"))))))
  (if ws
    (progn
      (setq rng (urb:ppto-obj (vlax-get-property ws 'Range "A1:B300")))
      (vl-catch-all-apply '(lambda () (vlax-invoke-method rng 'ClearContents)))
      (setq r 1)
      (foreach item equiv
        (urb:ppto-put-cell rng r 1 (car item))
        (urb:ppto-put-cell rng r 2 (cdr item))
        (setq r (1+ r)))
      (vlax-release-object rng)
      ;; 2 = xlSheetVeryHidden: invisible incluso en "Mostrar hojas"
      (vl-catch-all-apply '(lambda () (vlax-put-property ws 'Visible 2)))
      T)))

(defun urb:ppto-equiv-key (red concepto)
  (strcat red "|" (urb:ppto-normalize concepto)))

;; ---------- configuracion DENTRO del libro (2026-08-18, v4.32) ----------
;; Ajustes propios de ESTE libro (cual hoja es el presupuesto, etc.) --
;; a diferencia de la ruta del archivo (que es por PC, en %APPDATA%), esto
;; viaja con el libro. Misma idea que equivalencias/parametricas: hoja MUY
;; OCULTA "URB_CONFIG", col A clave, col B valor.
(defun urb:ppto-cfg-read (wb / ws rng r clave valor out)
  (setq out nil)
  (setq ws (urb:ppto-find-sheet wb "URB_CONFIG"))
  (if ws
    (progn
      (setq rng (urb:ppto-obj (vlax-get-property ws 'Range "A1:B50")))
      (setq r 1 clave "x")
      (while (and (<= r 50) (/= clave ""))
        (setq clave (urb:ppto-cell-text rng r 1)
              valor (urb:ppto-cell-text rng r 2))
        (if (/= clave "") (setq out (cons (cons clave valor) out)))
        (setq r (1+ r)))
      (vlax-release-object rng)))
  (reverse out))

(defun urb:ppto-cfg-write (wb cfg / ws sheets rng r item)
  (setq ws (urb:ppto-find-sheet wb "URB_CONFIG"))
  (if (null ws)
    (progn
      (setq sheets (vlax-get-property wb 'Worksheets))
      (setq ws (vl-catch-all-apply
        '(lambda () (urb:ppto-obj (vlax-invoke-method sheets 'Add)))))
      (if (vl-catch-all-error-p ws)
        (setq ws nil)
        (vl-catch-all-apply
          '(lambda () (vlax-put-property ws 'Name "URB_CONFIG"))))))
  (if ws
    (progn
      (setq rng (urb:ppto-obj (vlax-get-property ws 'Range "A1:B50")))
      (vl-catch-all-apply '(lambda () (vlax-invoke-method rng 'ClearContents)))
      (setq r 1)
      (foreach item cfg
        (urb:ppto-put-cell rng r 1 (car item))
        (urb:ppto-put-cell rng r 2 (cdr item))
        (setq r (1+ r)))
      (vlax-release-object rng)
      (vl-catch-all-apply '(lambda () (vlax-put-property ws 'Visible 2)))
      T)))

(defun urb:ppto-cfg-get (wb clave / cfg)
  (setq cfg (urb:ppto-cfg-read wb))
  (cdr (assoc clave cfg)))

(defun urb:ppto-cfg-set (wb clave valor / cfg)
  (setq cfg (urb:ppto-cfg-read wb))
  (setq cfg (cons (cons clave valor) (vl-remove (assoc clave cfg) cfg)))
  (urb:ppto-cfg-write wb cfg))

;; ---------- actividades PARAMETRICAS (cantidad = magnitud x factor) ----------
;; Como los parametros de Revit (pedido del usuario 2026-08-18): para un
;; TIPO de elemento se define una actividad adicional del presupuesto cuya
;; cantidad se mide sola: magnitud del elemento (area, longitud, corte,
;; profundidad, unidad...) multiplicada por un factor. Viven en la hoja
;; MUY OCULTA "URB_PARAMETRICAS" del libro (col A tipo, B magnitud,
;; C factor, D actividad destino) y viajan con el presupuesto.
;; catalogo: (TIPO RED (magnitudes disponibles...))
(setq *urb-ppto-param-tipos*
  '(("VIA" "VIA"
      ("AREA" "AREA_SIN_SOBREANCHO" "LONGITUD" "CORTE" "RELLENO" "UNIDAD"))
    ;; PERIMETRO se retiro del catalogo ANDEN (2026-08-19): el bloque no
    ;; guarda PERIMETRO_M como atributo, asi que la magnitud siempre daba
    ;; 0 -- una opcion muerta que enganaba en el desplegable [+]
    ("ANDEN" "ANDEN"
      ("AREA" "TOPEROL_ML" "GUIA_ML" "TOPEROL_UND" "GUIA_UND"
       "LOSETA_LISA_M2" "LOSETA_LISA_UND" "ADOQUIN_M2" "ADOQUIN_UND"
       "UNIDAD"))
    ("RAMPA" "RAMPA-PEATONAL"
      ("AREA" "TOPEROL_ML" "BORDILLO_ML" "UNIDAD"))
    ("SARDINEL" "VIA" ("LONGITUD" "UNIDAD"))
    ("BORDILLO" "ANDEN" ("LONGITUD" "UNIDAD"))
    ("TRAMO SANITARIO" "ALC-SANITARIO"
      ("LONGITUD" "EXCAVACION" "UNIDAD"))
    ("TRAMO PLUVIAL" "ALC-PLUVIAL" ("LONGITUD" "EXCAVACION" "UNIDAD"))
    ("TRAMO ACUEDUCTO" "ACUEDUCTO" ("LONGITUD" "EXCAVACION" "UNIDAD"))
    ("POZO SANITARIO" "ALC-SANITARIO" ("PROFUNDIDAD" "UNIDAD"))
    ("POZO PLUVIAL" "ALC-PLUVIAL" ("PROFUNDIDAD" "UNIDAD"))
    ("SUMIDERO" "ALC-PLUVIAL" ("UNIDAD"))
    ("SENDERO" "SENDERO" ("AREA" "PERIMETRO" "CORTE" "RELLENO" "UNIDAD"))
    ("BIOSWALE" "ALC-PLUVIAL" ("AREA" "PERIMETRO" "UNIDAD"))
    ;; 5.6.0: canuela pluvial -- LONGITUD (ML), AREA (largo x ancho)
    ("CANUELA" "ALC-PLUVIAL" ("LONGITUD" "AREA" "UNIDAD"))
    ;; 2026-09-14 (pedido del usuario: "elabora los parametros para que
    ;; quede todo totalmente vinculado"). El emisor de zonas verdes YA
    ;; pasaba estas seis magnitudes a urb:ppto-param-rows, pero el tipo
    ;; no estaba en este catalogo: no se podia crear el parametro desde
    ;; el dialogo. El texto debe ser ZONA_VERDE con guion bajo, que es
    ;; exactamente lo que el emisor compara contra la columna A de la
    ;; hoja URB_PARAMETRICAS.
    ("ZONA_VERDE" "ZONA-VERDE"
      ("AREA" "PERIMETRO" "VOLUMEN" "CORTE" "RELLENO" "UNIDAD"))))

;; etiquetas legibles de las magnitudes (pedido 2026-08-18: la creacion de
;; parametros debe leerse como en Revit, no en clave interna)
(setq *urb-ppto-mag-labels*
  '(("AREA" "Area (m2)")
    ("AREA_SIN_SOBREANCHO" "Area sin sobreancho (m2)")
    ("LONGITUD" "Longitud (ml)")
    ("CORTE" "Corte de tierra (m3)")
    ("RELLENO" "Relleno (m3)")
    ("EXCAVACION" "Excavacion de zanja (m3)")
    ("PROFUNDIDAD" "Profundidad (m)")
    ("TOPEROL_ML" "Franja toperol (ml)")
    ("GUIA_ML" "Franja guia (ml)")
    ("TOPEROL_UND" "Losetas toperol (unidades)")
    ("GUIA_UND" "Losetas guia (unidades)")
    ("BORDILLO_ML" "Bordillo (ml)")
    ("PERIMETRO" "Perimetro (ml)")
    ("LOSETA_LISA_M2" "Area loseta lisa (m2)")
    ("LOSETA_LISA_UND" "Losetas lisas (unidades)")
    ("ADOQUIN_M2" "Area adoquin (m2)")
    ("ADOQUIN_UND" "Adoquines (unidades)")
    ;; 2026-09-14: la zona verde expone VOLUMEN (tierra negra) y sin
    ;; etiqueta el desplegable de parametros lo mostraba en clave interna
    ("VOLUMEN" "Volumen de tierra negra (m3)")
    ("UNIDAD" "Unidad (1 por elemento)")))

(defun urb:ppto-mag-label (code / entry)
  (setq entry (assoc (strcase (urb:safe-string code "")) *urb-ppto-mag-labels*))
  (if entry (cadr entry) (urb:safe-string code "?")))

(defun urb:ppto-param-read (wb / ws rng r tipo mag factor act out)
  (setq out nil)
  (setq ws (urb:ppto-find-sheet wb "URB_PARAMETRICAS"))
  (if ws
    (progn
      (setq rng (urb:ppto-obj (vlax-get-property ws 'Range "A1:F200")))
      (setq r 1 tipo "x")
      (while (and (<= r 200) (/= tipo ""))
        (setq tipo (urb:ppto-cell-text rng r 1)
              mag (urb:ppto-cell-text rng r 2)
              factor (urb:ppto-cell rng r 3)
              act (urb:ppto-cell-text rng r 4))
        (if (and (/= tipo "") (/= mag "") (/= act ""))
          (setq out
            (cons
              (list (strcase tipo) (strcase mag)
                ;; factor: numero, o CODIGO de una segunda magnitud
                ;; (v4.43: formulas MAGNITUD x MAGNITUD)
                (cond
                  ((numberp factor) factor)
                  ((and (= (type factor) 'STR)
                        (assoc (strcase factor) *urb-ppto-mag-labels*))
                    (strcase factor))
                  (T (atof (urb:safe-string factor "1"))))
                act
                ;; col E: operacion X (multiplicar, default compatible),
                ;; D (dividir), S (sumar) o R (restar) -- v4.44
                (if (member (strcase (urb:ppto-cell-text rng r 5))
                      '("D" "S" "R"))
                  (strcase (urb:ppto-cell-text rng r 5)) "X")
                ;; col F: NOMBRE del parametro (estilo Revit; vacio en
                ;; parametricas guardadas antes de v4.31 -> se muestra la
                ;; actividad destino)
                (urb:ppto-cell-text rng r 6))
              out)))
        (setq r (1+ r)))
      (vlax-release-object rng)))
  (reverse out))

(defun urb:ppto-param-write (wb params / ws sheets rng r item)
  (setq ws (urb:ppto-find-sheet wb "URB_PARAMETRICAS"))
  (if (null ws)
    (progn
      (setq sheets (vlax-get-property wb 'Worksheets))
      (setq ws (vl-catch-all-apply
        '(lambda () (urb:ppto-obj (vlax-invoke-method sheets 'Add)))))
      (if (vl-catch-all-error-p ws)
        (setq ws nil)
        (vl-catch-all-apply
          '(lambda () (vlax-put-property ws 'Name "URB_PARAMETRICAS"))))))
  (if ws
    (progn
      (setq rng (urb:ppto-obj (vlax-get-property ws 'Range "A1:F200")))
      (vl-catch-all-apply '(lambda () (vlax-invoke-method rng 'ClearContents)))
      (setq r 1)
      (foreach item params
        (urb:ppto-put-cell rng r 1 (nth 0 item))
        (urb:ppto-put-cell rng r 2 (nth 1 item))
        (urb:ppto-put-cell rng r 3 (nth 2 item))
        (urb:ppto-put-cell rng r 4 (nth 3 item))
        (urb:ppto-put-cell rng r 5
          (if (member (urb:safe-string (nth 4 item) "X") '("D" "S" "R"))
            (nth 4 item) "X"))
        (urb:ppto-put-cell rng r 6 (urb:safe-string (nth 5 item) ""))
        (setq r (1+ r)))
      (vlax-release-object rng)
      (vl-catch-all-apply '(lambda () (vlax-put-property ws 'Visible 2)))
      T)))

;; UM real de una actividad del ppto (para la fila parametrica)
(defun urb:ppto-param-um (red actividad / entry out cap)
  (setq out "" cap (urb:ppto-caps-de red))
  (foreach entry *urb-ppto-vocab*
    (if (and (urb:ppto-cap-match-p (nth 0 entry) cap)
             (= (nth 2 entry) actividad))
      (setq out (nth 1 entry))))
  out)

;; filas parametricas de UN elemento: mags = alist (MAGNITUD . valor)
(defun urb:ppto-param-rows (tipo red mags id desde hasta etapa sub handle
                            / p qty um fila out factor)
  (setq out nil)
  (if (boundp '*urb-ppto-param*)
    (foreach p *urb-ppto-param*
      (if (= (nth 0 p) tipo)
        (progn
          ;; operacion: X = magnitud x factor; D = magnitud / factor.
          ;; El factor puede ser un NUMERO o el codigo de una SEGUNDA
          ;; magnitud del mismo elemento (v4.43: LONGITUD x EXCAVACION)
          (setq qty
            (if (cdr (assoc (nth 1 p) mags))
              (cdr (assoc (nth 1 p) mags)) 0.0))
          (setq factor
            (if (numberp (nth 2 p))
              (nth 2 p)
              (if (cdr (assoc (nth 2 p) mags))
                (cdr (assoc (nth 2 p) mags)) 0.0)))
          (setq qty
            (cond
              ((= (urb:safe-string (nth 4 p) "X") "S") (+ qty factor))
              ((= (urb:safe-string (nth 4 p) "X") "R") (- qty factor))
              ((and (= (urb:safe-string (nth 4 p) "X") "D")
                    (> factor 0.0))
                (/ qty factor))
              (T (* qty factor))))
          (setq um (urb:ppto-param-um red (nth 3 p)))
          (if (= um "") (setq um "?"))
          (setq fila
            (urb:ppto-row red (nth 3 p) id desde hasta etapa sub um qty
              handle))
          (if fila (setq out (cons fila out)))))))
  out)

;; ---------- normalizacion y match ----------
(defun urb:ppto-plain-char (code)
  ;; acentos/enie/simbolos ANSI -> ascii; lo demas no alfanumerico -> espacio
  (cond
    ((member code '(225 193)) "a") ((member code '(233 201)) "e")
    ((member code '(237 205)) "i") ((member code '(243 211)) "o")
    ((member code '(250 218 252 220)) "u") ((member code '(241 209)) "n")
    ((and (>= code 48) (<= code 57)) (chr code))
    ((and (>= code 97) (<= code 122)) (chr code))
    ((and (>= code 65) (<= code 90)) (chr (+ code 32)))
    ((= code 45) "-")
    (T " ")))

(defun urb:ppto-normalize (text / i n out)
  (setq text (urb:safe-string text "") i 1 n (strlen text) out "")
  (while (<= i n)
    (setq out (strcat out (urb:ppto-plain-char (ascii (substr text i 1)))))
    (setq i (1+ i)))
  ;; colapsar espacios
  (while (vl-string-search "  " out)
    (setq out (vl-string-subst " " "  " out)))
  (vl-string-trim " -" out))

(defun urb:ppto-words (text / raw result token)
  (setq raw (urb:split-string (urb:ppto-normalize text) " ") result nil)
  (foreach token raw
    (setq token (vl-string-trim "-" token))
    (if (and (> (strlen token) 0)
             (not (member token *urb-ppto-stopwords*)))
      (setq result (cons token result))))
  (reverse result))

(defun urb:ppto-digits (token / i c out)
  (setq i 1 out "")
  (repeat (strlen token)
    (setq c (substr token i 1))
    (if (wcmatch c "#") (setq out (strcat out c)))
    (setq i (1+ i)))
  out)

(defun urb:ppto-word-match-p (a b / la lb da db)
  (setq la (strlen a) lb (strlen b))
  (cond
    ((= a b) T)
    ;; raiz: prefijo >= 3 letras en cualquiera de los dos sentidos,
    ;; solo para tokens SIN digitos (exc ~ excavacion, no 8 ~ 18)
    ((and (= (urb:ppto-digits a) "") (= (urb:ppto-digits b) "")
          (>= (min la lb) 3)
          (or (= a (substr b 1 la)) (= b (substr a 1 lb)))) T)
    ;; t2400 ~ 2400: mismos digitos y a lo sumo 1 letra de prefijo
    ((and (/= (setq da (urb:ppto-digits a)) "")
          (= da (setq db (urb:ppto-digits b)))
          (<= (- la (strlen da)) 1)
          (<= (- lb (strlen db)) 1)) T)
    (T nil)))

(defun urb:ppto-score (term-words cand-words / hits w)
  (setq hits 0)
  (foreach w term-words
    (if (vl-some '(lambda (c) (urb:ppto-word-match-p w c)) cand-words)
      (setq hits (1+ hits))))
  (if (> (length term-words) 0)
    (/ (float hits) (float (length term-words)))
    0.0))

;; vocab: lista de (capitulo-norm um-mayuscula desc-original palabras fila)
;; devuelve (desc-original . fila) si hay UNA mejor candidata con score>=0.5;
;; si no, (list 'HUERFANA candidatas-con-score>=0.5)
;; capitulo comodin "*" (2026-08-19): las actividades de presupuestos por
;; secciones (sin NIVEL) valen para CUALQUIER red del plano -- una misma
;; hoja puede traer anden + redes + mas, y la disciplina la decide el
;; match por unidad+texto (o la asignacion manual), sin preguntar.
;; capitulo puede ser una CADENA o una LISTA de capitulos (red con alias)
(defun urb:ppto-cap-match-p (item-cap capitulo)
  (or (= item-cap "*")
      (and capitulo
        (if (listp capitulo)
          (member item-cap capitulo)
          (= item-cap capitulo)))))

(defun urb:ppto-match (red um concepto vocab / capitulo words best best-n
                       second item score exacto sin-um)
  (setq capitulo (urb:ppto-caps-de red))
  ;; 5.7.21 (barrido de conexion 2026-09-23): las filas PARAMETRICAS
  ;; (URB_PARAMETRICAS) no traen unidad -- la tabla no tiene esa columna --
  ;; y la comparacion de unidad las mandaba SIEMPRE a huerfanas (168 filas
  ;; del maestro: loseta guia, toperol, M.O. de instalacion, corte y
  ;; relleno de zona verde). Sin unidad se empareja solo por capitulo y
  ;; texto, que para estas filas ES el texto exacto del presupuesto.
  (setq sin-um (= (urb:safe-string um "") ""))
  ;; igualdad EXACTA de descripcion (caso de las actividades parametricas,
  ;; cuyo concepto ES el texto del ppto): gana directo, sin scoring
  (foreach item vocab
    (if (and (null exacto)
             (urb:ppto-cap-match-p (nth 0 item) capitulo)
             (or sin-um (= (nth 1 item) (strcase um)))
             (= (nth 2 item) concepto))
      (setq exacto item)))
  (if exacto
    (cons (nth 2 exacto) (nth 4 exacto))
    (urb:ppto-match-score red um concepto vocab capitulo)))

(defun urb:ppto-match-score (red um concepto vocab capitulo / words best
                             best-n second item score sin-um)
  (setq words (urb:ppto-words concepto))
  (setq sin-um (= (urb:safe-string um "") ""))
  (setq best nil best-n 0 second 0.0)
  (foreach item vocab
    (if (and (urb:ppto-cap-match-p (nth 0 item) capitulo)
             (or sin-um (= (nth 1 item) (strcase um))))
      (progn
        (setq score (urb:ppto-score words (nth 3 item)))
        (if (>= score 0.5)
          (progn
            (setq best-n (1+ best-n))
            (cond
              ((or (null best) (> score (cadr best)))
                (setq second (if best (cadr best) 0.0))
                (setq best (list item score)))
              ;; misma actividad DUPLICADA en otra seccion del ppto
              ;; (texto identico): no es ambiguedad real, no bloquea
              ((and (= score (cadr best))
                    (= (nth 2 item) (nth 2 (car best)))) nil)
              ((> score second) (setq second score))))))))
  (cond
    ((and best (> (cadr best) second))
      (cons (nth 2 (car best)) (nth 4 (car best))))
    (T (list 'HUERFANA best-n))))

;; ---------- Excel: enganche, validacion, vocabulario ----------
(defun urb:ppto-variant (value / out)
  (setq out value)
  (while (= (type out) 'variant) (setq out (vlax-variant-value out)))
  out)

;; desenvuelve un objeto COM que Item/Add pueden devolver como VARIANT
(defun urb:ppto-obj (value)
  (if (= (type value) 'variant) (vlax-variant-value value) value))

;; ListObjects.Item por CADENA da "type mismatch" via vlax (2026-08-17):
;; iterar por indice y comparar Name.
(defun urb:ppto-find-listobject (ws nombre / los count i lo nm found)
  (setq los (vlax-get-property ws 'ListObjects))
  (setq count
    (vl-catch-all-apply '(lambda () (vlax-get-property los 'Count))))
  (if (vl-catch-all-error-p count) (setq count 0))
  (setq i 1 found nil)
  (while (and (<= i count) (null found))
    ;; OJO: en ListObjects, Item es PROPIEDAD (get-property); via
    ;; invoke-method da "type mismatch" incluso con indice entero.
    (setq lo (vl-catch-all-apply
      '(lambda () (vlax-get-property los 'Item i))))
    (if (not (vl-catch-all-error-p lo))
      (progn
        (setq lo (urb:ppto-obj lo))
        (setq nm (vl-catch-all-apply
          '(lambda () (vlax-get-property lo 'Name))))
        (if (and (not (vl-catch-all-error-p nm))
                 (= (strcase nm) (strcase nombre)))
          (setq found lo))))
    (setq i (1+ i)))
  found)

(defun urb:ppto-cell (rng row col / cell v)
  ;; Range.Item llega como VARIANT (VT_DISPATCH): hay que desenvolverlo
  ;; antes de usarlo como objeto ("bad argument type: VLA-OBJECT" 2026-08-17)
  (setq cell (vlax-get-property rng 'Item row col))
  (if (= (type cell) 'variant) (setq cell (vlax-variant-value cell)))
  (setq v (urb:ppto-variant (vlax-get-property cell 'Value2)))
  (vlax-release-object cell)
  v)

(defun urb:ppto-cell-text (rng row col / v)
  (setq v (urb:ppto-cell rng row col))
  (cond
    ((= (type v) 'STR) v)
    ((numberp v) (rtos v 2 8))
    (T "")))

;; Lectura EN BLOQUE de un rango (2026-08-19, medido en el libro real:
;; 600 celdas leidas UNA por UNA vs Range.Item = 36 segundos y hasta
;; rechazo de llamadas COM -- RPC_E_CALL_REJECTED -- con formulas
;; volatiles/hojas de calculo pesadas como DINAMICA/BD. Un solo
;; Range.Value2 trae TODO el bloque en UNA llamada COM en vez de
;; filas*columnas llamadas. Devuelve una lista de FILAS, cada una una
;; lista de `cols` textos (mismo formato que urb:ppto-cell-text). Si algo
;; falla, devuelve nil (el llamador debe caer de vuelta a
;; urb:ppto-cell-text celda por celda si hace falta).
(defun urb:ppto-read-block (rng filas cols / varr lo-r lo-c out r c fila v)
  (setq varr (vl-catch-all-apply
    '(lambda () (vlax-variant-value (vlax-get-property rng 'Value2)))))
  (if (or (vl-catch-all-error-p varr) (null varr))
    nil
    (progn
      (setq lo-r (vl-catch-all-apply
        '(lambda () (vlax-safearray-get-l-bound varr 1))))
      (setq lo-c (vl-catch-all-apply
        '(lambda () (vlax-safearray-get-l-bound varr 2))))
      (if (or (vl-catch-all-error-p lo-r) (vl-catch-all-error-p lo-c))
        nil
        (progn
          (setq out nil r 0)
          (while (< r filas)
            (setq fila nil c 0)
            (while (< c cols)
              (setq v (vl-catch-all-apply
                '(lambda ()
                  (urb:ppto-variant
                    (vlax-safearray-get-element varr (+ lo-r r) (+ lo-c c))))))
              (setq fila
                (cons
                  (cond
                    ((vl-catch-all-error-p v) "")
                    ((= (type v) 'STR) v)
                    ((numberp v) (rtos v 2 8))
                    (T ""))
                  fila))
              (setq c (1+ c)))
            (setq out (cons (reverse fila) out))
            (setq r (1+ r)))
          (reverse out)))))
)

(defun urb:ppto-put-cell (rng row col value / cell)
  (setq cell (vlax-get-property rng 'Item row col))
  (if (= (type cell) 'variant) (setq cell (vlax-variant-value cell)))
  (vlax-put-property cell 'Value2 value)
  (vlax-release-object cell))

;; ultimo segmento de una URL (https://.../carpeta/libro.xlsx -> libro.xlsx),
;; con los %20 de SharePoint devueltos a espacios
(defun urb:ppto-url-filename (url / pos s)
  (setq s url pos (vl-string-search "/" s))
  (while pos
    (setq s (substr s (+ pos 2)) pos (vl-string-search "/" s)))
  (while (setq pos (vl-string-search "%20" s))
    (setq s (strcat (substr s 1 pos) " " (substr s (+ pos 4)))))
  s)

;; Devuelve (app wb propia-p) o (nil nil mensaje).
(defun urb:ppto-attach-excel (path / lock app wbs count i wb name result)
  (setq lock
    (strcat (vl-filename-directory path) "\\~$"
      (strcat (vl-filename-base path) (vl-filename-extension path))))
  ;; 1) instancia ya corriendo con el libro abierto?
  (setq app (vl-catch-all-apply 'vlax-get-object (list "Excel.Application")))
  (if (vl-catch-all-error-p app) (setq app nil))
  (setq wb nil)
  (if app
    (progn
      (setq wbs (vlax-get-property app 'Workbooks))
      (setq count (vlax-get-property wbs 'Count) i 1)
      (while (and (<= i count) (null wb))
        (setq name
          (vl-catch-all-apply
            '(lambda ()
              (vlax-get-property
                (urb:ppto-obj (vlax-get-property wbs 'Item i)) 'FullName))))
        ;; 5.6.9 (reporte del usuario: "no me esta dejando conectar al libro"):
        ;; un libro de una carpeta sincronizada con SharePoint/OneDrive
        ;; reporta FullName como URL (https://...sharepoint.com/.../x.xlsx),
        ;; nunca como la ruta local. La comparacion exacta fallaba, el plugin
        ;; intentaba abrirlo OTRA VEZ en una instancia oculta y Excel
        ;; respondia "no puede obtener acceso al archivo". Ahora tambien se
        ;; reconoce por NOMBRE de archivo cuando FullName es una URL.
        (if (and (not (vl-catch-all-error-p name))
                 (or (= (strcase name) (strcase path))
                     (and (wcmatch (strcase name) "HTTP*")
                          (= (strcase (urb:ppto-url-filename name))
                             (strcase (strcat (vl-filename-base path)
                                              (vl-filename-extension path)))))))
          (setq wb (urb:ppto-obj (vlax-get-property wbs 'Item i))))
        (setq i (1+ i)))
      (vlax-release-object wbs)
      ;; 5.6.9: un Excel OCULTO y SIN libros es un sobrante de un intento
      ;; anterior (visto hoy: PID vivo desde la manana, 0 libros, y cada
      ;; "Reintentar abrir" chocaba con el). Se cierra y se sigue con uno
      ;; nuevo; nunca se toca un Excel visible del usuario.
      (if (and (null wb) (= count 0)
               (not (vl-catch-all-error-p
                      (vl-catch-all-apply 'vlax-get-property (list app 'Visible))))
               (= (vlax-get-property app 'Visible) :vlax-false))
        (progn
          (vl-catch-all-apply 'vlax-invoke-method (list app 'Quit))
          (vl-catch-all-apply 'vlax-release-object (list app))
          (gc) (gc)
          (prompt "\nPresupuesto: se cerro un Excel oculto sobrante de un intento anterior.")))))
  (cond
    (wb (list app wb nil))
    ;; 2) lock ~$: puede ser un HUERFANO de un Excel que cerro mal (visto
    ;; 2026-08-18 con el libro cerrado). Si se deja eliminar era huerfano
    ;; y se continua; si NO se deja, un Excel vivo (otra sesion/PC) lo
    ;; tiene -> abortar (nunca escritura parcial).
    ((and (findfile lock) (not (vl-file-delete lock)))
      (list nil nil
        (strcat "El libro esta abierto en otra sesion/PC (lock "
          lock "). Cierre el libro alla y reintente.")))
    ;; 3) instancia propia oculta (con UN reintento: create-object puede
    ;; fallar transitoriamente justo despues de cerrarse otra instancia)
    (T
      (setq app (vl-catch-all-apply 'vlax-create-object
        (list "Excel.Application")))
      (if (vl-catch-all-error-p app)
        (progn
          (setq app (vl-catch-all-apply 'vlax-create-object
            (list "Excel.Application")))))
      (if (vl-catch-all-error-p app)
        (list nil nil "No fue posible iniciar Excel (COM, 2 intentos).")
        (progn
          (vlax-put-property app 'DisplayAlerts :vlax-false)
          (setq result
            (vl-catch-all-apply
              '(lambda ()
                (vlax-invoke-method
                  (vlax-get-property app 'Workbooks) 'Open path))))
          (if (vl-catch-all-error-p result)
            (progn
              (vl-catch-all-apply 'vlax-invoke-method (list app 'Quit))
              (vlax-release-object app) (gc) (gc)
              (list nil nil
                (strcat "No fue posible abrir el libro: "
                  (vl-catch-all-error-message result))))
            (list app result T)))))))

;; Valida TM_MEMORIAS + firma de 12 encabezados; en libro nuevo crea la
;; hoja MEMORIAS, la tabla y el nombre definido. Devuelve el ListObject
;; TablaMemorias o nil (con mensaje por prompt).
(defun urb:ppto-find-name (wb tag / nm)
  ;; Item por CADENA via invoke-method (Names.Item es metodo). NO iterar la
  ;; coleccion: los nombres rotos (#REF!) del libro real crashean acad
  ;; (access violation, no atrapable) -- visto 2026-08-17.
  (setq nm
    (vl-catch-all-apply
      '(lambda ()
        (vlax-invoke-method (vlax-get-property wb 'Names) 'Item tag))))
  (if (vl-catch-all-error-p nm) nil nm))

(defun urb:ppto-memorias-table (wb / names nm refrange ws headers i ok lo
                                sheets result)
  (setq nm (urb:ppto-find-name wb "TM_MEMORIAS"))
  (if (null nm)
    (progn
      ;; libro nuevo: crear hoja + encabezados + tabla + nombre (defensivo:
      ;; reutiliza la hoja MEMORIAS si ya existe)
      (setq sheets (vlax-get-property wb 'Worksheets))
      (setq ws (vl-catch-all-apply
        '(lambda () (urb:ppto-obj (vlax-get-property sheets 'Item "MEMORIAS")))))
      (if (vl-catch-all-error-p ws)
        (progn
          (setq ws (vlax-invoke-method sheets 'Add))
          (vl-catch-all-apply
            '(lambda () (vlax-put-property ws 'Name "MEMORIAS"))))
        ;; PROTECCION (2026-08-19, consulta del usuario "que pasa si ya
        ;; tengo una hoja MEMORIAS"): si la hoja YA existia y su fila 1
        ;; tiene contenido que NO es la firma de encabezados del plugin,
        ;; es una hoja AJENA -- no se le escribe ni una celda; se aborta
        ;; con mensaje (renombrarla o usar otro libro).
        (progn
          (setq refrange (vlax-get-property ws 'Range "A1:L1"))
          (setq ok T i 1)
          (foreach h *urb-ppto-headers*
            (if (/= (strcase (urb:ppto-cell-text refrange 1 i)) h)
              (setq ok nil))
            (setq i (1+ i)))
          (vlax-release-object refrange)
          (if (and (not ok)
                   (/= (urb:ppto-cell-text
                         (setq refrange
                           (vlax-get-property ws 'Range "A1:L1")) 1 1) ""))
            (progn
              (vlax-release-object refrange)
              (prompt "\nEl libro ya tiene una hoja MEMORIAS con OTRO contenido: no se toco. Renombre esa hoja o use otro libro.")
              (setq ws nil)))))
      (if (null ws)
        nil
        (progn
      (setq refrange (vlax-get-property ws 'Range "A1:L1"))
      (setq i 1)
      (foreach h *urb-ppto-headers*
        (urb:ppto-put-cell refrange 1 i h)
        (setq i (1+ i)))
      (setq result
        (vl-catch-all-apply
          '(lambda ()
            (vlax-invoke-method
              (vlax-get-property ws 'ListObjects) 'Add
              1 refrange nil 1))))
      (if (not (vl-catch-all-error-p result))
        (vl-catch-all-apply
          '(lambda () (vlax-put-property result 'Name "TablaMemorias"))))
      (setq names (vlax-get-property wb 'Names))
      (vl-catch-all-apply
        '(lambda ()
          (vlax-invoke-method names 'Add "TM_MEMORIAS"
            "=MEMORIAS!$A$1:$L$1")))
      (prompt "\nLibro nuevo: hoja MEMORIAS + TablaMemorias creadas.")
      (setq nm (urb:ppto-find-name wb "TM_MEMORIAS"))))))
  (if nm
    (setq refrange
      (vl-catch-all-apply
        '(lambda () (vlax-get-property nm 'RefersToRange))))
    (progn
      ;; fallback sin Names (el libro real tiene nombres rotos #REF!):
      ;; hoja MEMORIAS directa; la firma de encabezados sigue validando.
      (prompt "\nTM_MEMORIAS no accesible; validando la hoja MEMORIAS directo.")
      (setq refrange
        (vl-catch-all-apply
          '(lambda ()
            (vlax-get-property
              (vlax-get-property
                (vlax-get-property wb 'Worksheets) 'Item "MEMORIAS")
              'Range "A1:L1"))))))
  (if (vl-catch-all-error-p refrange)
    (progn (prompt "\nNi TM_MEMORIAS ni la hoja MEMORIAS son accesibles.") nil)
    (progn
      (setq ws (vlax-get-property refrange 'Worksheet))
      (setq ok T i 1)
      (foreach h *urb-ppto-headers*
        (if (/= (strcase (urb:ppto-cell-text refrange 1 i)) h)
          (setq ok nil))
        (setq i (1+ i)))
      (if (not ok)
        (progn
          (prompt
            "\nFirma de encabezados de MEMORIAS no coincide. ABORTADO.")
          nil)
        (progn
          (setq lo (urb:ppto-find-listobject ws "TablaMemorias"))
          (if (null lo)
            (progn (prompt "\nNo existe la tabla TablaMemorias.") nil)
            lo))))))

;; Vocabulario vivo: hoja con encabezados NIVEL/DESCRIPCION/UM.
;; busca en TODAS las hojas del libro, en las filas 1..15 de cada una, la
;; fila de encabezados NIVEL (col A) / DESCRIPCION* (col D) / UM (col E).
;; No exige que exista una tabla de Excel: solo esos 3 encabezados en algun
;; punto arriba de la hoja. Devuelve (("Hoja1" . fila-encabezado) ...).
;; 2026-08-19: reescrita para leer cada hoja EN BLOQUE (una llamada COM)
;; en vez de celda por celda (hasta 75 llamadas por hoja) -- medido en el
;; libro real: 36s y rechazo de llamadas COM (RPC_E_CALL_REJECTED) con
;; hojas de calculo pesadas (formulas volatiles). Con bloque: <1s. Si el
;; bloque falla en una hoja puntual, esa hoja cae de vuelta a leer celda
;; por celda (nunca se deja de revisar una hoja por un fallo del atajo).
;; 2026-08-19: tope de filas subido 15->40 -- se descubrio en vivo que un
;; libro real (PEATONAL 3 Y 4.xlsx) tiene su encabezado en la fila 20
;; (bloques de metadatos/totales arriba). Con la lectura en bloque (v4.39)
;; escanear mas filas cuesta lo mismo (sigue siendo UNA llamada COM), asi
;; que no hay motivo para quedarse corto.
(setq *urb-ppto-tope-filas-header* 40)
(defun urb:ppto-vocab-candidatas (wb / sheets count i ws rng bloque fila
                                  r c1 c4 c5 out nombre tope)
  (setq tope *urb-ppto-tope-filas-header*)
  (setq sheets (vlax-get-property wb 'Worksheets))
  (setq count (vlax-get-property sheets 'Count) i 1 out nil)
  (while (<= i count)
    (setq ws (urb:ppto-obj (vlax-get-property sheets 'Item i)))
    (setq rng (urb:ppto-obj (vlax-get-property ws 'Range
      (strcat "A1:E" (itoa tope)))))
    (setq bloque (urb:ppto-read-block rng tope 5))
    (setq r 1)
    (while (<= r tope)
      (if bloque
        (progn
          (setq fila (nth (1- r) bloque))
          (setq c1 (strcase (nth 0 fila)) c4 (strcase (nth 3 fila))
                c5 (strcase (nth 4 fila))))
        (progn
          (setq c1 (strcase (urb:ppto-cell-text rng r 1)))
          (setq c4 (strcase (urb:ppto-cell-text rng r 4)))
          (setq c5 (strcase (urb:ppto-cell-text rng r 5)))))
      (if (and (= c1 "NIVEL") (wcmatch c4 "DESCRIPCION*") (= c5 "UM"))
        (progn
          (setq nombre
            (vl-catch-all-apply '(lambda () (vlax-get-property ws 'Name))))
          (if (not (vl-catch-all-error-p nombre))
            (setq out (cons (cons nombre r) out)))
          (setq r 99)))
      (setq r (1+ r)))
    (vlax-release-object rng)
    (setq i (1+ i)))
  (reverse out))

;; extrae vocabulario + arbol de UNA hoja ya identificada como presupuesto,
;; con su fila de encabezado. Convencion del libro real: 1 fila de
;; "sub-encabezado" entre el encabezado y el primer dato (header+1 se
;; salta), igual que el diseno original con header fijo en fila 1 -> datos
;; desde fila 3.
;; 2026-08-19: reescrita para leer en BLOQUES de 500 filas (una llamada
;; COM por bloque) en vez de fila por fila (hasta 8000 filas x 4 celdas =
;; 32000 llamadas). Medido en el libro real: la lectura celda a celda de
;; solo 600 celdas de encabezados ya tomaba 36s con formulas volatiles
;; (DINAMICA/BD) -- con ~1500 filas reales de actividades esto explicaba
;; la demora larga al abrir "Presupuesto". Con bloques: unas pocas
;; llamadas COM en vez de miles. Si el bloque falla en un tramo puntual,
;; ESE tramo cae de vuelta a leer celda por celda (nunca se pierden filas
;; por un fallo del atajo).
(defun urb:ppto-vocab-extraer (ws header-row / capitulo seccion vocab
                               empties r nivel-txt codigo desc um limite
                               bsize base fin chunk-rng bloque idx fila
                               nivel rr tmp)
  ;; seccion = titulo nivel 4 vigente (v4.46: para el match por ZONA de
  ;; parque -- campo 7 de cada entrada del vocabulario)
  (setq capitulo "" seccion "" vocab nil empties 0
        r (+ header-row 2) limite 8000)
  (setq *urb-ppto-outline* nil)
  (setq bsize 500)
  (while (and (<= r limite) (< empties 80))
    (setq base r)
    (setq fin (min limite (+ base bsize -1)))
    (setq chunk-rng (vlax-get-property ws 'Range
      (strcat "A" (itoa base) ":E" (itoa fin))))
    (setq bloque (urb:ppto-read-block chunk-rng (1+ (- fin base)) 5))
    (if (null bloque)
      (progn
        (setq rr 1 tmp nil)
        (while (<= rr (1+ (- fin base)))
          (setq tmp
            (cons
              (list (urb:ppto-cell-text chunk-rng rr 1) ""
                    (urb:ppto-cell-text chunk-rng rr 3)
                    (urb:ppto-cell-text chunk-rng rr 4)
                    (urb:ppto-cell-text chunk-rng rr 5))
              tmp))
          (setq rr (1+ rr)))
        (setq bloque (reverse tmp))))
    (vlax-release-object chunk-rng)
    (setq idx 0)
    (while (and (<= r fin) (< empties 80))
      (setq fila (nth idx bloque))
      (setq nivel-txt (nth 0 fila) codigo (nth 2 fila) desc (nth 3 fila)
            um (nth 4 fila))
      (setq nivel (if (/= nivel-txt "") (atof nivel-txt) nil))
      (if (and (null nivel) (= desc ""))
        (setq empties (1+ empties))
        (progn
          (setq empties 0)
          (if nivel
            (progn
              (if (= (fix nivel) 3)
                (progn
                  (setq capitulo (urb:ppto-normalize desc))
                  (setq seccion "")))
              (if (= (fix nivel) 4)
                (setq seccion (urb:ppto-normalize desc)))
              (if (and (>= (fix nivel) 3) (/= desc ""))
                (setq *urb-ppto-outline*
                  (cons
                    (list (fix nivel) codigo desc (strcase um) capitulo)
                    *urb-ppto-outline*)))
              (if (and (= (fix nivel) 5) (/= desc "") (/= um ""))
                (setq vocab
                  (cons
                    (list capitulo (strcase um) desc
                          (urb:ppto-words desc) r codigo seccion)
                    vocab)))))))
      (setq r (1+ r) idx (1+ idx))))
  (setq *urb-ppto-outline* (reverse *urb-ppto-outline*))
  (reverse vocab))

;; resuelve QUE hoja leer: preferencia guardada en el libro (URB_CONFIG,
;; clave HOJA_PRESUPUESTO) si sigue siendo valida; si no hay preferencia y
;; hay una sola candidata, se usa y se guarda sola (sin preguntar); si hay
;; varias candidatas y el usuario esta interactivo, se pregunta con un
;; dialogo y la eleccion se guarda; en corridas headless se toma la
;; primera y se deja constancia en el log.
(defun urb:ppto-resolver-hoja (wb / candidatas pref entry elegida)
  (setq candidatas (urb:ppto-vocab-candidatas wb))
  (setq pref (urb:ppto-cfg-get wb "HOJA_PRESUPUESTO"))
  (setq entry (if pref (assoc pref candidatas) nil))
  (cond
    (entry entry)
    ((null candidatas) nil)
    ((= (length candidatas) 1)
      (urb:ppto-cfg-set wb "HOJA_PRESUPUESTO" (caar candidatas))
      (car candidatas))
    ((and (boundp '*urb-ppto-sin-dialogo*) *urb-ppto-sin-dialogo*)
      (prompt (strcat "\nOJO: " (itoa (length candidatas))
        " hojas parecen presupuesto (candidata usada: " (caar candidatas)
        "); use PPTOLIBRO para fijar cual es."))
      (car candidatas))
    (T
      (setq elegida (urb:ppto-elegir-hoja-dialog candidatas
        (strcat (if pref
          (strcat "La hoja guardada (\"" pref
            "\") ya no tiene encabezados de presupuesto. ")
          "")
          "Hay " (itoa (length candidatas))
          " hoja(s) con encabezados NIVEL/DESCRIPCION/UM: elija cual es"
          " el presupuesto vigente.")))
      (if elegida
        (progn
          (urb:ppto-cfg-set wb "HOJA_PRESUPUESTO" (car elegida))
          elegida)
        (car candidatas)))))

(defun urb:ppto-write-hoja-dcl ()
  (urb:write-dialog-dcl
    "urb_ppto_hoja"
    '*urb-ppto-hoja-dcl-ok*
    (list
      "urb_ppto_hoja : dialog { label = \"Elegir la hoja del presupuesto\";"
      ": text { key = \"info\"; width = 90; }"
      ": list_box { key = \"hojas\"; label = \"Hojas del libro con encabezados NIVEL/DESCRIPCION/UM\"; width = 90; height = 10; }"
      "ok_cancel; }")))

;; candidatas: (("Hoja1" . fila) ...). Devuelve la elegida (par) o nil si
;; cancela. Blindado (2026-08-18, bug real en vivo): load_dialog exige un
;; NOMBRE DE ARCHIVO como argumento -- si urb:write-dialog-dcl no pudo
;; escribir el .dcl temporal (carpeta temp con problema transitorio) y
;; devuelve nil, pasarlo directo a load_dialog crashea con
;; "bad argument type: stringp nil" en vez de avisar con un mensaje claro.
(defun urb:ppto-elegir-hoja-dialog (candidatas info / dcl c done sel dclfile)
  (setq sel nil)
  (setq dclfile (urb:ppto-write-hoja-dcl))
  (if (null dclfile)
    (alert "No se pudo preparar el dialogo de seleccion de hoja (revise permisos de la carpeta temporal de Windows).")
    (progn
      (setq dcl (load_dialog dclfile))
      (if (and (> dcl 0) (new_dialog "urb_ppto_hoja" dcl))
        (progn
          (set_tile "info" (urb:safe-string info ""))
          (start_list "hojas")
          (foreach c candidatas
            (add_list
              (strcat (urb:safe-string (car c) "?")
                "  (encabezado en fila " (itoa (cdr c)) ")")))
          (end_list)
          (set_tile "hojas" "0")
          ;; CAUSA RAIZ del "bad argument type: stringp nil" visto en vivo
          ;; (2026-08-18 en Elegir hoja y 2026-08-19 en Elegir red,
          ;; reproducido con driver interactivo): get_tile DESPUES de
          ;; start_dialog es invalido (el dialogo ya no existe) y devuelve
          ;; nil a veces -> (atoi nil) revienta. La seleccion se captura
          ;; DENTRO del action_tile del boton OK, mientras el dialogo vive.
          (setq *urb-ppto-hoja-sel* "0")
          (action_tile "accept"
            "(setq *urb-ppto-hoja-sel* (get_tile \"hojas\")) (done_dialog 1)")
          (setq done (start_dialog))
          (if (= done 1)
            (setq sel
              (nth (atoi (urb:safe-string *urb-ppto-hoja-sel* "0"))
                candidatas)))))
      (if (and dcl (> dcl 0)) (unload_dialog dcl))))
  sel)

;; ---------- presupuesto SIN columna NIVEL, "por secciones" (2026-08-19) ----------
;; Pedido del usuario tras probar con "PEATONAL 3 Y 4.xlsx": ese formato no
;; tiene NIVEL/CODIGO -- la jerarquia se lee por que columna trae texto:
;; fila de SECCION = una sola columna con texto y la de unidad vacia (ej.
;; "Descapote y nivelacion subrasante" solo en la columna del "codigo",
;; sin unidad); fila de ACTIVIDAD = descripcion + una unidad reconocida
;; (M2, M3, ML, UN...) en la columna que el encabezado marco como
;; UM/UN/UND. Solo se activa como RESPALDO, cuando el escaneo normal (con
;; NIVEL) no encuentra nada -- el camino ya probado no se toca.
(setq *urb-ppto-unidades-conocidas*
  '("M2" "M3" "ML" "M" "UN" "UND" "KG" "TON" "GL" "GLB" "HA" "L" "DIA"
    "VJ" "PAR" "JGO" "KM"))

;; busca, en una hoja, una fila (1-15) con DESCRIPCION en alguna columna
;; (1-12) y UM/UN/UND en otra de la MISMA fila. Devuelve (fila col-desc
;; col-um) o nil. No exige NIVEL -- por eso encuentra "PPTO" (COD |
;; DESCRIPCION | UN | CANT) ademas de books con NIVEL.
;; 2026-08-19: bloque en vez de celda a celda (mismo motivo que
;; urb:ppto-vocab-candidatas -- ver su comentario).
(defun urb:ppto-header-scan-b (ws / rng r c col-desc col-um encontrado
                               txt bloque fila tope)
  (setq tope *urb-ppto-tope-filas-header*)
  (setq rng (urb:ppto-obj (vlax-get-property ws 'Range
    (strcat "A1:L" (itoa tope)))))
  (setq bloque (urb:ppto-read-block rng tope 12))
  (setq encontrado nil r 1)
  (while (and (<= r tope) (null encontrado))
    (setq col-desc nil col-um nil c 1)
    (setq fila (if bloque (nth (1- r) bloque) nil))
    (while (<= c 12)
      (setq txt
        (strcase
          (if bloque (nth (1- c) fila) (urb:ppto-cell-text rng r c))))
      (cond
        ((wcmatch txt "DESCRIPCION*") (setq col-desc c))
        ((member txt '("UM" "UN" "UND")) (setq col-um c)))
      (setq c (1+ c)))
    (if (and col-desc col-um) (setq encontrado (list r col-desc col-um)))
    (setq r (1+ r)))
  (vlax-release-object rng)
  encontrado)

;; candidatas formato-B en TODO el libro: (("Hoja1" . (fila col-desc
;; col-um)) ...)
(defun urb:ppto-vocab-candidatas-b (wb / sheets count i ws info out
                                    nombre)
  (setq sheets (vlax-get-property wb 'Worksheets))
  (setq count (vlax-get-property sheets 'Count) i 1 out nil)
  (while (<= i count)
    (setq ws (urb:ppto-obj (vlax-get-property sheets 'Item i)))
    (setq info (urb:ppto-header-scan-b ws))
    (if info
      (progn
        (setq nombre (vl-catch-all-apply
          '(lambda () (vlax-get-property ws 'Name))))
        (if (not (vl-catch-all-error-p nombre))
          (setq out (cons (cons nombre info) out)))))
    (setq i (1+ i)))
  (reverse out))

;; extrae el vocabulario de una hoja formato-B. capitulo = el valor de
;; *urb-ppto-red-capitulo* de la red elegida por el usuario para TODA la
;; hoja (no hay disciplinas separadas dentro de un archivo asi). El arbol
;; (*urb-ppto-outline*) se sintetiza con un solo nivel 3 (el nombre de la
;; red) y las actividades directo debajo como nivel 5 -- sin nivel 4,
;; porque los titulos de seccion del archivo no corresponden a una red
;; distinta, son solo fases de obra dentro de la misma.
;; 2026-08-19: en bloques de 500 filas (una llamada COM por bloque) --
;; mismo motivo que urb:ppto-vocab-extraer (Formato A).
(defun urb:ppto-vocab-extraer-b (ws col-desc col-um header-row
                                 / vocab empties r desc um limite bsize
                                 base fin chunk-rng bloque idx fila
                                 fila-rng)
  (setq vocab nil empties 0 r (1+ header-row) limite 8000)
  ;; capitulo comodin "*": las actividades valen para cualquier red
  (setq *urb-ppto-outline*
    (list (list 3 "" "PRESUPUESTO (toda la hoja)" "" "*")))
  (setq bsize 500)
  (while (and (<= r limite) (< empties 200))
    (setq base r)
    (setq fin (min limite (+ base bsize -1)))
    (setq chunk-rng (vlax-get-property ws 'Range
      (strcat "A" (itoa base) ":P" (itoa fin))))
    (setq bloque (urb:ppto-read-block chunk-rng (1+ (- fin base)) 16))
    (vlax-release-object chunk-rng)
    (setq idx 0)
    (while (and (<= r fin) (< empties 200))
      (if bloque
        (progn
          (setq fila (nth idx bloque))
          (setq desc (nth (1- col-desc) fila))
          (setq um (strcase (nth (1- col-um) fila))))
        (progn
          ;; respaldo puntual: reabre SOLO esta fila
          (setq fila-rng (vlax-get-property ws 'Range
            (strcat "A" (itoa r) ":P" (itoa r))))
          (setq desc (urb:ppto-cell-text fila-rng 1 col-desc))
          (setq um (strcase (urb:ppto-cell-text fila-rng 1 col-um)))
          (vlax-release-object fila-rng)))
      (cond
        ((and (/= um "") (member um *urb-ppto-unidades-conocidas*)
              (/= desc ""))
          (setq empties 0)
          (setq *urb-ppto-outline*
            (cons (list 5 "" desc um "*") *urb-ppto-outline*))
          (setq vocab
            (cons
              (list "*" um desc (urb:ppto-words desc) r "")
              vocab)))
        ((= desc "") (setq empties (1+ empties))))
      (setq r (1+ r) idx (1+ idx))))
  (setq *urb-ppto-outline* (reverse *urb-ppto-outline*))
  (reverse vocab))

;; 2026-08-19 (pedido del usuario): las hojas por secciones YA NO se atan
;; a UNA red -- una misma hoja puede traer anden + redes sanitarias + mas.
;; Sus actividades entran con capitulo COMODIN "*": el matcher las acepta
;; para CUALQUIER red del plano (misma unidad + texto), y la disciplina la
;; decide el match automatico o la asignacion manual, sin desplegable.
;; El dialogo "elegir elemento/red" se elimino por completo.
(defun urb:ppto-read-vocab-b (wb / candidatas entry ws vocab)
  (setq candidatas (urb:ppto-vocab-candidatas-b wb))
  (if (null candidatas)
    (progn
      (setq *urb-ppto-vocab-hoja* nil)
      (prompt "\nNo se encontro ninguna hoja de presupuesto (ni con NIVEL ni por secciones DESCRIPCION/UM).")
      nil)
    (progn
      ;; varias candidatas formato-B es raro (la mayoria de estos archivos
      ;; son de una sola hoja) -- se usa la primera y se avisa
      (if (> (length candidatas) 1)
        (prompt (strcat "\nOJO: " (itoa (length candidatas))
          " hojas sin NIVEL parecen presupuesto; se usa la primera ("
          (caar candidatas) ").")))
      (setq entry (car candidatas))
      (setq *urb-ppto-vocab-hoja* (car entry))
      ;; formato-B no tiene columnas de subetapa: el puente a la hoja
      ;; (urb:ppto-write-pe) se desactiva solo con header nil
      (setq *urb-ppto-vocab-header* nil)
      (setq ws (urb:ppto-obj
        (vlax-get-property (vlax-get-property wb 'Worksheets) 'Item
          (car entry))))
      (setq vocab
        (urb:ppto-vocab-extraer-b ws (nth 1 (cdr entry))
          (nth 2 (cdr entry)) (nth 0 (cdr entry))))
      (prompt (strcat "\nPresupuesto por secciones (hoja \""
        (car entry) "\", todas las disciplinas): " (itoa (length vocab))
        " actividades leidas."))
      vocab)))

(defun urb:ppto-read-vocab (wb / entry target-name header-row vocab)
  (setq entry (urb:ppto-resolver-hoja wb))
  (if (null entry)
    ;; sin NIVEL en ninguna hoja: intentar el formato por secciones antes
    ;; de rendirse (2026-08-19)
    (urb:ppto-read-vocab-b wb)
    (progn
      (setq target-name (car entry) header-row (cdr entry))
      ;; nombre de la hoja para mostrarlo en los dialogos (trazabilidad
      ;; pedida por el usuario 2026-08-18: que se VEA de donde sale todo)
      (setq *urb-ppto-vocab-hoja* target-name)
      ;; fila del encabezado (v4.71): el puente urb:ppto-write-pe lee la
      ;; fila de CODIGOS de subetapa (header+1) para mapear columnas
      (setq *urb-ppto-vocab-header* header-row)
      (setq vocab
        (urb:ppto-vocab-extraer
          (urb:ppto-obj
            (vlax-get-property (vlax-get-property wb 'Worksheets) 'Item
              target-name))
          header-row))
      (prompt (strcat "\nVocabulario del presupuesto (hoja \"" target-name
        "\"): " (itoa (length vocab)) " actividades leidas."))
      vocab)))

;; ---------- generacion de filas CAD (formato largo) ----------
;; fila cruda: (red concepto id desde hasta etapa subetapa um cantidad handle)
(defun urb:ppto-row (red concepto id desde hasta etapa subetapa um qty handle)
  ;; devuelve UNA fila (lista plana de 10) o nil -- OJO: una envoltura
  ;; doble aqui rompia el match de TODAS las filas (2026-08-17)
  (if (> qty 0.0005)
    (list red concepto id desde hasta
      (urb:safe-string etapa "")
      (if (= (urb:safe-string subetapa "") "") "GEN"
        (urb:safe-string subetapa ""))
      um (atof (rtos qty 2 3)) handle)
    nil))

(defun urb:ppto-rows-vias (/ ss i be d atts nombre etapa sub perfil handle
                           area sobre base-area corte relleno span prof
                           layers layer tipo espesor traslapo scope um qty
                           aused rows out r)
  (setq ss (ssget "_X" '((0 . "INSERT") (-3 ("URB_VIA")))) out nil i 0)
  (if ss
    (repeat (sslength ss)
      (setq be (ssname ss i)
            d (urb:get-xdata-strings be "URB_VIA")
            atts (urb:block-attribute-values (vlax-ename->vla-object be))
            nombre (urb:safe-string (nth 1 d) "VIA")
            etapa (urb:safe-string (nth 2 d) "")
            sub (urb:safe-string (nth 3 d) "")
            perfil (urb:safe-string (nth 4 d) "")
            handle (cdr (assoc 5 (entget be)))
            area (atof (urb:safe-string (nth 17 d) "0"))
            span (atof (urb:safe-string (nth 18 d) "0"))
            sobre (* span
              (+ (atof (urb:safe-string (nth 14 d) "0"))
                 (atof (urb:safe-string (nth 15 d) "0"))))
            corte (atof (urb:safe-string
              (cdr (assoc "VIA_CORTE_M3" atts)) "0"))
            relleno (atof (urb:safe-string
              (cdr (assoc "VIA_RELLENO_M3" atts)) "0")))
      ;; 2026-08-30 CORRECCION SEMANTICA (auditoria con el usuario): el
      ;; CONTORNO dibujado es la CALZADA (sardinel a sardinel, anchos
      ;; medios reales 6.3-7.7 m lo confirman) y el SOBREANCHO de las
      ;; capas granulares es ADICIONAL (1.0 m por lado, estudio
      ;; AUS-10786-10). Antes se asumia al reves (contorno CON
      ;; sobreancho) y el asfalto quedaba subestimado ~30% mientras a
      ;; los granulares les faltaba el sobreancho.
      ;;   base-area = contorno = calzada (asfalto, emulsiones)
      ;;   area      = calzada + sobreancho (descapote, subrasante,
      ;;               granulares, geotextil)
      ;;   corte/relleno se escalan al area total (la excavacion de la
      ;;   banca cubre tambien el sobreancho)
      (setq base-area area)
      (setq area (+ area sobre))
      (if (> base-area 1e-6)
        (setq corte (* corte (/ area base-area))
              relleno (* relleno (/ area base-area))))
      (setq rows
        (list
          (urb:ppto-row "VIA" "Descapote mecanico de material vegetal"
            nombre "" "" etapa sub "M2" area handle)
          (urb:ppto-row "VIA" "Compactacion de subrasante"
            nombre "" "" etapa sub "M2" area handle)
          (urb:ppto-row "VIA" "Excavación en material común (incluye cargue, transporte y disposición final)"
            nombre "" "" etapa sub "M3" corte handle)
          (urb:ppto-row "VIA" "Suministro y colocacion de recebo B-200"
            nombre "" "" etapa sub "M3" relleno handle)
          (urb:ppto-row "VIA" "Emulsion asfaltica CRL-1 imprimacion"
            nombre "" "" etapa sub "M2" base-area handle)
          (urb:ppto-row "VIA" "Emulsion asfaltica CRR-2 riego de liga"
            nombre "" "" etapa sub "M2" base-area handle)))
      ;; capas del perfil de pavimento de ESTA via
      (setq prof
        (vl-some
          '(lambda (p) (if (urb:string-equal-p (car p) perfil) p))
          (urb:road-profiles)))
      (foreach layer (if prof (cadr prof) nil)
        (setq tipo (urb:safe-string (nth 1 layer) "")
              espesor (atof (urb:safe-string (nth 2 layer) "0"))
              traslapo (atof (urb:safe-string (nth 3 layer) "0"))
              scope (if (> (length layer) 4)
                      (urb:safe-string (nth 4 layer) "") "")
              aused (if (urb:string-equal-p scope "Base") base-area area))
        (cond
          ((urb:string-equal-p tipo "Volumen")
            (setq um "M3" qty (* aused espesor)))
          ((urb:string-equal-p tipo "Geotextil")
            (setq um "M2" qty (* area (+ 1.0 (/ traslapo 100.0)))))
          (T (setq um "" qty 0.0)))
        (if (/= um "")
          (setq rows
            (cons
              (urb:ppto-row "VIA" (nth 0 layer)
                nombre "" "" etapa sub um qty handle)
              rows))))
      ;; actividades parametricas del tipo VIA (magnitud x factor)
      (setq rows
        (append rows
          (urb:ppto-param-rows "VIA" "VIA"
            (list (cons "AREA" area)
              (cons "AREA_SIN_SOBREANCHO" base-area)
              (cons "LONGITUD" span)
              (cons "CORTE" corte)
              (cons "RELLENO" relleno)
              (cons "UNIDAD" 1.0))
            nombre "" "" etapa sub handle)))
      (setq rows (urb:ppto-rows+zona rows (urb:ppto-zona-de be)))
      (foreach r rows (if r (setq out (cons r out))))
      (setq i (1+ i))))
  out)

;; area de los anillos de prefabricado INTERNOS vinculados a este anden
;; (xdata URB_PREFAB_ANILLO = handle-del-anden + posicion): su franja
;; ancho x longitud se descuenta del area del anden -- el prefabricado
;; ya cuenta su propio ML al presupuesto.
;; 2026-08-27: re-apunta los anillos de prefabricado del handle viejo al
;; nuevo cuando un anden se re-empaqueta (EDITAR). Sin esto el vinculo
;; URB_PREFAB_ANILLO quedaba muerto y el descuento de area se perdia en
;; silencio (caso real encontrado en el master). Devuelve cuantos re-vinculo.
(defun urb:relink-anden-anillos (old-h new-h / ss i ce d n r)
  (setq n 0)
  (if (and old-h new-h (/= old-h "") (/= new-h "") (/= old-h new-h)
           (tblsearch "APPID" "URB_PREFAB_ANILLO")
           (setq ss (ssget "_X"
             '((0 . "INSERT") (-3 ("URB_PREFAB_ANILLO"))))))
    (progn
      (setq i 0)
      (repeat (sslength ss)
        (setq ce (ssname ss i))
        (setq d (urb:get-xdata-strings ce "URB_PREFAB_ANILLO"))
        (if (and d (= (urb:safe-string (car d) "") old-h))
          (progn
            (setq r
              (vl-catch-all-apply
                '(lambda ()
                  (urb:set-xdata-strings ce "URB_PREFAB_ANILLO"
                    (list new-h (urb:safe-string (cadr d) "Interno"))))))
            (if (not (vl-catch-all-error-p r)) (setq n (1+ n)))))
        (setq i (1+ i)))))
  n)

(defun urb:anden-area-anillos (be / h ss i ce d total dest-h dest bb lo hi
                               p relinked)
  (setq total 0.0
        h (cdr (assoc 5 (entget be))))
  (if (and (tblsearch "APPID" "URB_PREFAB_ANILLO")
           (setq ss (ssget "_X"
             '((0 . "INSERT") (-3 ("URB_PREFAB_ANILLO"))))))
    (progn
      ;; bounding box del anden, para adoptar anillos HUERFANOS (ver abajo)
      (setq bb
        (vl-catch-all-apply
          '(lambda ( / mn mx)
            (vla-GetBoundingBox (vlax-ename->vla-object be) 'mn 'mx)
            (list (vlax-safearray->list mn) (vlax-safearray->list mx)))))
      (if (vl-catch-all-error-p bb) (setq bb nil))
      (setq lo (car bb) hi (cadr bb))
      (setq i 0)
      (repeat (sslength ss)
        (setq ce (ssname ss i))
        (setq d (urb:get-xdata-strings ce "URB_PREFAB_ANILLO"))
        (setq dest-h (urb:safe-string (car d) ""))
        (cond
          ((and d (= dest-h h)
                (urb:string-equal-p
                  (urb:safe-string (cadr d) "") "Interno"))
            (setq total
              (+ total
                 (atof (urb:safe-string
                   (cdr (assoc "AREA_M2" (mp:att-alist ce))) "0")))))
          ;; 2026-08-27 (caso real del master: anillo con handle destino
          ;; MUERTO -- el anden fue editado/re-empaquetado con handle
          ;; nuevo y el descuento se perdia en silencio): si el destino
          ;; ya no existe y el anillo cae dentro de la caja de ESTE
          ;; anden, se ADOPTA -- se reescribe el vinculo al handle vivo
          ;; y se descuenta normal. Auto-reparacion en el siguiente
          ;; export, sin comando nuevo.
          ((and d bb
                (urb:string-equal-p
                  (urb:safe-string (cadr d) "") "Interno")
                (or (= dest-h "")
                    (null (setq dest
                      (vl-catch-all-apply 'handent (list dest-h))))
                    (vl-catch-all-error-p dest)
                    (null (entget dest)))
                ;; el bloque prefab se inserta en (0,0,0) con geometria
                ;; en coordenadas mundo -- la posicion real del anillo
                ;; es el CENTRO de su propio bounding box, no el assoc 10
                (setq p
                  (vl-catch-all-apply
                    '(lambda ( / mn mx)
                      (vla-GetBoundingBox
                        (vlax-ename->vla-object ce) 'mn 'mx)
                      (setq mn (vlax-safearray->list mn)
                            mx (vlax-safearray->list mx))
                      (list (/ (+ (car mn) (car mx)) 2.0)
                            (/ (+ (cadr mn) (cadr mx)) 2.0)))))
                (not (vl-catch-all-error-p p))
                (>= (car p) (car lo)) (<= (car p) (car hi))
                (>= (cadr p) (cadr lo)) (<= (cadr p) (cadr hi)))
            (setq relinked
              (vl-catch-all-apply
                '(lambda ()
                  (urb:set-xdata-strings ce "URB_PREFAB_ANILLO"
                    (list h (urb:safe-string (cadr d) "Interno"))))))
            (if (not (vl-catch-all-error-p relinked))
              (progn
                (prompt (strcat "\nAnillo de prefabricado huerfano "
                  "re-vinculado al anden " h " (descuento recuperado)."))
                (setq total
                  (+ total
                     (atof (urb:safe-string
                       (cdr (assoc "AREA_M2" (mp:att-alist ce))) "0"))))))))
        (setq i (1+ i)))))
  total)

;; area total de contenedores de raices cuyo punto de insercion cae
;; dentro de la caja del anden (2026-08-21, pedido del usuario: el
;; contenedor CORTA el anden tambien en CANTIDADES, no solo visualmente).
;; La pertenencia se decide por bounding box del bloque del anden --
;; suficiente para franjas de anden; si dos andenes se traslapan, el
;; contenedor solo descuenta en el primero que lo contiene.
(defun urb:anden-area-contenedores (be usados / ss j ce nom atts tipo entry
                                    minpt maxpt lo hi p poly total)
  (setq total 0.0)
  (setq poly (urb:anden-boundary-samples be))
  (setq ss (ssget "_X" '((0 . "INSERT") (2 . "URB_MOB_CONT*"))))
  (if ss
    (progn
      (vl-catch-all-apply
        '(lambda ()
          (vla-GetBoundingBox (vlax-ename->vla-object be)
            'minpt 'maxpt)))
      (if (and minpt maxpt)
        (progn
          (setq lo (vlax-safearray->list minpt)
                hi (vlax-safearray->list maxpt))
          (setq j 0)
          (repeat (sslength ss)
            (setq ce (ssname ss j))
            (setq p (cdr (assoc 10 (entget ce))))
            (if (and p
                     (not (member ce (eval usados)))
                     (>= (car p) (car lo)) (<= (car p) (car hi))
                     (>= (cadr p) (cadr lo)) (<= (cadr p) (cadr hi))
                     ;; Si el usuario dibujo un entrante alrededor del
                     ;; contenedor, su centro ya esta FUERA del poligono y
                     ;; no se vuelve a descontar por segunda vez.
                     (or (null poly)
                         (urb:point-in-poly-2d
                           (list (car p) (cadr p)) poly)))
              (progn
                (setq atts (urb:block-attribute-values ce))
                (setq tipo (urb:safe-string (cdr (assoc "TIPO" atts)) ""))
                (setq entry (assoc tipo *urb-mob-tipos*))
                (if entry
                  (progn
                    (setq total
                      (+ total (* (nth 4 entry) (nth 5 entry))))
                    (set usados (cons ce (eval usados)))))))
            (setq j (1+ j)))))))
  total)

;; 2026-09-02 (pedido del usuario: "no quiero que el bordillo quede
;; sobrepuesto sobre el anden... son independientes"): si un prefabricado
;; INDEPENDIENTE (bordillo/sardinel de via, sin vinculo de anillo) corre
;; POR DENTRO del contorno del anden, su franja se DESCUENTA del area del
;; anden en el export (el prefab ya cobra su propio ML) -- sin doble
;; conteo aunque el usuario haya dibujado el anden hasta el borde de la
;; via pisando el bordillo. Muestreo de la arista del prefab (0.25 m)
;; contra el poligono del anden.
(defun urb:anden-boundary-samples (be / obj bname blk item role best bestlen len)
  (setq obj (vlax-ename->vla-object be)
        bname (vla-get-EffectiveName obj))
  (setq blk (vl-catch-all-apply 'vla-Item
    (list (vla-get-Blocks (urb:doc)) bname)))
  (if (vl-catch-all-error-p blk)
    nil
    (progn
      ;; contorno: la polilinea CERRADA mas larga del def (la boundary);
      ;; los roles xdata no siempre sobreviven, la longitud si.
      (setq best nil bestlen 0.0)
      (vlax-for item blk
        (if (and (member (vla-get-ObjectName item)
                   '("AcDbPolyline" "AcDb2dPolyline"))
                 (= (vla-get-Closed item) :vlax-true))
          (progn
            (setq len (vl-catch-all-apply 'vla-get-Length (list item)))
            (if (and (not (vl-catch-all-error-p len)) (> len bestlen))
              (setq bestlen len best item)))))
      (if best
        (urb:curve-sample-points (vlax-vla-object->ename best) 0.50)
        nil))))

(defun urb:anden-area-prefabs-solapados (be poly / ss i ce d obj bname blk
   item ref len d2 pt nin ntot frac width total bb1 bb2 abx res lo hi)
  (setq total 0.0)
  (if (null poly)
    0.0
    (progn
      (setq lo (list (apply 'min (mapcar 'car poly))
                     (apply 'min (mapcar 'cadr poly)))
            hi (list (apply 'max (mapcar 'car poly))
                     (apply 'max (mapcar 'cadr poly))))
      (setq ss (ssget "_X" '((0 . "INSERT") (-3 ("URB_PREFAB_BLOCK")))) i 0)
      (if ss
        (while (< i (sslength ss))
          (setq ce (ssname ss i))
          ;; los anillos vinculados ya descuentan por su propio camino
          (if (null (urb:get-xdata-strings ce "URB_PREFAB_ANILLO"))
            (progn
              ;; prefiltro bbox
              (setq res (vl-catch-all-apply 'vla-GetBoundingBox
                (list (vlax-ename->vla-object ce) 'bb1 'bb2)))
              (if (and (not (vl-catch-all-error-p res))
                       (progn
                         (setq bb1 (vlax-safearray->list bb1)
                               bb2 (vlax-safearray->list bb2))
                         (and (< (car bb1) (car hi)) (> (car bb2) (car lo))
                              (< (cadr bb1) (cadr hi)) (> (cadr bb2) (cadr lo)))))
                (progn
                  (setq d (urb:prefab-data ce)
                        width (atof (urb:safe-string (nth 3 d) "0.20")))
                  ;; arista de referencia: polilinea mas larga DEL DEF del
                  ;; prefab (sin explotar nada)
                  (setq obj (vlax-ename->vla-object ce)
                        bname (vla-get-EffectiveName obj))
                  (setq blk (vl-catch-all-apply 'vla-Item
                    (list (vla-get-Blocks (urb:doc)) bname)))
                  (setq ref nil len 0.0)
                  (if (not (vl-catch-all-error-p blk))
                    (vlax-for item blk
                      (if (member (vla-get-ObjectName item)
                            '("AcDbPolyline" "AcDb2dPolyline"))
                        (progn
                          (setq d2 (vl-catch-all-apply 'vla-get-Length
                            (list item)))
                          (if (and (not (vl-catch-all-error-p d2))
                                   (> d2 len))
                            (setq len d2 ref item))))))
                  (if (and ref (> len 0.1))
                    (progn
                      (setq nin 0 ntot 0 d2 0.0)
                      (setq abx (vlax-vla-object->ename ref))
                      (while (<= d2 len)
                        (setq pt (vl-catch-all-apply
                          'vlax-curve-getPointAtDist (list abx d2)))
                        (if (not (vl-catch-all-error-p pt))
                          (progn
                            (setq ntot (1+ ntot))
                            (if (urb:point-in-poly-2d
                                  (list (car pt) (cadr pt)) poly)
                              (setq nin (1+ nin)))))
                        (setq d2 (+ d2 0.25)))
                      (if (and (> ntot 0) (> nin 0))
                        (progn
                          (setq frac (/ (float nin) ntot))
                          (setq total
                            (+ total (* frac len width)))))))))))
          (setq i (1+ i))))
      total)))

(defun urb:ppto-rows-andenes (/ ss i be d atts area material etapa sub handle
                              corte relleno loseta-und adoq-und rows out r
                              cont-usados area-cont poly area-neta-p over-area mt-estado mt-mov)
  (setq ss (ssget "_X" '((0 . "INSERT") (-3 ("URB_ANDEN_BLOCK")))) out nil i 0)
  (setq cont-usados nil)
  (if ss
    (repeat (sslength ss)
      (setq be (ssname ss i)
            d (urb:get-xdata-strings be "URB_ANDEN_BLOCK")
            atts (urb:block-attribute-values (vlax-ename->vla-object be))
            area (atof (urb:safe-string (cdr (assoc "AREA_M2" atts)) "0"))
            material (strcase (urb:safe-string (nth 1 d) ""))
            etapa (urb:safe-string (nth 2 d) "")
            sub (urb:safe-string (nth 3 d) "")
            handle (cdr (assoc 5 (entget be)))
            corte (atof (urb:safe-string
              (cdr (assoc "ANDEN_CORTE_M3" atts)) "0"))
            relleno (atof (urb:safe-string
              (cdr (assoc "ANDEN_RELLENO_M3" atts)) "0")))
      ;; 2026-09-08: los andenes creados desde v4.77.1 guardan el AREA_M2
      ;; ya NETA (el contorno menos prefabricados y contenedores, medido
      ;; sobre la region real) y lo marcan con AREA_NETA=Si. En esos NO
      ;; se vuelve a descontar; los bloques anteriores conservan el
      ;; camino de siempre.
      (setq area-neta-p
        (urb:yes-p (urb:safe-string (cdr (assoc "AREA_NETA" atts)) "No")))
      ;; CORTE por contenedores de raices: su area (dimensiones reales
      ;; del catalogo) se DESCUENTA del area del anden y de todo lo
      ;; derivado de ella (descapote, subbase, geotextil, arena, M.O.,
      ;; parametricas por AREA...). OJO limites documentados: los
      ;; CONTEOS de piezas guardados al crear el anden (losetas lisas,
      ;; adoquines) y las franjas toperol/guia en ML no se recalculan --
      ;; si el contenedor se agrega despues de crear el anden, re-EDITE
      ;; el anden para regenerar esos conteos sobre la geometria real.
      (if (not area-neta-p)
        (progn
      (setq area-cont (urb:anden-area-contenedores be 'cont-usados))
      (if (> area-cont 0.0)
        (setq area (max 0.0 (- area area-cont))))
      ;; v4.50: los anillos de prefabricado INTERNOS tambien descuentan
      ;; su franja del area del anden (el prefab ya cuenta su propio ML)
      (setq area-cont (urb:anden-area-anillos be))
      (if (> area-cont 0.0)
        (setq area (max 0.0 (- area area-cont))))
      ;; 2026-09-02: prefabricados INDEPENDIENTES (bordillo de via) que
      ;; corren por dentro del contorno tambien descuentan su franja
      (setq poly (urb:anden-boundary-samples be))
      (setq area-cont (urb:anden-area-prefabs-solapados be poly))
      (if (> area-cont 0.0)
        (setq area (max 0.0 (- area area-cont))))))
      (setq over-area (urb:parse-real (urb:safe-string
        (cdr (assoc "AREA_CON_SOBREANCHO_M2" atts)) "")))
      ;; Bloques viejos conservan su valor anterior hasta regeneracion.
      (if (not over-area) (setq over-area area))
      ;; No sustituir un MT pendiente por area x espesor: no es un corte
      ;; contra SUP_TN. Se conserva como pendiente, nunca como volumen medido.
      ;; 5.7.13 (reporte del usuario: "no me esta conectando las
      ;; excavaciones de andenes"). La migracion de v4.23 que depuro la
      ;; paleta Properties RETIRO el atributo ANDEN_METODO de los andenes;
      ;; sin atributo este chequeo caia al valor por defecto "PENDIENTE" y
      ;; TODOS los andenes exportaban corte/relleno en 0 aunque tuvieran su
      ;; MT calculado (medido en el maestro: 28 andenes, todos con
      ;; URB_ANDEN_MOV = "OK ..."). El estado se toma ahora del atributo si
      ;; existe y, si no, de la XDATA URB_ANDEN_MOV (nth 1 = estado).
      ;; 5.7.20 (reporte del usuario 2026-09-22: "Exportacion detenida en
      ;; andenes: bad argument type: consp nil"): un anden recien dibujado
      ;; no tiene XDATA URB_ANDEN_MOV y (nth 1 nil) abortaba TODA la
      ;; exportacion (backtrace: NTH 1 nil en esta funcion). Sin XDATA el
      ;; anden queda PENDIENTE como cualquier MT sin calcular.
      (setq mt-estado (urb:safe-string (cdr (assoc "ANDEN_METODO" atts)) ""))
      (if (= mt-estado "")
        (setq mt-estado
          (urb:safe-string
            (if (listp (setq mt-mov (urb:get-xdata-strings be "URB_ANDEN_MOV")))
              (cadr mt-mov))
            "PENDIENTE")))
      (if (wcmatch (strcase mt-estado) "PENDIENTE*")
        (progn
          (setq corte 0.0 relleno 0.0)
          (prompt (strcat "\nMT pendiente en anden " handle ": corte/relleno no exportados."))))
      (setq rows
        (list
          (urb:ppto-row "ANDEN" "Descapote mecanico de material vegetal"
            "" "" "" etapa sub "M2" over-area handle)
          (urb:ppto-row "ANDEN" "Compactacion de subrasante"
            "" "" "" etapa sub "M2" over-area handle)
          (urb:ppto-row "ANDEN" "Excavación en material común (incluye cargue, transporte y disposición final)"
            "" "" "" etapa sub "M3" corte handle)
          (urb:ppto-row "ANDEN" "Suministro y colocacion de recebo B-200"
            "" "" "" etapa sub "M3" relleno handle)
          (urb:ppto-row "ANDEN" "Subbase granular SBG"
            "" "" "" etapa sub "M3" (* over-area 0.50) handle)
          (urb:ppto-row "ANDEN" "Geotextil tejido 2100"
            "" "" "" etapa sub "M2" (* over-area 1.15) handle)
          (urb:ppto-row "ANDEN" "Arena de nivelacion"
            "" "" "" etapa sub "M3" (* over-area 0.04) handle)
          (urb:ppto-row "ANDEN" "M.O. localizacion y replanteo"
            "" "" "" etapa sub "M2" area handle)
          (urb:ppto-row "ANDEN" "M.O. nivelacion con arena"
            "" "" "" etapa sub "M2" area handle)
          (urb:ppto-row "ANDEN" "M.O. instalacion de adoquin y tabletas"
            "" "" "" etapa sub "M2" area handle)))
      ;; acabados: PRIMERO los conteos reales guardados al crear el anden
      ;; (permiten andenes mixtos adoquin+loseta); factores de area solo
      ;; como respaldo de bloques viejos sin esos atributos
      (setq loseta-und (atof (urb:safe-string
        (cdr (assoc "LOSETA_LISA_UND" atts)) "0")))
      (setq adoq-und (atof (urb:safe-string
        (cdr (assoc "ADOQUIN_20X10_UND" atts)) "0")))
      (cond
        ((> loseta-und 0.0)
          (setq rows
            (cons (urb:ppto-row "ANDEN" "Loseta lisa 20x20x6"
              "" "" "" etapa sub "UN" loseta-und handle) rows)))
        ((wcmatch material "*LOSETA*")
          (setq rows
            (cons (urb:ppto-row "ANDEN" "Loseta lisa 20x20x6"
              "" "" "" etapa sub "UN" (* area 25.0) handle) rows))))
      (cond
        ((> adoq-und 0.0)
          (setq rows
            (cons (urb:ppto-row "ANDEN" "Adoquin gris 10x20x6"
              "" "" "" etapa sub "UN" adoq-und handle) rows)))
        ((wcmatch material "*ADOQUIN*")
          (setq rows
            (cons (urb:ppto-row "ANDEN" "Adoquin gris 10x20x6"
              "" "" "" etapa sub "UN" (* area 50.0) handle) rows))))
      (setq rows
        (append rows
          (urb:ppto-param-rows "ANDEN" "ANDEN"
            (list (cons "AREA" over-area)
              (cons "AREA_SIN_SOBREANCHO" area)
              (cons "AREA_CON_SOBREANCHO" over-area)
              (cons "TOPEROL_ML"
                (atof (urb:safe-string
                  (cdr (assoc "LOSETA_TOPEROL_ML" atts)) "0")))
              (cons "GUIA_ML"
                (atof (urb:safe-string
                  (cdr (assoc "LOSETA_GUIA_ML" atts)) "0")))
              ;; unidades de pieza (v4.42): del atributo si existe;
              ;; respaldo = ml de franja / 0.20 (bloques viejos)
              (cons "TOPEROL_UND"
                (if (cdr (assoc "LOSETA_TOPEROL_UND" atts))
                  (atof (urb:safe-string
                    (cdr (assoc "LOSETA_TOPEROL_UND" atts)) "0"))
                  (/ (atof (urb:safe-string
                    (cdr (assoc "LOSETA_TOPEROL_ML" atts)) "0")) 0.20)))
              (cons "GUIA_UND"
                (if (cdr (assoc "LOSETA_GUIA_UND" atts))
                  (atof (urb:safe-string
                    (cdr (assoc "LOSETA_GUIA_UND" atts)) "0"))
                  (/ (atof (urb:safe-string
                    (cdr (assoc "LOSETA_GUIA_ML" atts)) "0")) 0.20)))
              (cons "PERIMETRO"
                (atof (urb:safe-string
                  (cdr (assoc "PERIMETRO_M" atts)) "0")))
              (cons "LOSETA_LISA_M2"
                (atof (urb:safe-string
                  (cdr (assoc "LOSETA_LISA_M2" atts)) "0")))
              (cons "LOSETA_LISA_UND" loseta-und)
              (cons "ADOQUIN_M2"
                (atof (urb:safe-string
                  (cdr (assoc "ADOQUIN_20X10_M2" atts)) "0")))
              (cons "ADOQUIN_UND" adoq-und)
              (cons "UNIDAD" 1.0))
            "" "" "" etapa sub handle)))
      (setq rows (urb:ppto-rows+zona rows (urb:ppto-zona-de be)))
      (foreach r rows (if r (setq out (cons r out))))
      (setq i (1+ i))))
  out)

;; MOBILIARIO (v4.45): agrupa los bloques URB_MOB_* por tipo+etapa+sub y
;; emite UNA fila UN por grupo con el conteo; el concepto es el texto
;; exacto de la actividad del catalogo (match directo por igualdad)
(defun urb:ppto-rows-mobiliario (/ ss i be atts tipo etapa sub zona key
                                 grupos g entry fila out handle)
  (setq ss (ssget "_X" '((0 . "INSERT") (2 . "URB_MOB_*"))))
  (setq grupos nil out nil i 0)
  (if ss
    (repeat (sslength ss)
      (setq be (ssname ss i))
      (setq atts (urb:block-attribute-values be))
      (setq tipo (urb:safe-string (cdr (assoc "TIPO" atts)) ""))
      (setq etapa (urb:safe-string (cdr (assoc "ETAPA" atts)) ""))
      (setq sub (urb:safe-string (cdr (assoc "SUBETAPA" atts)) ""))
      (setq zona (urb:ppto-zona-de be))
      (setq handle (urb:safe-string (cdr (assoc 5 (entget be))) ""))
      ;; la ZONA separa el grupo: los arboles del parque suman al parque
      (setq key (strcat tipo "|" etapa "|" sub "|" zona))
      (setq g (assoc key grupos))
      (if g
        (setq grupos
          (subst
            (list key tipo etapa sub (1+ (nth 4 g)) (nth 5 g) zona)
            g grupos))
        (setq grupos (cons (list key tipo etapa sub 1 handle zona) grupos)))
      (setq i (1+ i))))
  (foreach g (reverse grupos)
    (setq entry (assoc (nth 1 g) *urb-mob-tipos*))
    (if entry
      (progn
        ;; red del tipo: campo 7 opcional del catalogo (default ANDEN;
        ;; p.ej. el bolardo pertenece a los capitulos de rampa)
        (setq fila
          (urb:ppto-row
            (if (nth 6 entry) (nth 6 entry) "ANDEN")
            (nth 2 entry)
            "" "" "" (nth 2 g) (nth 3 g) "UN"
            (float (nth 4 g)) (nth 5 g)))
        (if fila
          (progn
            (if (/= (urb:safe-string (nth 6 g) "") "")
              (setq fila (append fila (list (nth 6 g)))))
            (setq out (cons fila out)))))))
  (reverse out))

(defun urb:ppto-rows-prefabs (/ ss i be atts data tipo lng etapa sub handle red
                              destino conceptos rows out r)
  (setq ss (ssget "_X" '((0 . "INSERT") (-3 ("URB_PREFAB_BLOCK")))) out nil i 0)
  (if ss
    (repeat (sslength ss)
      (setq be (ssname ss i)
            atts (urb:block-attribute-values (vlax-ename->vla-object be))
            data (urb:prefab-data be)
            tipo (strcase (urb:safe-string (cdr (assoc "TIPO" atts)) ""))
            lng (atof (urb:safe-string (cdr (assoc "LONGITUD_M" atts)) "0"))
            etapa (urb:safe-string (cdr (assoc "ETAPA" atts)) "")
            sub (urb:safe-string (cdr (assoc "SUBETAPA" atts)) "")
            handle (cdr (assoc 5 (entget be)))
            destino (urb:safe-string
              (cdr (assoc "DESTINO_PPTO" atts))
              (urb:safe-string (nth 7 data)
                (urb:prefab-destino-default tipo)))
            red (urb:prefab-destino-red destino tipo)
            conceptos (urb:prefab-conceptos tipo))
      (setq rows
        (if (= (urb:safe-string (nth 3 conceptos) "") "PIEZA")
          ;; 2026-09-11: piezas sueltas (remate A-105 de las aletas del
          ;; acceso vehicular): UNA unidad por pieza, no por metro, y sin
          ;; fila de ML -- asi lo cuenta el libro (2.2.4.2.1 / 2.2.4.3.7)
          (list
            (urb:ppto-row red (nth 0 conceptos)
              "" "" "" etapa sub "UN" 1.0 handle)
            (urb:ppto-row red (nth 1 conceptos)
              "" "" "" etapa sub "UN" 1.0 handle))
          ;; 2026-09-11: el largo de la pieza depende del tipo (A-80 de
          ;; 0,80; sardineles de rampa de 1,00), no siempre 0,80.
          (list
            (urb:ppto-row red
              (nth 0 conceptos)
              "" "" "" etapa sub "UN"
              (float (fix (+ 0.999999 (/ lng (urb:prefab-largo tipo))))) handle)
            (urb:ppto-row red
              (nth 1 conceptos)
              "" "" "" etapa sub "ML" lng handle))))
      (setq rows
        (append rows
          (urb:ppto-param-rows
            (nth 2 conceptos) red
            (list (cons "LONGITUD" lng) (cons "UNIDAD" 1.0))
            "" "" "" etapa sub handle)))
      (setq rows (urb:ppto-rows+zona rows (urb:ppto-zona-de be)))
      (foreach r rows (if r (setq out (cons r out))))
      (setq i (1+ i))))
  out)


;; 2026-09-11 (pedido del usuario: "define lo referente a los materiales y
;; longitudes ... asi mismo quiero que eso lo conectes al presupuesto, pasa
;; lo mismo con el paso peatonal y la rampa peatonal").
;;
;; Cada modulo sale con el TEXTO EXACTO de SU capitulo, y solo con las
;; actividades que ESE capitulo tiene -- se leyeron los tres del libro:
;;
;;   2.2.4 RAMPA VEHICULAR: subrasante, los 4 suministros de sardinel/remate
;;     (A-105, A-86, A-85, A-100), excavacion, recebo B-200, geotextil, SBG,
;;     M.O. de adoquin y tabletas / bordillo / sardinel / loseta guia y
;;     toperol, y el bolardo M-63. NO tiene suministro de adoquin, losetas,
;;     arena ni A-80: esos materiales los compra el capitulo de ANDENES
;;     (2.2.1), que es donde caen.
;;   2.2.5 RAMPA PEATONAL: lo tiene todo en su propio capitulo.
;;   2.2.6 PASO PEATONAL SEGURO: tiene adoquin, A-80, transporte, arena,
;;     excavacion, recebo (sin "B-200" en el nombre), SBG, geotextil y sus
;;     M.O.; NO tiene losetas ni M.O. de loseta guia y toperol -> esas van a
;;     ANDENES, y el remate de rampa fundido en sitio va a 2.2.5, el unico
;;     capitulo que lo tiene.
;;
;; Los bordillos y sardineles del acceso vehicular son PREFABRICADOS
;; (urb:ppto-rows-prefabs los cobra con su suministro y su M.O. en el
;; capitulo de la rampa), asi que aqui no se repiten.
;;
;; Acceso vehicular en SUPERPOSICION sobre un anden: el anden ya cobra su
;; subrasante, su excavacion, sus granulares y su pavimento, asi que el
;; modulo solo aporta los prefabricados, los bolardos y su tableta de
;; alerta. Con pavimento propio aporta todo.
(defun urb:ppto-rows-rampas (/ ss i be atts data mov tipo red etapa sub handle
                             area corte relleno sbg arena geo adoq-und adoq-m2
                             loseta-und loseta-m2 top-ml top-und guia-ml
                             guia-und bor-ml a80 a81 a105 bolardos a85 a86 propio
                             kg-prefab base rows out r)
  (setq ss (ssget "_X" '((0 . "INSERT") (-3 ("URB_RAMPA_BLOCK")))) out nil i 0)
  (if ss
    (repeat (sslength ss)
      (setq be (ssname ss i)
            atts (urb:block-attribute-values (vlax-ename->vla-object be))
            data (urb:get-xdata-strings be "URB_RAMPA_BLOCK")
            mov (urb:get-xdata-strings be "URB_RAMPA_MOV")
            tipo (urb:safe-string (cdr (assoc "TIPO" atts))
              (urb:safe-string (nth 0 data) "RAMPA-PEATONAL"))
            red (urb:rampa-red tipo)
            etapa (urb:safe-string (cdr (assoc "ETAPA" atts)) "")
            sub (urb:safe-string (cdr (assoc "SUBETAPA" atts)) "")
            handle (cdr (assoc 5 (entget be))))
      (defun urb:ra-num (clave defecto)
        (atof (urb:safe-string (cdr (assoc clave atts)) defecto)))
      (setq area (urb:ra-num "AREA_M2" "0")
            adoq-m2 (urb:ra-num "ADOQUIN_M2" "0")
            loseta-m2 (urb:ra-num "LOSETA_LISA_M2" "0")
            adoq-und (urb:ra-num "ADOQUIN_20X10_UND" "0")
            loseta-und (urb:ra-num "LOSETA_LISA_UND" "0")
            top-ml (urb:ra-num "TOPEROL_ML" "0")
            top-und (urb:ra-num "LOSETA_TOPEROL_UND" (rtos (/ top-ml 0.20) 2 6))
            guia-ml (urb:ra-num "LOSETA_GUIA_ML" "0")
            guia-und (urb:ra-num "LOSETA_GUIA_UND" (rtos (/ guia-ml 0.20) 2 6))
            bor-ml (urb:ra-num "BORDILLO_ML" "0")
            a80 (/ bor-ml 0.80)
            a85 (urb:ra-num "SARDINEL_A85_ML" "0")
            a86 (urb:ra-num "SARDINEL_A86_ML" "0")
            a105 (urb:ra-num "A105_UND" "0")
            a81 (urb:ra-num "A81_UND" "0")
            bolardos (urb:ra-num "BOLARDO_UND" "0"))
      ;; el acceso vehicular sin anden debajo trae su propio pavimento
      (setq propio (or (/= tipo "RAMPA-VEHICULAR")
                       (> (+ loseta-m2 adoq-m2) 0.0)))
      (setq base (if propio area 0.0))
      (setq corte (if (and mov (car mov)) (atof (car mov)) (* base *urb-anden-depth*))
            relleno (if (and mov (cadr mov)) (atof (cadr mov)) 0.0)
            sbg (urb:ra-num "SBG_M3" (rtos (* base 0.50) 2 6))
            arena (urb:ra-num "ARENA_M3" (rtos (* base 0.04) 2 6))
            geo (urb:ra-num "GEOTEXTIL_M2" (rtos (* base 1.15) 2 6)))
      (if (not propio) (setq corte 0.0 relleno 0.0 sbg 0.0 arena 0.0 geo 0.0))
      ;; KG de transporte de prefabricados: pesos de catalogo por pieza
      (setq kg-prefab
        (+ (* adoq-und (urb:prefab-peso "ADOQUIN"))
           (* (+ loseta-und top-und guia-und) (urb:prefab-peso "LOSETA"))
           (* a80 (urb:prefab-peso "A-80"))
           (if (= tipo "RAMPA-PEATONAL")
             (+ (* (fix (+ 0.999999 (/ a85 (urb:prefab-largo "Sardinel A-85")))) (urb:prefab-peso "A-85"))
                (* (fix (+ 0.999999 (/ a86 (urb:prefab-largo "Sardinel A-86")))) (urb:prefab-peso "A-86")))
             0.0)))
      (defun rr (r c um q) (urb:ppto-row r c "" "" "" etapa sub um q handle))
      ;; ---------- lo que comparten los tres capitulos ----------
      (setq rows
        (list
          (rr red "Compactacion de subrasante (Incluye nivelacion)" "M2" base)
          (rr red
            "Descapote mecanico de material vegetal (Incluye cargue y retiro externo)"
            "M2" base)
          (rr red
            "Excavacion mecanica en material comun (Incluye cargue, transporte y disposicion externa)"
            "M3" corte)
          (rr red "Subbase granular SBG" "M3" sbg)
          (rr red "Geotextil tejido 2100" "M2" geo)
          (rr red "M.O. instalacion de adoquin y tabletas" "M2" base)))
      ;; ---------- lo propio de cada capitulo ----------
      (cond
        ;; ===== 2.2.4 RAMPA VEHICULAR =====
        ((= tipo "RAMPA-VEHICULAR")
          (setq rows
            (append rows
              (list
                (rr red "Suministro y colocacion de recebo B-200" "M3" relleno)
                ;; la M.O. de bordillo y de sardinel las cobra el
                ;; prefabricado con su propia fila; aqui solo la tactil
                (rr red "M.O. instalacion de loseta guia y toperol" "ML"
                  (+ guia-ml top-ml))
                (rr red
                  "Suministro e instalacion de bolardo alto en hierro Tipo M-63"
                  "UN" bolardos)
                ;; 2.2.4 no compra materiales de pavimento: van a ANDENES
                (rr "ANDEN" "Adoquin gris 10x20x6" "UN" adoq-und)
                (rr "ANDEN" "Loseta lisa 20x20x6" "UN" loseta-und)
                (rr "ANDEN" "Loseta toperol 20x20x6" "UN" top-und)
                (rr "ANDEN" "Loseta guia 20x20x6" "UN" guia-und)
                (rr "ANDEN" "Arena de nivelacion" "M3" arena)
                (rr "ANDEN" "Transporte de prefabricados" "KG" kg-prefab)
                (rr "ANDEN" "M.O. localizacion y replanteo" "M2" base)
                (rr "ANDEN" "M.O. nivelacion con arena" "M2" base)))))
        ;; ===== 2.2.6 PASO PEATONAL SEGURO =====
        ((= tipo "PASO-PEATONAL")
          (setq rows
            (append rows
              (list
                (rr red "Suministro y colocacion de recebo B-200" "M3" relleno)
                (rr red "Adoquin gris 10x20x6" "UN" adoq-und)
                (rr red "Bordillo prefabricado A-80" "UN" a80)
                (rr red "Arena de nivelacion" "M3" arena)
                (rr red "Transporte de prefabricados" "KG" kg-prefab)
                (rr red "M.O. localizacion y replanteo" "M2" base)
                (rr red "M.O. nivelacion con arena" "M2" base)
                (rr red "M.O. instalacion de bordillo prefabricado" "ML" bor-ml)
                ;; 2.2.6 no tiene losetas ni su M.O.: van a ANDENES
                (rr "ANDEN" "Loseta lisa 20x20x6" "UN" loseta-und)
                (rr "ANDEN" "Loseta toperol 20x20x6" "UN" top-und)
                (rr "ANDEN" "Loseta guia 20x20x6" "UN" guia-und)
                (rr "ANDEN" "M.O. instalacion de loseta guia y toperol" "ML"
                  (+ guia-ml top-ml))
                ;; el remate de rampa fundido en sitio solo existe en 2.2.5
                (rr "RAMPA-PEATONAL"
                  "Suministro y construccion de remate de rampa en concreto fundido en sitio"
                  "M2" (* a81 0.39))))))
        ;; ===== 2.2.5 RAMPA PEATONAL =====
        (T
          (setq rows
            (append rows
              (list
                (rr red "Suministro y colocacion de recebo B-200" "M3" relleno)
                (rr red "Adoquin gris 10x20x6" "UN" adoq-und)
                (rr red "Loseta lisa 20x20x6" "UN" loseta-und)
                (rr red "Loseta toperol 20x20x6" "UN" top-und)
                (rr red "Loseta guia 20x20x6" "UN" guia-und)
                (rr red "Bordillo prefabricado A-80" "UN" a80)
                (rr red "Arena de nivelacion" "M3" arena)
                (rr red "Transporte de prefabricados" "KG" kg-prefab)
                (rr red "Suministro sardinel bajo A-85 para rampa" "UN"
                  (if (> a85 0.0) (float (fix (+ 0.999999 a85))) 0.0))
                (rr red "Suministro sardinel alto A-86 para rampas" "UN"
                  (if (> a86 0.0)
                    (float (fix (+ 0.999999 (/ a86 (urb:prefab-largo "Sardinel A-86")))) ) 0.0))
                (rr red "M.O. instalacion de sardinel prefabricado" "ML" (+ a85 a86))
                (rr red
                  "Suministro y construccion de remate de rampa en concreto fundido en sitio"
                  "M2" (* (+ a81 a105) 0.39))
                (rr red "M.O. localizacion y replanteo" "M2" base)
                (rr red "M.O. nivelacion con arena" "M2" base)
                (rr red "M.O. instalacion de bordillo prefabricado" "ML" bor-ml)
                (rr red "M.O. instalacion de loseta guia y toperol" "ML"
                  (+ guia-ml top-ml))
                (rr red
                  "Suministro e instalacion de bolardo alto en hierro Tipo M-63"
                  "UN" bolardos))))))
      (setq rows (vl-remove nil rows))
      (setq rows
        (append rows
          (urb:ppto-param-rows "RAMPA" red
            (list
              (cons "AREA" area) (cons "TOPEROL_ML" top-ml)
              (cons "BORDILLO_ML" bor-ml)
              (cons "SARDINEL_A85_ML" a85)
              (cons "SARDINEL_A86_ML" a86)
              (cons "A105_UND" a105)
              (cons "LOSETA_LISA_M2" loseta-m2)
              (cons "ADOQUIN_M2" adoq-m2)
              (cons "GUIA_ML" guia-ml) (cons "CORTE" corte)
              (cons "RELLENO" relleno) (cons "UNIDAD" 1.0))
            "" "" "" etapa sub handle)))
      (setq rows (urb:ppto-rows+zona rows (urb:ppto-zona-de be)))
      (foreach r rows (if r (setq out (cons r out))))
      (setq i (1+ i))))
  out)
(defun urb:ppto-tramo-red (atts / red tipo)
  (setq red (strcase (urb:safe-string (cdr (assoc "RED" atts)) ""))
        tipo (strcase (urb:safe-string (cdr (assoc "TIPO_RED" atts)) "")))
  (cond
    ((wcmatch red "ARESIDUAL") "ALC-SANITARIO")
    ((wcmatch red "ALLUVIAS") "ALC-PLUVIAL")
    ((wcmatch red "ACUEDUCTO") "ACUEDUCTO")
    ((= tipo "MT") "ELECTRICA-MT")
    ((member tipo '("BT" "AP")) "ELECTRICA-BT-AP")
    (T nil)))

;; entibado en los TRES rangos del ppto (E-1A <=2, E-1B 2-3, E-2 >3),
;; repartido con el perfil guardado MP_TRAMO_MEMORIA (frac tn key depth);
;; sin perfil: toda la pared a la banda de la profundidad media.
(defun urb:ppto-entibado-3 (be lng prof-media / samples prev e1a e1b e2
                            frac depth ds dmid item parts)
  (setq samples (mp:read-tramo-memory-samples be)
        e1a 0.0 e1b 0.0 e2 0.0 prev nil)
  (if (and samples (> (length samples) 1))
    (foreach item samples
      (setq frac (nth 0 item) depth (nth 3 item))
      (if prev
        (progn
          (setq ds (* (- frac (car prev)) lng)
                parts (mp:entibado-segment-areas ds (cadr prev) depth)
                e1a (+ e1a (car parts)) e1b (+ e1b (cadr parts))
                e2 (+ e2 (caddr parts)))))
      (setq prev (list frac depth)))
    (if (> prof-media 0.0)
      (cond
        ((<= prof-media 2.0) (setq e1a (* 2.0 lng prof-media)))
        ((<= prof-media 3.0) (setq e1b (* 2.0 lng prof-media)))
        (T (setq e2 (* 2.0 lng prof-media))))))
  (list e1a e1b e2))

;; "3x185mm2 Al XLPE 15kV" -> "3x185 mm2 Al XLPE 15 kV": separa los
;; tokens numericos igual que los escribe el presupuesto, para que el
;; match distinga 3x120 de 3x185 de 3x240.
(defun urb:elec-cond-tokens (cond)
  (setq cond (urb:safe-string cond ""))
  (if (vl-string-search "mm2" cond)
    (setq cond (vl-string-subst " mm2" "mm2" cond)))
  (if (vl-string-search "kV" cond)
    (setq cond (vl-string-subst " kV" "kV" cond)))
  cond)

(defun urb:ppto-rows-tramos (/ ss i be atts red lng diam mat etapa sub handle
                             pini pfin id ent rows out r ductos-n diam-d
                             mat-d ctok exc prof anchoz vol-ductos recub
                             env-banco arena base-gran circ mat-libro
                             trit rec profm dnum cama colchon envv tiporep)
  (setq ss (ssget "_X" '((0 . "INSERT") (2 . "TRAMO_*,MP_TRAMO_*")))
        out nil i 0)
  (if ss
    (repeat (sslength ss)
      (setq be (ssname ss i)
            atts (mp:att-alist be)
            red (urb:ppto-tramo-red atts)
            lng (atof (urb:safe-string (cdr (assoc "LONGITUD" atts)) "0"))
            diam (urb:safe-string (cdr (assoc "DIAMETRO" atts)) "")
            mat (urb:safe-string (cdr (assoc "MATERIAL" atts)) "")
            etapa (urb:safe-string (cdr (assoc "ETAPA" atts)) "")
            sub (urb:safe-string (cdr (assoc "SUBETAPA" atts)) "")
            handle (cdr (assoc 5 (entget be)))
            pini (urb:safe-string (cdr (assoc "POZO_INI" atts)) "")
            pfin (urb:safe-string (cdr (assoc "POZO_FIN" atts)) "")
            id (strcat pini "-" pfin))
      (if (member red '("ALC-SANITARIO" "ALC-PLUVIAL" "ACUEDUCTO"))
        (progn
          ;; MT COMPLETO DE LA ZANJA (2026-09-07, reclamo "falta el MT
          ;; completo de tuberia del acueducto"): los tramos de PRESION
          ;; creados antes de v4.71.1 no traen cimentacion/recebo (el
          ;; bloque de creacion solo cubria gravedad) y a veces tampoco
          ;; profundidad -- aqui se DERIVAN de la geometria del propio
          ;; tramo (excavacion, ancho, diametro, cama) para que el
          ;; capitulo de MT quede completo SIN re-editar el master.
          (setq exc (atof (urb:safe-string
                  (cdr (assoc "EXCAVACION_M3" atts)) "0"))
                trit (atof (urb:safe-string
                  (cdr (assoc "TRITURADO_M3" atts)) "0"))
                rec (atof (urb:safe-string
                  (cdr (assoc "RECEBO_M3" atts)) "0"))
                anchoz (atof (urb:safe-string
                  (cdr (assoc "ANCHO_ZANJA" atts)) "0"))
                profm (atof (urb:safe-string
                  (cdr (assoc "PROFUNDIDAD_MEDIA" atts)) "0"))
                dnum (* 0.0254 (atof (urb:safe-string diam "0"))))
          (if (<= anchoz 1e-9) (setq anchoz (+ 0.60 dnum)))
          (if (and (<= profm 1e-9) (> exc 1e-9) (> lng 0.0)
                   (> anchoz 1e-9))
            (setq profm (/ exc (* lng anchoz))))
          (if (and (<= trit 1e-9) (> exc 1e-9) (> lng 0.0)
                   (> dnum 1e-9))
            (progn
              (setq cama (atof (urb:safe-string
                (cdr (assoc "ESPESOR_CAMA" atts)) "0")))
              (if (<= cama 1e-9) (setq cama 0.10))
              ;; colchon sobre clave: arena 0.10 (presion) / gravilla
              ;; *mp-triturado-sobre-clave* (gravedad)
              (setq colchon
                (if (= red "ACUEDUCTO") 0.10
                  (if (boundp '*mp-triturado-sobre-clave*)
                    *mp-triturado-sobre-clave* 0.30)))
              (setq envv (min exc (* lng anchoz (+ cama dnum colchon)))
                    trit (max 0.0 (- envv (* 0.7854 dnum dnum lng)))
                    rec (max 0.0 (- exc envv)))))
          (setq ent (urb:ppto-entibado-3 be lng profm))
          ;; 2026-09-07 (pedido del usuario: desagregar redes humedas):
          ;; el libro pluvial YA NO trae el APU combinado "Tuberia MAT
          ;; D Hex (banda)" -- quedo desagregado igual que el sanitario
          ;; en SUMINISTRO (UN = tubos de 6 m) + INSTALACION (ML) por
          ;; material y diametro, y la zanja sale por su capitulo de
          ;; MOVIMIENTO DE TIERRAS propio. Nomenclatura por capitulo:
          ;; * ACUEDUCTO: "PVC presion ØN" / "y piezas especiales HD ØN".
          ;; * SANITARIO/PLUVIAL: NOVAFORT/NOVALOC/PVC -> "PVC flexible"
          ;;   (texto del libro; ademas asi el pluvial hereda el precio
          ;;   del sanitario por SUMIF); CSR/CCR/CER -> "en concreto MAT".
          (setq rows
            (cond
              ((= red "ACUEDUCTO")
                ;; PVC va como "PVC presion ØN" en el libro; HD va como
                ;; "tuberia y piezas especiales HD ØN".
                ;; 2026-09-06 (regla del usuario: SUMINISTRO siempre en
                ;; UNIDAD, mano de obra en ML): el suministro se emite en
                ;; UN = tubos de 6 m (ML/6), igual que el sanitario; la
                ;; instalacion sigue en ML.
                (list
                  (urb:ppto-row red
                    (if (= (strcase mat) "PVC")
                      (strcat "Instalacion tuberia PVC presion " diam)
                      (strcat "Instalacion tuberia y piezas especiales " mat " " diam))
                    id pini pfin etapa sub "ML" lng handle)
                  (urb:ppto-row red
                    (if (= (strcase mat) "PVC")
                      (strcat "Suministro tuberia PVC presion " diam)
                      (strcat "Suministro tuberia y piezas especiales " mat " " diam))
                    id pini pfin etapa sub "UN" (/ lng 6.0) handle)))
              (T
                (setq mat-libro
                  (cond
                    ((member (strcase mat) '("NOVAFORT" "NOVALOC" "PVC"))
                      "PVC flexible")
                    ((member (strcase mat) '("CSR" "CCR" "CER"))
                      (strcat "en concreto " (strcase mat)))
                    (T mat)))
                (list
                  (urb:ppto-row red
                    (strcat "Instalacion tuberia " mat-libro " " diam)
                    id pini pfin etapa sub "ML" lng handle)
                  (urb:ppto-row red
                    (strcat "Suministro tuberia " mat-libro " " diam)
                    id pini pfin etapa sub "UN"
                    (float (fix (+ 0.999999 (/ lng 6.0)))) handle)))))
          ;; 2026-09-02: carcamo de proteccion (RAS 0330: cruces o
          ;; recubrimiento insuficiente) -- fila ML solo si el tramo lo
          ;; declara (CARCAMO=SI); actividad "CARCAMO" del libro.
          (if (= (strcase (urb:safe-string
                    (cdr (assoc "CARCAMO" atts)) "")) "SI")
            (setq rows
              (append rows
                (list
                  (urb:ppto-row red "Carcamo"
                    id pini pfin etapa sub "ML" lng handle)))))
          ;; zanja de las TRES redes humedas (2026-09-07: pluvial ya no
          ;; queda embebida en el APU Hex). La cimentacion segun el
          ;; libro: presion (ACU) = arena de pena; alcantarillado =
          ;; gravilla (cama y atraque).
          (setq rows
            (append rows
            (list
              (urb:ppto-row red "Localizacion y replanteo topografico"
                id pini pfin etapa sub "ML" lng handle)
              (urb:ppto-row red "Excavación en material común (incluye cargue, transporte y disposición final)"
                id pini pfin etapa sub "M3" exc handle)
              (urb:ppto-row red
                (if (= red "ACUEDUCTO")
                  "Cama y atraque en arena de pena"
                  "Cimentacion de tuberia en gravilla")
                id pini pfin etapa sub "M3" trit handle)
              (urb:ppto-row red "Suministro y colocacion de recebo B-200"
                id pini pfin etapa sub "M3" rec handle)
              ;; 5.7.22 (pedido del usuario 2026-09-23): el retiro de
              ;; sobrantes YA NO es una actividad aparte -- el cargue, el
              ;; transporte y la disposicion final quedaron dentro del
              ;; unitario de la excavacion mecanica. La fila de sobrantes
              ;; (que desde 5.7.14 repetia el volumen de excavacion) se
              ;; retira para no cobrar dos veces el mismo movimiento.
              (urb:ppto-row red "Entibado E-1A"
                id pini pfin etapa sub "M2" (nth 0 ent) handle)
              (urb:ppto-row red "Entibado E-1B"
                id pini pfin etapa sub "M2" (nth 1 ent) handle)
              (urb:ppto-row red "Entibado E-2"
                id pini pfin etapa sub "M2" (nth 2 ent) handle))))
          ;; 5.7.24 (pedido del usuario): tramos bajo superficie ya
          ;; construida. REPOSICION_M2 = longitud x ancho de reposicion, que
          ;; el motor ya calculaba y nadie exportaba.
          (setq tiporep
            (strcase (urb:safe-string (cdr (assoc "TIPO_REPOSICION" atts)) "")))
          (if (or (wcmatch tiporep "*ADOQUIN*") (wcmatch tiporep "*PAVIMENTO*"))
            (setq rows
              (append rows
                (list
                  (urb:ppto-row red
                    (if (wcmatch tiporep "*ADOQUIN*")
                      "Reposición de andén en adoquín (levante y reinstalación)"
                      "Reposición de pavimento flexible y estructura")
                    id pini pfin etapa sub "M2"
                    (atof (urb:safe-string
                      (cdr (assoc "REPOSICION_M2" atts)) "0"))
                    handle)))))
          ;; cinta de senalizacion sobre tuberia de presion (RAS 0330)
          (if (= red "ACUEDUCTO")
            (setq rows
              (append rows
                (list
                  (urb:ppto-row red "Cinta de senalizacion"
                    id pini pfin etapa sub "ML" lng handle)))))
          (setq rows
            (append rows
              (urb:ppto-param-rows
                (cond
                  ((= red "ALC-SANITARIO") "TRAMO SANITARIO")
                  ((= red "ALC-PLUVIAL") "TRAMO PLUVIAL")
                  (T "TRAMO ACUEDUCTO"))
                red
                (list (cons "LONGITUD" lng)
                  (cons "EXCAVACION"
                    (atof (urb:safe-string
                      (cdr (assoc "EXCAVACION_M3" atts)) "0")))
                  (cons "UNIDAD" 1.0))
                id pini pfin etapa sub handle)))
          (foreach r rows (if r (setq out (cons r out))))))
      (if (member red '("ELECTRICA-MT" "ELECTRICA-BT-AP"))
        (progn
          ;; datos comunes del banco de ductos
          (setq ductos-n (urb:safe-string (cdr (assoc "DUCTOS" atts)) "0")
                diam-d (urb:safe-string (cdr (assoc "DIAM_DUCTO" atts)) "")
                mat-d (urb:safe-string
                  (cdr (assoc "MATERIAL_DUCTO" atts)) "PVC")
                ctok (urb:elec-cond-tokens
                  (urb:safe-string (cdr (assoc "CONDUCTOR" atts)) ""))
                exc (atof (urb:safe-string
                  (cdr (assoc "EXCAVACION_M3" atts)) "0"))
                prof (atof (urb:safe-string
                  (cdr (assoc "PROFUNDIDAD" atts)) "0"))
                anchoz (atof (urb:safe-string
                  (cdr (assoc "ANCHO_ZANJA" atts)) "0"))
                vol-ductos (atof (urb:safe-string
                  (cdr (assoc "VOLUMEN_ELEMENTO_M3" atts)) "0"))
                recub (if (vl-string-search "CALZADA"
                        (strcase (urb:safe-string
                          (cdr (assoc "UBICACION" atts)) "")))
                        0.80 0.60)
                ;; envolvente de arena = altura del banco x ancho x longitud
                ;; (CS203: los ductos van embebidos en arena; encima va el
                ;; relleno compactado hasta la rasante)
                env-banco (max 0.0 (* (- prof recub) anchoz lng))
                arena (max 0.0 (- (min exc env-banco) vol-ductos))
                base-gran (max 0.0 (- exc env-banco)))
          (if (= red "ELECTRICA-MT")
            ;; 2026-08-26 (cruce contra el libro CORRECTO "urbanismo
            ;; maipore.xlsx", capitulo 2.6.1): banco de ductos POR TAMANO
            ;; (filas 1029-1032: 4/6/9/12 en 6"), suministro Y tendido de
            ;; cable por calibre (1040-1045), excavacion/arena/base
            ;; granular (1023-1025), cinta (1034) y mandrilado (1035).
            ;; SIN sobrantes ni reposicion (orden explicita del usuario;
            ;; el libro las tiene en 1026/1027 pero no reciben cantidades
            ;; del modelo).
            (progn
              (if (= (vl-string-trim " " ctok) "")
                (setq ctok "3x185 mm² Al XLPE 15 kV"))
              ;; circuitos de cable en el mismo banco: multiplica el ML
              ;; de suministro y tendido (2026-08-26, 46 tramos del plano
              ;; llevan doble/triple circuito)
              (setq circ
                (max 1 (atoi (urb:safe-string
                  (cdr (assoc "CIRCUITOS" atts)) "1"))))
              (setq rows
                (list
                  (urb:ppto-row red
                    (strcat "Suministro e instalación de banco de ductos "
                      mat-d "-TDP " ductos-n (chr 216) diam-d "\"")
                    id "" "" etapa sub "ML" lng handle)
                  (urb:ppto-row red (strcat "Suministro cable " ctok)
                    id "" "" etapa sub "ML" (* lng circ) handle)
                  (urb:ppto-row red
                    (strcat
                      "Tendido, conexionado e identificación cable " ctok)
                    id "" "" etapa sub "ML" (* lng circ) handle)
                  (urb:ppto-row red
                    "Excavación en material común (incluye cargue, transporte y disposición final)"
                    id "" "" etapa sub "M3" exc handle)
                  (urb:ppto-row red
                    "Relleno en arena limpia para protección de ductos"
                    id "" "" etapa sub "M3" arena handle)
                  (urb:ppto-row red
                    "Relleno y compactación con base granular clase B"
                    id "" "" etapa sub "M3" base-gran handle)
                  (urb:ppto-row red
                    "Cinta de señalización para red de media tensión"
                    id "" "" etapa sub "ML" lng handle)
                  (urb:ppto-row red
                    "Limpieza, mandrilado y verificación de ductos MT"
                    id "" "" etapa sub "ML"
                    (* lng (atof ductos-n)) handle))))
            ;; BT / alumbrado. 5.7.19 (pedido del usuario 2026-09-22): el
            ;; movimiento de tierras sale APARTE con la misma zanja
            ;; normativa de MT (CODENSA CS203/CS207: recubrimiento 0.60 m
            ;; en anden/zona verde y 0.80 m en calzada, ductos embebidos
            ;; en arena y base granular hasta la rasante). Antes el APU de
            ;; la tuberia decia incluir excavacion y relleno; ahora la
            ;; tuberia es solo suministro e instalacion. Los sobrantes van
            ;; en el libro como formula = excavacion.
            (setq rows
              (list
                (urb:ppto-row red
                  (strcat "Suministro e instalación de tuberia "
                    ductos-n " " diam-d " TDP")
                  id "" "" etapa sub "ML" lng handle)
                (urb:ppto-row red
                  (strcat "Suministro e instalación de cable " ctok)
                  id "" "" etapa sub "ML" lng handle)
                (urb:ppto-row red
                  "Excavación en material común (incluye cargue, transporte y disposición final)"
                  id "" "" etapa sub "M3" exc handle)
                (urb:ppto-row red
                  "Relleno en arena limpia para protección de ductos"
                  id "" "" etapa sub "M3" arena handle)
                (urb:ppto-row red
                  "Relleno y compactación con base granular clase B"
                  id "" "" etapa sub "M3" base-gran handle)
                (urb:ppto-row red
                  "Cinta de señalización para red de alumbrado público"
                  id "" "" etapa sub "ML" lng handle))))
          (foreach r rows (if r (setq out (cons r out))))))
      (setq i (1+ i))))
  out)

;; Umbral de REVISION de datos, no profundidad maxima normativa de diseno.
;; No intercambiar cotas ni inferir profundidades automaticamente.
(if (not (boundp '*mp-pozo-depth-review-limit*)) (setq *mp-pozo-depth-review-limit* 30.0))
;; 2026-09-13 (pedido del usuario): la auditoria ya no mira solo el pozo
;; sanitario. Cubre TODO punto que lleve cotas -- pozos, sumideros,
;; cabezales de descole y camaras electricas -- y reporta LAS DOS COTAS,
;; no solo la profundidad, para saber CUAL corregir sin abrir el dialogo
;; de cada elemento uno por uno.
(setq *mp-bases-con-cota*
  '("POZO_SANITARIO" "POZO_PLUVIAL" "SUMIDERO" "CABEZAL_PLUVIAL"
    "CAMARA_CS274" "CAMARA_CS275" "CAMARA_CS276" "CAMARA_CS280"
    "CAJA_BARRAJE_CS281"))

(defun mp:base-con-cota-p (base)
  (if (and base (member (strcase base) *mp-bases-con-cota*)) T nil))

;; Solo el pozo mide ANILLO por ML a partir de la profundidad. En sumideros,
;; cabezales y camaras electricas la profundidad no entra en ninguna
;; cantidad (la de los tramos electricos es normativa CODENSA), asi que
;; que este vacia no es un problema y no se reporta: si no, el aviso sale
;; con cientos de elementos y tapa lo que si importa.
(defun mp:base-es-pozo-p (base)
  (if (and base (member (strcase base) '("POZO_SANITARIO" "POZO_PLUVIAL"))) T nil))

;; En este proyecto una cota es una ELEVACION (~2540-2580 msnm). Un valor
;; chico en una casilla de cota es una PROFUNDIDAD escrita donde va la
;; elevacion. Caso real DOM41 (handle 4B951): COTA_CLAVE_INI = 2.00 contra
;; tapa 2561.65 -> "profundidad" 2559.65. El caso espejo son los TRAT-01/
;; 05/08, con la clave correcta y la tapa en 0 porque el punto cae fuera
;; de SUP_TN: tapa - clave = -2547.
(if (not (boundp '*mp-cota-elevacion-minima*))
  (setq *mp-cota-elevacion-minima* 100.0))

(defun mp:punto-cota-issue (atts / raw d tapa clave)
  (setq raw (vl-string-trim " " (mp:getval "PROFUNDIDAD" atts ""))
        d (distof raw 2)
        tapa (mp:numeric-real (mp:getval "COTA_TN_INI" atts ""))
        clave (mp:numeric-real (mp:getval "COTA_CLAVE_INI" atts "")))
  (cond
    ;; la cota chica delata el dato mal digitado: se nombra primero
    ;; porque dice exactamente CUAL de las dos hay que arreglar
    ((and tapa clave
          (>= (abs tapa) *mp-cota-elevacion-minima*)
          (< (abs clave) *mp-cota-elevacion-minima*))
      "COTA CLAVE NO ES ELEVACION")
    ((and tapa clave
          (>= (abs clave) *mp-cota-elevacion-minima*)
          (< (abs tapa) *mp-cota-elevacion-minima*))
      "COTA TERRENO NO ES ELEVACION")
    ((and tapa clave (<= (- tapa clave) 0.0)) "COTAS INVERTIDAS")
    ((= raw "") "FALTA PROFUNDIDAD")
    ((not d) "PROFUNDIDAD NO NUMERICA")
    ((<= d 0.0) "PROFUNDIDAD NO POSITIVA")
    ((> d *mp-pozo-depth-review-limit*) "PROFUNDIDAD EXCEDE UMBRAL DE REVISION")
    (T nil)))

;; nombre viejo conservado: lo usaban las versiones 5.0.6/5.0.7
(defun mp:pozo-depth-issue (atts) (mp:punto-cota-issue atts))

(defun urb:audit-punto-cotas (/ ss i en base atts issue out)
  (setq ss (ssget "_X" '((0 . "INSERT") (2 . "MP_PUNTO_*"))) i 0)
  (if ss (repeat (sslength ss)
    (setq en (ssname ss i)
          atts (mp:att-alist en))
    ;; el filtro barato primero: sin casillas de cota no hay nada que
    ;; auditar, y asi no se crea el objeto ActiveX de cada luminaria,
    ;; poste o accesorio (el barrido corre dos veces por exportacion)
    (if (or (assoc "COTA_CLAVE_INI" atts) (assoc "COTA_TN_INI" atts))
      (progn
        (setq base (mp:point-reference-base en))
        (if (mp:base-con-cota-p base)
          (setq issue (mp:punto-cota-issue atts))
          (setq issue nil))
        ;; falta de profundidad solo es noticia en los pozos
        (if (and (= issue "FALTA PROFUNDIDAD") (not (mp:base-es-pozo-p base)))
          (setq issue nil))
        (if issue (setq out (cons (list (cdr (assoc 5 (entget en)))
          (mp:getval "ID" atts "") (mp:getval "SUBETAPA" atts "") base
          (mp:getval "COTA_TN_INI" atts "")
          (mp:getval "COTA_CLAVE_INI" atts "")
          (mp:getval "PROFUNDIDAD" atts "") issue) out)))))
    (setq i (1+ i))))
  (reverse out))

(defun urb:audit-pozo-depths () (urb:audit-punto-cotas))

;; una linea legible: el problema, el elemento y las TRES cifras que hay
;; que mirar para corregirlo
(defun urb:punto-cota-txt (v) (if (= v "") "(vacia)" v))
(defun urb:punto-cota-linea (row)
  (strcat (nth 7 row) " | " (nth 3 row) " " (nth 1 row)
    " (sub " (nth 2 row) ", handle " (nth 0 row) ")"
    " terreno=" (urb:punto-cota-txt (nth 4 row))
    " clave=" (urb:punto-cota-txt (nth 5 row))
    " prof=" (urb:punto-cota-txt (nth 6 row))))

(defun urb:print-punto-cota-audit (/ issues row)
  (setq issues (urb:audit-punto-cotas))
  (foreach row issues
    (prompt (strcat "\n  " (urb:punto-cota-linea row))))
  (prompt (strcat "\nPuntos con cotas por revisar: " (itoa (length issues))
    ". Solo lectura; no se modificaron cotas."))
  (princ))

(defun urb:print-pozo-depth-audit () (urb:print-punto-cota-audit))

;; 2026-09-13: ANTES esto BLOQUEABA la exportacion, y cinco puntos malos
;; dejaban al usuario sin poder actualizar ninguna cantidad del libro.
;; Ahora avisa y deja seguir. No es una relajacion del control: los
;; elementos con cota invalida NO SE MIDEN (su anillo sale en cero, el
;; mismo trato que ya tenian los que no tienen profundidad), asi que
;; ningun volumen absurdo entra al presupuesto. Devuelve siempre T.
;; la exportacion pasa por aqui dos veces (c:PPTOEXPORTAR y urb:ppto-run).
;; Con el bloqueo ya no existe, repetir el barrido solo costaba tiempo y
;; le imprimia al usuario la misma lista dos veces: se avisa una sola vez
;; por corrida. c:PPTOEXPORTAR reinicia la bandera.
(defun urb:ppto-warn-punto-cotas (/ issues graves faltan row)
  (if (and (boundp '*urb-cotas-avisado*) *urb-cotas-avisado*)
    T
    (progn
  (setq *urb-cotas-avisado* T)
  (setq issues (urb:audit-punto-cotas))
  (foreach row issues
    (if (= (nth 7 row) "FALTA PROFUNDIDAD")
      (setq faltan (cons row faltan))
      (setq graves (cons row graves))))
  (setq graves (reverse graves))
  (foreach row graves (prompt (strcat "\nCOTA: " (urb:punto-cota-linea row))))
  (if graves
    (prompt (strcat "\nAVISO: " (itoa (length graves))
      " punto(s) con cotas invalidas. NO se miden (quedan en cero) pero la"
      " exportacion CONTINUA. Corrijalos con EDITAR y vuelva a exportar:"
      " al hacerlo, la profundidad se rederiva sola de las dos cotas.")))
  (if faltan
    (prompt (strcat "\nAVISO: " (itoa (length faltan))
      " punto(s) sin profundidad: sus anillos quedan PENDIENTES, no medidos.")))
  T)))

(defun urb:ppto-check-pozo-depths () (urb:ppto-warn-punto-cotas))

(defun urb:ppto-rows-puntos (/ ss i be base atts red id etapa sub handle prof
                             rows out r)
  (setq ss (ssget "_X" '((0 . "INSERT") (2 . "MP_PUNTO_*"))) out nil i 0)
  (if ss
    (repeat (sslength ss)
      (setq be (ssname ss i)
            base (mp:point-reference-base be)
            atts (mp:att-alist be)
            id (urb:safe-string (cdr (assoc "ID" atts)) "")
            etapa (urb:safe-string (cdr (assoc "ETAPA" atts)) "")
            sub (urb:safe-string (cdr (assoc "SUBETAPA" atts)) "")
            ;; 2026-09-13: si las cotas del punto no son confiables la
            ;; profundidad NO se mide (queda en cero). Es lo que permite
            ;; que la exportacion ya no se bloquee: sigue de largo sin
            ;; meter al libro un anillo de 2.559 m.
            prof (if (and (mp:base-con-cota-p base)
                          (mp:punto-cota-issue atts))
                   0.0
                   (atof (urb:safe-string
                     (cdr (assoc "PROFUNDIDAD" atts)) "0")))
            handle (cdr (assoc 5 (entget be)))
            rows nil)
      (cond
        ;; 2026-08-30 (barrido ppto): el capitulo PLUVIAL del libro trae
        ;; el pozo como UNA actividad combinada ("base, cono y tapa") +
        ;; anillo por ML; el desglose de 4 piezas es del capitulo
        ;; SANITARIO. Cada red genera lo que su capitulo espera.
        ;; 2026-09-23 (pedido del usuario): el pozo deja de desglosarse en
        ;; piezas (base, canuela, cono, tapa y anillo por ML) y pasa a UNA
        ;; actividad A TODO COSTO, igual para cualquier altura. El precio
        ;; del libro incluye la excavacion del foso, el retiro y el relleno
        ;; --que antes no estaban en ninguna parte-- y absorbe la camara de
        ;; caida de los pozos profundos. La profundidad ya no multiplica
        ;; nada, pero se sigue leyendo porque alimenta los cuadros, el
        ;; perfil y la auditoria de cotas.
        ((= base "POZO_PLUVIAL")
          (setq rows
            (list
              (urb:ppto-row "ALC-PLUVIAL"
                "Pozo de inspeccion a todo costo"
                id "" "" etapa sub "UN" 1.0 handle))))
        ((= base "POZO_SANITARIO")
          (setq rows
            (list
              (urb:ppto-row "ALC-SANITARIO"
                "Pozo de inspeccion a todo costo"
                id "" "" etapa sub "UN" 1.0 handle))))
        ;; cabezal de descole pluvial (elemento nuevo 2026-08-28)
        ;; 2026-09-07 se DESAGREGO por rango de diametro (8-10 / 12-16 /
        ;; 18-24). 2026-09-23 el usuario pide volver a UNA SOLA actividad:
        ;; en el maestro los 45 cabezales caen todos en la banda 12-16 y
        ;; las otras dos filas del libro quedaban en cero, ademas de que
        ;; el cabezal sin diametro se volvia huerfana. Ahora el concepto
        ;; es unico y el libro lo cobra a todo costo (aletas, solado y
        ;; enrocado), asi que el diametro ya no decide el precio.
        ((= base "CABEZAL_PLUVIAL")
          (setq rows
            (list (urb:ppto-row "ALC-PLUVIAL"
              "Cabezal de descarga en concreto"
              id "" "" etapa sub "UN" 1.0 handle))))
        ((= base "SUMIDERO")
          (setq rows
            (list (urb:ppto-row "ALC-PLUVIAL" "Sumidero"
              id "" "" etapa sub "UN" 1.0 handle))))
        ((= base "ACCESORIO_ACUEDUCTO")
          ;; 2026-08-30: si hay DIAMETRO_SALIDA (tees/reducciones con
          ;; derivacion, viene de los atributos del plano) el concepto
          ;; lleva AMBOS numeros ("TEE 12 4") y el score encuentra la
          ;; actividad exacta "Tee O12 x O4" sin ambiguedad
          (setq rows
            (list (urb:ppto-row "ACUEDUCTO"
              (strcat
                (urb:safe-string (cdr (assoc "TIPO_ACCESORIO" atts)) "Accesorio")
                " " (urb:safe-string (cdr (assoc "DIAMETRO" atts)) "")
                (if (/= (urb:safe-string (cdr (assoc "DIAMETRO_SALIDA" atts)) "") "")
                  (strcat " " (urb:safe-string (cdr (assoc "DIAMETRO_SALIDA" atts)) ""))
                  ""))
              id "" "" etapa sub "UN" 1.0 handle)))
          ;; 2026-09-23: el kit de nivelacion va UNO POR HIDRANTE y la
          ;; prueba va una por cada valvula, hidrante o ventosa. Las dos
          ;; estaban en cero en el libro por no tener de donde salir la
          ;; cantidad; ahora las emite el propio accesorio.
          (setq r (strcase (urb:safe-string (cdr (assoc "TIPO_ACCESORIO" atts)) "")))
          (if (= r "HIDRANTE_TORRE")
            (setq rows
              (cons (urb:ppto-row "ACUEDUCTO"
                      "Kit de nivelacion para hidrante de trafico"
                      id "" "" etapa sub "UN" 1.0 handle)
                    rows)))
          (if (or (wcmatch r "VALVULA*") (wcmatch r "*HIDRANTE*")
                  (wcmatch r "*VENTOSA*"))
            (setq rows
              (cons (urb:ppto-row "ACUEDUCTO"
                      "Pruebas de valvulas, hidrantes y ventosas"
                      id "" "" etapa sub "UN" 1.0 handle)
                    rows))))
        ;; cajas y camaras electricas: 1 UN a su actividad de norma.
        ;; CS276/CS280 pertenecen a MT; CS274/CS275/CS281 a alumbrado/BT.
        ((member base *mp-caja-elec-list*)
          (setq rows
            (list (urb:ppto-row
              (if (member base '("CAMARA_CS276" "CAMARA_CS280"))
                "ELECTRICA-MT" "ELECTRICA-BT-AP")
              (cond
                ((= base "CAMARA_CS274")
                  "Suministro e instalación Caja de paso en mamposteria según norma CS-274")
                ((= base "CAMARA_CS275")
                  "Suministro e instalación Caja de paso en mamposteria según norma CS-275")
                ;; 2026-08-26: redaccion del libro correcto (fila 1037)
                ((= base "CAMARA_CS276")
                  "Construcción de caja de inspección doble norma CS276")
                ;; CS280 NO existe en el libro correcto -- queda pendiente
                ;; a proposito (afectacion reportada al usuario)
                ((= base "CAMARA_CS280")
                  "Construcción de cámara de paso MT norma CS280")
                (T "Caja para barraje norma CS281"))
              id "" "" etapa sub "UN" 1.0 handle))))
        ((= base "LUMINARIA_AP")
          (setq r (urb:safe-string (cdr (assoc "TIPO_LUMINARIA" atts)) ""))
          (setq rows
            (list (urb:ppto-row "ELECTRICA-BT-AP"
              (if (wcmatch (strcase r) "CAMBIO*")
                "Retiro y reinstalación de luminarias nuevas"
                (strcat "Suministro e instalación de luminaria LED"
                  (if (or (= r "") (= (strcase r) "LED")) "" (strcat " " r))))
              (urb:safe-string (cdr (assoc "CODIGO" atts)) id)
              "" "" etapa sub "UN" 1.0 handle))))
        ((= base "POSTE_ELEC")
          ;; 2026-08-26: el poste lleva SUS luminarias (atributos
          ;; LUMINARIAS + TIPO_LUMINARIA) -> genera: poste por altura
          ;; (filas 1082/1098 del libro), luminarias LED (1080/1096) y
          ;; acometida 2x12 AWG (1090/1103). SUPUESTO acometida:
          ;; ML = luminarias x (altura + 3 m) -- ajustable.
          (setq r (urb:safe-string (cdr (assoc "ALTURA_M" atts)) ""))
          (if (= r "") (setq r "12"))
          (setq prof
            (max 0 (atoi (urb:safe-string (cdr (assoc "LUMINARIAS" atts)) "0"))))
          (setq rows
            (list (urb:ppto-row "ELECTRICA-BT-AP"
              (strcat "Suministro e instalación poste de concreto " r
                " m. Tipo recto AP (Incluye ahoyada, hincada y plomada)")
              id "" "" etapa sub "UN" 1.0 handle)))
          (if (> prof 0)
            (setq rows
              (append rows
                (list
                  (urb:ppto-row "ELECTRICA-BT-AP"
                    "Suministro e instalación de luminaria LED"
                    id "" "" etapa sub "UN" (float prof) handle)
                  (urb:ppto-row "ELECTRICA-BT-AP"
                    "Suministro e instalación de alambre 2x12 AWG-THW (Acometida para luminarias)"
                    id "" "" etapa sub "ML"
                    (* prof (+ (atof r) 3.0)) handle))))))
        ((= base "TRANSFORMADOR_AP")
          ;; fila 1084 del libro (pedestal 30 KVA para AP)
          (setq rows
            (list (urb:ppto-row "ELECTRICA-BT-AP"
              "Transformador tipo pedestal 30 KVA 11400 / 380 / 220V"
              id "" "" etapa sub "UN" 1.0 handle)))))
      (cond
        ((= base "POZO_SANITARIO")
          (setq rows
            (append rows
              (urb:ppto-param-rows "POZO SANITARIO" "ALC-SANITARIO"
                (list (cons "PROFUNDIDAD" prof) (cons "UNIDAD" 1.0))
                id "" "" etapa sub handle))))
        ((= base "POZO_PLUVIAL")
          (setq rows
            (append rows
              (urb:ppto-param-rows "POZO PLUVIAL" "ALC-PLUVIAL"
                (list (cons "PROFUNDIDAD" prof) (cons "UNIDAD" 1.0))
                id "" "" etapa sub handle))))
        ((= base "SUMIDERO")
          (setq rows
            (append rows
              (urb:ppto-param-rows "SUMIDERO" "ALC-PLUVIAL"
                (list (cons "UNIDAD" 1.0))
                id "" "" etapa sub handle)))))
      (foreach r rows (if r (setq out (cons r out))))
      (setq i (1+ i))))
  out)

;; ---------- escritura transaccional en TablaMemorias ----------
;; version LENTA original (fila por fila): queda SOLO como respaldo
;; automatico si la via rapida masiva falla por cualquier rareza COM.
(defun urb:ppto-write-rows-slow (lo final-rows dwg / listrows count i row rng
                            val borradas nueva c item)
  ;; borrar de abajo hacia arriba las filas del mismo DWG
  (setq listrows (vlax-get-property lo 'ListRows))
  (setq count (vlax-get-property listrows 'Count) i count borradas 0)
  (while (>= i 1)
    (setq row (urb:ppto-obj (vlax-get-property listrows 'Item i)))
    (setq rng (urb:ppto-obj (vlax-get-property row 'Range)))
    (setq val (urb:ppto-cell-text rng 1 11))
    (vlax-release-object rng)
    (if (= (strcase val) (strcase dwg))
      (progn (vlax-invoke-method row 'Delete) (setq borradas (1+ borradas))))
    (vlax-release-object row)
    (setq i (1- i)))
  ;; insertar el bloque nuevo
  (foreach item final-rows
    (setq nueva (urb:ppto-obj (vlax-invoke-method listrows 'Add)))
    (setq rng (urb:ppto-obj (vlax-get-property nueva 'Range)))
    (setq c 1)
    (foreach v item
      (urb:ppto-put-cell rng 1 c v)
      (setq c (1+ c)))
    (vlax-release-object rng)
    (vlax-release-object nueva))
  (vlax-release-object listrows)
  borradas)

;; 2026-09-04: tabla agregada TablaAgg (hoja MUY OCULTA URB_AGG) -- suma
;; de CANTIDAD por clave ESPECIFICACION|SUBETAPA|RED. Es la fuente de los
;; LOOKUP binarios del libro OPTIMIZADO (etapas_clasif/optimizar_libro.ps1
;; reemplazo los ~800k SUMIFS que hacian el CalculateFull de ~20 min).
;; Si el libro no tiene la tabla (sin optimizar), no hace nada y los
;; SUMIFS clasicos siguen funcionando igual.
(defun urb:ppto-write-agg (wb final / ws lo agg item key q pair rows n
   rng srt sf keyrng lcols nfix cent)
  (setq ws (urb:ppto-find-sheet wb "URB_AGG"))
  (if ws
    (progn
      (setq lo (urb:ppto-find-listobject ws "TablaAgg"))
      (if lo
        (progn
          ;; 1) agregar en memoria (final: 0=RED 2=ESPEC 7=SUBETAPA 9=CANT)
          (setq agg nil)
          (foreach item final
            (setq key (strcat
              (urb:safe-string (nth 2 item) "") "|"
              (urb:safe-string (nth 7 item) "") "|"
              (urb:safe-string (nth 0 item) "")))
            (setq q (nth 9 item))
            (if (not (numberp q)) (setq q (atof (urb:safe-string q "0"))))
            (setq pair (assoc key agg))
            (if pair
              (setq agg (subst (cons key (+ (cdr pair) q)) pair agg))
              (setq agg (cons (cons key q) agg))))
          (setq rows (mapcar '(lambda (p) (list (car p) (cdr p))) agg))
          (setq n (length rows))
          ;; 2) SOLO VALORES sobre la tabla de TAMANO FIJO (jamas Delete/
          ;; Add/Resize: una operacion estructural sobre una tabla con
          ;; ~800k formulas dependientes reconstruye el arbol de
          ;; dependencias y tarda minutos). Relleno con centinela U+00FF
          ;; (ordena despues de cualquier clave real).
          (setq rng (urb:ppto-obj (vlax-get-property lo 'DataBodyRange)))
          (setq nfix (vlax-get-property
            (urb:ppto-obj (vlax-get-property rng 'Rows)) 'Count))
          (if (> n nfix)
            (prompt (strcat "\nOJO TablaAgg: " (itoa n) " claves > "
              (itoa nfix) " filas fijas -- ampliar la tabla con "
              "optimizar_libro.ps1 (export sigue, agregada INCOMPLETA)."))
            (progn
              ;; (chr 255) = U+00FF via codepage 1252 al pasar por COM
              (setq cent (strcat (chr 255) (chr 255) (chr 255)
                                 (chr 255) (chr 255) (chr 255)))
              (repeat (- nfix n)
                (setq rows (cons (list cent 0.0) rows)))
              ;; el centinela va al final por el SORT de abajo; el orden
              ;; de la lista aqui no importa
              (vlax-put-property rng 'Value2
                (urb:excel-matrix-variant (reverse rows)))
              ;; 3) ORDENAR con el criterio de Excel (el LOOKUP binario lo
              ;; exige; ordenar en LISP romperia acentos/simbolos)
              (setq srt (urb:ppto-obj (vlax-get-property lo 'Sort)))
              (setq sf (urb:ppto-obj (vlax-get-property srt 'SortFields)))
              (vlax-invoke-method sf 'Clear)
              (setq lcols (urb:ppto-obj (vlax-get-property lo 'ListColumns)))
              (setq keyrng (urb:ppto-obj (vlax-get-property
                (urb:ppto-obj (vlax-get-property lcols 'Item 1)) 'Range)))
              (vlax-invoke-method sf 'Add keyrng 0 1)
              (vlax-put-property srt 'Header 1)
              (vlax-put-property srt 'MatchCase :vlax-false)
              (vlax-invoke-method srt 'Apply)
              (prompt (strcat "\nTablaAgg actualizada: " (itoa n)
                " claves agregadas (libro optimizado)."))))
          n)
        nil))
    nil))

;; ============================================================
;; PUENTE EXPORT -> HOJA POR EJECUTAR (2026-09-07, v4.71)
;; El ppto reestructurado guarda las cantidades como VALORES en las
;; columnas de subetapa de POR EJECUTAR (ya no existen los SUMIFS/
;; LOOKUP del libro viejo), asi que despues de escribir TablaMemorias
;; hay que VOLCAR la agregacion en las celdas de cada actividad:
;;   - agrega TODA TablaMemorias (todos los DWG) por espec+red+id+sub;
;;   - la fila destino se resuelve con el MISMO vocabulario del match
;;     (desc exacta; desempate por zona del ID, capitulo de la red, UM);
;;   - pone en blanco las filas tocadas por el export ANTERIOR de este
;;     DWG (urb:ppto-pe-old-rows, capturadas antes del reemplazo) y las
;;     tocadas ahora: una actividad que salio del modelo queda en 0 y
;;     las filas MANUALES (nunca exportadas) no se tocan;
;;   - una fila cuyas celdas de subetapa llevan FORMULA (el 3,5% de
;;     preliminares) se salta con aviso, jamas se pisa.
;; ============================================================

;; "1.00000000" (rtos de un codigo numerico) -> "1"; "3A"/"GEN" intactos
(defun urb:ppto-pe-code (txt)
  (setq txt (urb:safe-string txt ""))
  (if (vl-string-search "." txt)
    (vl-string-right-trim "." (vl-string-right-trim "0" txt))
    txt))

;; valor de un elemento del safearray de TablaMemorias como TEXTO plano
(defun urb:ppto-pe-sa-txt (sa i c / v)
  (setq v (vl-catch-all-apply
    '(lambda () (urb:ppto-variant (vlax-safearray-get-element sa i c)))))
  (cond
    ((vl-catch-all-error-p v) "")
    ((= (type v) 'STR) v)
    ((numberp v) (urb:ppto-pe-code (rtos v 2 8)))
    (T "")))

(defun urb:ppto-pe-sa-num (sa i c / v)
  (setq v (vl-catch-all-apply
    '(lambda () (urb:ppto-variant (vlax-safearray-get-element sa i c)))))
  (cond
    ((vl-catch-all-error-p v) 0.0)
    ((numberp v) v)
    ((= (type v) 'STR) (atof v))
    (T 0.0)))

;; (espec red id) de las memorias de ESTE dwg ANTES del reemplazo: son
;; las filas del ppto que el export anterior alimento y que hay que
;; poner en cero si el modelo ya no las trae
(defun urb:ppto-pe-old-rows (lo dwg / dbr n sa out i esp)
  (setq out nil dwg (strcase dwg))
  (setq dbr (vl-catch-all-apply
    '(lambda () (urb:ppto-obj (vlax-get-property lo 'DataBodyRange)))))
  (if (not (vl-catch-all-error-p dbr))
    (progn
      (setq n (vl-catch-all-apply
        '(lambda () (vlax-get-property
          (urb:ppto-obj (vlax-get-property dbr 'Rows)) 'Count))))
      (setq sa (vl-catch-all-apply
        '(lambda () (vlax-variant-value (vlax-get-property dbr 'Value2)))))
      (if (and (not (vl-catch-all-error-p n)) (numberp n) (> n 0)
               (not (vl-catch-all-error-p sa)))
        (progn
          (setq i 1)
          (while (<= i n)
            (if (= (strcase (urb:ppto-pe-sa-txt sa i 11)) dwg)
              (progn
                (setq esp (urb:ppto-pe-sa-txt sa i 3))
                (if (and (/= esp "") (/= (substr esp 1 4) "[SIN"))
                  (setq out (cons (list esp
                    (urb:ppto-pe-sa-txt sa i 1)
                    (urb:ppto-pe-sa-txt sa i 4)) out)))))
            (setq i (1+ i)))))))
  out)

;; resuelve la FILA de POR EJECUTAR de una espec: candidatas por desc
;; exacta y desempate por zona (ID) -> capitulo de la red -> UM.
;; dindex: alist (desc . entradas-del-vocab). Devuelve fila o nil.
(defun urb:ppto-pe-resolve (dindex esp red id um / cands f zn caps)
  (setq cands (cdr (assoc esp dindex)))
  (if (and cands (cdr cands))
    (progn
      ;; 1) zona: el ID de las filas de area lleva el parque
      (setq zn (urb:ppto-normalize id))
      (if (/= zn "")
        (progn
          (setq f (vl-remove-if-not
            '(lambda (e) (urb:ppto-zona-aplica-p e zn)) cands))
          (if f (setq cands f))))
      ;; 2) capitulo de la red
      (if (cdr cands)
        (progn
          (setq caps (urb:ppto-caps-de red))
          (setq f (vl-remove-if-not
            '(lambda (e) (urb:ppto-cap-match-p (nth 0 e) caps)) cands))
          (if f (setq cands f))))
      ;; 3) unidad
      (if (cdr cands)
        (progn
          (setq f (vl-remove-if-not
            '(lambda (e) (= (nth 1 e) (strcase um))) cands))
          (if f (setq cands f))))))
  (if cands (nth 4 (car cands)) nil))

(defun urb:ppto-write-pe (wb lo vocab old-rows / t0 hoja hrow ws coderow
   codes cmap colini colfin dindex pair entry dbr n sa i esp red id sub um
   q ckey rrow cache flat rmap srow rowset item vec letini letfin rng
   escritas ceros saltadas dstart)
  (setq t0 (getvar "MILLISECS"))
  (setq hoja (if (boundp '*urb-ppto-vocab-hoja*) *urb-ppto-vocab-hoja* nil)
        hrow (if (boundp '*urb-ppto-vocab-header*) *urb-ppto-vocab-header* nil))
  (if (and vocab hoja hrow)
    (progn
      (setq ws (urb:ppto-find-sheet wb hoja))
      (if (null ws)
        (prompt "\nOJO puente PE: no encontre la hoja del presupuesto.")
        (progn
          ;; --- mapa de columnas: fila de codigos (header+1) hasta CANTIDAD ---
          (setq coderow (1+ hrow) dstart (+ hrow 2))
          (setq codes (urb:ppto-read-block
            (urb:ppto-obj (vlax-get-property ws 'Range
              (strcat "F" (itoa coderow) ":CB" (itoa coderow)))) 1 75))
          (setq cmap nil colini 6 colfin nil i 0)
          (if codes
            (foreach item (car codes)
              (setq item (urb:ppto-pe-code item))
              (if (and (null colfin) (= (strcase item) "CANTIDAD"))
                (setq colfin (+ 6 i -1)))
              (if (and (null colfin) (/= item ""))
                (setq cmap (cons (cons (+ 6 i) item) cmap)))
              (setq i (1+ i))))
          (setq cmap (reverse cmap))
          (if (or (null cmap) (null colfin))
            (prompt "\nOJO puente PE: no encontre las columnas de subetapa (fila de codigos + CANTIDAD).")
            (progn
              ;; --- indice del vocabulario por descripcion exacta ---
              (setq dindex nil)
              (foreach entry vocab
                (setq pair (assoc (nth 2 entry) dindex))
                (if pair
                  (setq dindex (subst (append pair (list entry)) pair dindex))
                  (setq dindex (cons (list (nth 2 entry) entry) dindex))))
              ;; --- leer TablaMemorias completa y acumular (fila sub q)
              ;; en lista PLANA (cons O(1); nada de subst anidado que se
              ;; vuelve cuadratico con las ~5.400 memorias del master) ---
              (setq flat nil rowset nil cache nil)
              (setq dbr (vl-catch-all-apply
                '(lambda () (urb:ppto-obj (vlax-get-property lo 'DataBodyRange)))))
              (setq n (if (vl-catch-all-error-p dbr) 0
                (vlax-get-property
                  (urb:ppto-obj (vlax-get-property dbr 'Rows)) 'Count)))
              (setq sa (if (> n 0)
                (vl-catch-all-apply
                  '(lambda () (vlax-variant-value
                    (vlax-get-property dbr 'Value2)))) nil))
              (if (vl-catch-all-error-p sa) (setq sa nil n 0))
              (setq i 1)
              (while (<= i n)
                (setq esp (urb:ppto-pe-sa-txt sa i 3))
                (if (and (/= esp "") (/= (substr esp 1 4) "[SIN"))
                  (progn
                    (setq red (urb:ppto-pe-sa-txt sa i 1)
                          id (urb:ppto-pe-sa-txt sa i 4)
                          sub (urb:ppto-pe-code (urb:ppto-pe-sa-txt sa i 8))
                          um (urb:ppto-pe-sa-txt sa i 9)
                          q (urb:ppto-pe-sa-num sa i 10))
                    (if (= sub "") (setq sub "GEN"))
                    (setq ckey (strcat esp "|" red "|" id))
                    (setq pair (assoc ckey cache))
                    (if pair
                      (setq rrow (cdr pair))
                      (progn
                        (setq rrow (urb:ppto-pe-resolve dindex esp red id um))
                        (setq cache (cons (cons ckey rrow) cache))))
                    (if rrow
                      (progn
                        (setq flat (cons (list rrow sub q) flat))
                        (if (not (member rrow rowset))
                          (setq rowset (cons rrow rowset)))))))
                (setq i (1+ i)))
              ;; --- filas a cero: las del export anterior de este dwg ---
              (foreach item old-rows
                (setq ckey (strcat (nth 0 item) "|" (nth 1 item) "|"
                  (nth 2 item)))
                (setq pair (assoc ckey cache))
                (if pair
                  (setq rrow (cdr pair))
                  (progn
                    (setq rrow (urb:ppto-pe-resolve dindex
                      (nth 0 item) (nth 1 item) (nth 2 item) ""))
                    (setq cache (cons (cons ckey rrow) cache))))
                (if (and rrow (not (member rrow rowset)))
                  (setq rowset (cons rrow rowset))))
              ;; --- escribir cada fila afectada (una llamada por fila) ---
              (setq letini (urb:excel-column-name colini)
                    letfin (urb:excel-column-name colfin)
                    escritas 0 ceros 0 saltadas 0)
              (foreach srow rowset
                (if (>= srow dstart)
                  (progn
                    (setq rng (urb:ppto-obj (vlax-get-property ws 'Range
                      (strcat letini (itoa srow) ":" letfin (itoa srow)))))
                    (if (equal (vl-catch-all-apply
                          '(lambda () (vlax-variant-value
                            (vlax-get-property rng 'HasFormula))) )
                          :vlax-true)
                      (progn
                        (setq saltadas (1+ saltadas))
                        (prompt (strcat "\n  puente PE: fila "
                          (itoa srow) " tiene formulas (no se toca).")))
                      (progn
                        ;; triples de ESTA fila y suma por codigo
                        (setq rmap (vl-remove-if-not
                          '(lambda (x) (= (car x) srow)) flat))
                        (setq vec nil)
                        (foreach pair cmap
                          (setq q 0.0)
                          (foreach item rmap
                            (if (= (nth 1 item) (cdr pair))
                              (setq q (+ q (nth 2 item)))))
                          (setq vec (cons
                            (if (> q 0.0005) (atof (rtos q 2 2)) "")
                            vec)))
                        (vlax-put-property rng 'Value2
                          (urb:excel-matrix-variant (list (reverse vec))))
                        (if rmap
                          (setq escritas (1+ escritas))
                          (setq ceros (1+ ceros))))))))
              (prompt (strcat "\nCantidades volcadas en la hoja: "
                (itoa escritas) " actividad(es) escritas"
                (if (> ceros 0)
                  (strcat ", " (itoa ceros) " puestas en cero (ya no estan en el modelo)")
                  "")
                (if (> saltadas 0)
                  (strcat ", " (itoa saltadas) " saltadas por formula")
                  "")
                "."))
              (urb:perf-log (strcat "write-pe: "
                (itoa (- (getvar "MILLISECS") t0)) " ms, "
                (itoa (length rowset)) " filas"))
              (length rowset))))))
    (prompt "\n(puente PE inactivo: presupuesto sin formato NIVEL/subetapas.)")))

;; 2026-09-03 OPTIMIZACION MASIVA (reporte del usuario "actualizar se
;; demora mucho"; export medido en 21 min): la version vieja borraba e
;; insertaba FILA POR FILA (~70.000 llamadas COM y una re-maquetacion de
;; la tabla por fila). Ahora:
;;   1) la columna DWG del cuerpo completo se lee en UNA llamada Value2;
;;   2) las filas a borrar se eliminan por RANGOS contiguos, de abajo
;;      hacia arriba (pocas llamadas en vez de una por fila);
;;   3) el bloque nuevo se escribe con UNA asignacion Value2 de la matriz
;;      completa y un unico Resize de la tabla.
;; Si CUALQUIER paso COM falla, cae solo a urb:ppto-write-rows-slow.
(defun urb:ppto-write-rows (lo final-rows dwg / res)
  (setq res
    (vl-catch-all-apply 'urb:ppto-write-rows-fast
      (list lo final-rows dwg)))
  (if (vl-catch-all-error-p res)
    (progn
      (prompt (strcat "\nEscritura masiva fallo ("
        (vl-catch-all-error-message res)
        "); usando escritura fila a fila..."))
      (urb:ppto-write-rows-slow lo final-rows dwg))
    res))

;; Cells NO es propiedad parametrizada via vlax ("Too many actual
;; parameters", cazado con perf5 2026-09-04): se llega por Cells.Item(r,c)
(defun urb:ppto-cells (ws r c)
  (urb:ppto-obj (vlax-get-property
    (urb:ppto-obj (vlax-get-property ws 'Cells)) 'Item r c)))

(defun urb:ppto-write-rows-fast (lo final-rows dwg / listrows count dbr sa
   vals i v matches runs a ws hdr hrow hcol dtop dcol c1 c2 rng n0 n
   borradas newrng dm)
  (setq borradas 0 dwg (strcase dwg))
  (setq listrows (urb:ppto-obj (vlax-get-property lo 'ListRows)))
  (setq count (vlax-get-property listrows 'Count))
  (setq ws (urb:ppto-obj (vlax-get-property lo 'Parent)))
  (setq hdr (urb:ppto-obj (vlax-get-property lo 'HeaderRowRange)))
  (setq hrow (vlax-get-property hdr 'Row)
        hcol (vlax-get-property hdr 'Column))
  (if (> count 0)
    (progn
      ;; columna DWG (11) completa en UNA llamada
      (setq dbr (urb:ppto-obj (vlax-get-property lo 'DataBodyRange)))
      (setq dtop (vlax-get-property dbr 'Row)
            dcol (vlax-get-property dbr 'Column))
      (setq sa (vlax-variant-value (vlax-get-property dbr 'Value2)))
      (setq vals nil i count)
      (while (>= i 1)
        (setq v (urb:ppto-variant (vlax-safearray-get-element sa i 11)))
        (setq vals (cons (strcase (urb:safe-string
          (if (= (type v) 'STR) v (vl-princ-to-string v)) "")) vals))
        (setq i (1- i)))
      ;; indices (1..count) que son de este DWG -> runs contiguos
      (setq matches nil i 1)
      (foreach v vals
        (if (= v dwg) (setq matches (cons i matches)))
        (setq i (1+ i)))
      ;; matches queda DESCENDENTE; agrupar en runs (fin inicio) y borrar
      ;; de abajo hacia arriba (los indices de arriba no se corren)
      (setq runs nil)
      (foreach i matches
        (if (and runs (= (1+ i) (cadr (car runs))))
          (setq runs (cons (list (car (car runs)) i) (cdr runs)))
          (setq runs (cons (list i i) runs))))
      ;; runs quedo ASCENDENTE por construccion; borrar en reversa
      (foreach a (reverse runs)
        ;; rango absoluto en la hoja: filas del cuerpo (dtop + idx - 1)
        (setq c1 (urb:ppto-cells ws (+ dtop (cadr a) -1) dcol))
        (setq c2 (urb:ppto-cells ws (+ dtop (car a) -1) (+ dcol 11)))
        (setq rng (urb:ppto-obj (vlax-get-property ws 'Range c1 c2)))
        (vlax-invoke-method rng 'Delete -4162)  ;; xlShiftUp
        (setq borradas (+ borradas (1+ (- (car a) (cadr a))))))))
  ;; insertar el bloque nuevo con UNA asignacion + UN Resize
  (setq n (length final-rows))
  (if (> n 0)
    (progn
      (setq n0 (vlax-get-property
        (urb:ppto-obj (vlax-get-property lo 'ListRows)) 'Count))
      (setq c1 (urb:ppto-cells ws (+ hrow n0 1) hcol))
      (setq c2 (urb:ppto-cells ws (+ hrow n0 n) (+ hcol 11)))
      (setq rng (urb:ppto-obj (vlax-get-property ws 'Range c1 c2)))
      (setq dm (urb:excel-matrix-variant final-rows))
      (vlax-put-property rng 'Value2 dm)
      (setq newrng (urb:ppto-obj (vlax-get-property ws 'Range
        (urb:ppto-cells ws hrow hcol) c2)))
      (vlax-invoke-method lo 'Resize newrng)))
  borradas)

;; procesa UNA fila cruda: match + acumuladores (globales de la corrida) +
;; fila final de 12 columnas. Se llama envuelta en vl-catch-all para que un
;; item malo no tumbe la exportacion completa (queda registrado con error).
;; Consulta PRIMERO las equivalencias manuales (*urb-ppto-equiv*, decididas
;; en el dialogo pre-export); una equivalencia solo vale si su descripcion
;; sigue VIVA en el capitulo+UM del presupuesto (si la renombraron, el
;; concepto vuelve a salir como pendiente).
;; ---------- ZONAS (parques) 2026-08-20 ----------
;; Un elemento marcado con ZONA (xdata URB_ZONA, p.ej. "PARQUE 3" o
;; "PQ14") deja de matchear contra su capitulo general y matchea SOLO
;; contra las partes del presupuesto cuyo CAPITULO (nivel 3) o SECCION
;; (nivel 4) contienen ese nombre -- asi las cantidades del anden o
;; bordillo DENTRO de un parque suman al capitulo del parque con sus
;; propios codigos, sin tocar los andenes normales.
(defun urb:ppto-zona-de (ename / d)
  (setq d (urb:get-xdata-strings ename "URB_ZONA"))
  (if (and d (car d)) (urb:safe-string (car d) "") ""))

(defun urb:ppto-rows+zona (rows zona)
  (if (= zona "") rows
    (mapcar '(lambda (f) (if f (append f (list zona)) f)) rows)))

;; hint de seccion (campo 12) -- SOLO sobre filas que ya llevan zona
(defun urb:ppto-rows+hint (rows hint)
  (if (= (urb:safe-string hint "") "") rows
    (mapcar '(lambda (f) (if f (append f (list hint)) f)) rows)))

;; el item del vocabulario aplica a la zona si su capitulo o su seccion
;; (campo 7, nivel 4) contienen el nombre normalizado de la zona
(defun urb:ppto-zona-aplica-p (entry zn)
  (or (vl-string-search zn (nth 0 entry))
      (and (nth 6 entry)
           (vl-string-search zn (nth 6 entry)))))

;; la seccion (nivel 4) del item contiene el hint normalizado
(defun urb:ppto-hint-aplica-p (item hn)
  (and (nth 6 item) (vl-string-search hn (nth 6 item))))

;; match (exacto primero, score despues) sobre una lista de candidatas
(defun urb:ppto-match-zona-1 (cands um concepto / words best best-n second
                              item score exacto)
  (foreach item cands
    (if (and (null exacto) (= (nth 2 item) concepto))
      (setq exacto item)))
  (if exacto
    (cons (nth 2 exacto) (nth 4 exacto))
    (progn
      (setq words (urb:ppto-words concepto))
      (setq best nil best-n 0 second 0.0)
      (foreach item cands
        (setq score (urb:ppto-score words (nth 3 item)))
        (if (>= score 0.5)
          (progn
            (setq best-n (1+ best-n))
            (cond
              ((or (null best) (> score (cadr best)))
                (setq second (if best (cadr best) 0.0))
                (setq best (list item score)))
              ;; texto identico duplicado en otra seccion: no bloquea
              ((and (= score (cadr best))
                    (= (nth 2 item) (nth 2 (car best)))) nil)
              ((> score second) (setq second score))))))
      (if (and best (or (= best-n 1) (> (cadr best) second)))
        (cons (nth 2 (car best)) (nth 4 (car best)))
        (list 'HUERFANA best-n)))))

;; match restringido a la zona; hint (opcional) = palabra de la SECCION
;; preferida dentro del parque (p.ej. "CICLOR" para que una ciclorruta
;; dentro de PQ10A caiga en su seccion CICLORUTA y no en SENDEROS).
;; Si la seccion del hint no puede resolver el concepto, se reintenta
;; sobre toda la zona (el hint es preferencia, no jaula).
(defun urb:ppto-match-zona (zona um concepto vocab hint / zn hn item cands
                            cands-h r)
  (setq zn (urb:ppto-normalize zona)
        hn (urb:ppto-normalize (urb:safe-string hint "")))
  (foreach item vocab
    (if (and (urb:ppto-zona-aplica-p item zn)
             (= (nth 1 item) (strcase um)))
      (setq cands (cons item cands))))
  (setq cands (reverse cands))
  (if (/= hn "")
    (setq cands-h
      (vl-remove-if-not '(lambda (it) (urb:ppto-hint-aplica-p it hn))
        cands)))
  (if cands-h
    (progn
      (setq r (urb:ppto-match-zona-1 cands-h um concepto))
      (if (and (eq (car r) 'HUERFANA) (= (cadr r) 0))
        (urb:ppto-match-zona-1 cands um concepto)
        r))
    (urb:ppto-match-zona-1 cands um concepto)))

(defun urb:ppto-cache-get (key cache / found item)
  ;; assoc con "equal" real: assoc/eq de AutoLISP no garantiza igualdad
  ;; de CONTENIDO para claves construidas con strcat/list (identidad de
  ;; objeto, no de valor) -- foreach + equal es la forma segura
  (setq found nil)
  (foreach item cache
    (if (and (null found) (equal (car item) key)) (setq found item)))
  found)

(defun urb:ppto-process-item (item vocab dwg / m espec red-count ekey evalue
                              valido capitulo entry zona zn cachekey cached
                              origen)
  (setq zona
    (if (> (length item) 10) (urb:safe-string (nth 10 item) "") ""))
  ;; clave con zona: el mismo concepto dentro y fuera del parque son
  ;; vinculaciones DISTINTAS (decisiones y equivalencias separadas)
  (setq ekey
    (if (= zona "")
      (urb:ppto-equiv-key (nth 0 item) (nth 1 item))
      (strcat (nth 0 item) "|" (urb:ppto-normalize zona) "|"
        (urb:ppto-normalize (nth 1 item)))))
  ;; 2026-08-25 (pedido del usuario: Presupuesto lento tras el LOTE
  ;; REDES): la validacion de una equivalencia guardada Y el match en si
  ;; dependen SOLO de (ekey um) -- ni de id/desde/hasta/etapa/handle/qty.
  ;; Con miles de filas repitiendo el MISMO concepto (ej. 337 tramos
  ;; "Instalacion tuberia PVC 8"" tras el lote de ayer), escanear TODO
  ;; el vocabulario en CADA fila (incluso para revalidar una
  ;; equivalencia ya guardada) volvia el export cuadratico. Se memoiza
  ;; (espec origen best-n) por (ekey um) dentro de esta corrida -- el
  ;; registro de huerfanas sigue siendo POR FILA (lleva el handle) y la
  ;; logica de match/validacion en si NO CAMBIA, solo se evita repetirla.
  (setq cachekey (list ekey (strcase (urb:safe-string (nth 7 item) ""))))
  (setq cached (urb:ppto-cache-get cachekey *urb-ppto-match-cache*))
  (if cached
    (progn
      (setq espec (nth 1 cached) origen (nth 2 cached))
      (if (= origen "PENDIENTE")
        (progn
          (setq espec
            (strcat "[SIN MATCH x" (itoa (nth 3 cached)) "] " (nth 1 item)))
          (setq *urb-ppto-huerfanas*
            (cons (list (nth 0 item) (nth 1 item) (nth 3 cached) (nth 9 item)
              (nth 7 item))
              *urb-ppto-huerfanas*)))))
    (progn
      (setq evalue (cdr (assoc ekey *urb-ppto-equiv*)))
      (if evalue
        (progn
          (setq valido nil
                capitulo (urb:ppto-caps-de (nth 0 item))
                zn (if (= zona "") nil (urb:ppto-normalize zona)))
          (foreach entry vocab
            (if (and (if zn
                       (urb:ppto-zona-aplica-p entry zn)
                       (urb:ppto-cap-match-p (nth 0 entry) capitulo))
                     (= (nth 1 entry) (strcase (nth 7 item)))
                     (= (nth 2 entry) evalue))
              (setq valido T)))
          (if (not valido) (setq evalue nil))))
      (if evalue
        (progn
          (setq espec evalue origen "ASIGNADA")
          (setq *urb-ppto-match-cache*
            (cons (list cachekey espec origen 0) *urb-ppto-match-cache*)))
        (progn
          (setq m
            (if (= zona "")
              (urb:ppto-match (nth 0 item) (nth 7 item) (nth 1 item) vocab)
              (urb:ppto-match-zona zona (nth 7 item) (nth 1 item) vocab
                (if (> (length item) 11)
                  (urb:safe-string (nth 11 item) "") ""))))
          (if (eq (car m) 'HUERFANA)
            (progn
              (setq origen "PENDIENTE")
              (setq espec
                (strcat "[SIN MATCH x" (itoa (cadr m)) "] " (nth 1 item)))
              (setq *urb-ppto-huerfanas*
                (cons (list (nth 0 item) (nth 1 item) (cadr m) (nth 9 item)
                  (nth 7 item))
                  *urb-ppto-huerfanas*))
              (setq *urb-ppto-match-cache*
                (cons (list cachekey espec origen (cadr m))
                  *urb-ppto-match-cache*)))
            (progn
              (setq espec (car m) origen "AUTO")
              (setq *urb-ppto-match-cache*
                (cons (list cachekey espec origen 0)
                  *urb-ppto-match-cache*))))))))
  ;; registro de TODAS las vinculaciones de la corrida (una por concepto)
  ;; para el dialogo pre-export y la vista de presupuesto:
  ;; (clave red concepto um origen espec cantidad-total-acumulada)
  (setq entry (assoc ekey *urb-ppto-matches*))
  (if entry
    (setq *urb-ppto-matches*
      (subst
        (list (nth 0 entry) (nth 1 entry) (nth 2 entry) (nth 3 entry)
          (nth 4 entry) (nth 5 entry) (+ (nth 6 entry) (nth 8 item)))
        entry *urb-ppto-matches*))
    (setq *urb-ppto-matches*
      (cons
        (list ekey (nth 0 item)
          ;; con zona, el concepto se muestra con su parque para
          ;; distinguirlo del mismo concepto fuera del parque
          (if (= zona "") (nth 1 item)
            (strcat (nth 1 item) " @ " zona))
          (strcase (nth 7 item))
          ;; origen ya viene resuelto (ASIGNADA/AUTO/PENDIENTE) tanto en
          ;; la rama de cache como en la de calculo -- ver arriba
          origen
          espec (nth 8 item))
        *urb-ppto-matches*)))
  (setq *urb-ppto-total* (+ *urb-ppto-total* (nth 8 item)))
  (setq red-count (assoc (nth 0 item) *urb-ppto-por-red*))
  (setq *urb-ppto-por-red*
    (cons (cons (nth 0 item) (1+ (if red-count (cdr red-count) 0)))
      (vl-remove red-count *urb-ppto-por-red*)))
  ;; con zona, la columna ID (si esta libre) lleva el nombre de la zona
  ;; para trazabilidad en el libro
  (list (nth 0 item) (nth 1 item) espec
    (if (and (/= zona "") (= (urb:safe-string (nth 2 item) "") ""))
      zona (nth 2 item))
    (nth 3 item)
    (nth 4 item) (nth 5 item) (nth 6 item) (nth 7 item) (nth 8 item)
    dwg (nth 9 item)))

;; pasada completa de match sobre las filas crudas; reinicia los
;; acumuladores globales y devuelve la lista final de filas de 12 columnas.
(defun urb:ppto-match-all (raw vocab dwg / item m final t0)
  (setq t0 (getvar "MILLISECS"))
  (setq *urb-ppto-huerfanas* nil *urb-ppto-total* 0.0
        *urb-ppto-por-red* nil *urb-ppto-item-errs* nil
        *urb-ppto-matches* nil final nil
        ;; cache de match por (ekey um) -- ver urb:ppto-process-item;
        ;; se reinicia en CADA corrida (incluida ACTUALIZAR) porque el
        ;; usuario puede haber cambiado una equivalencia entre corridas
        *urb-ppto-match-cache* nil)
  (foreach item raw
    (setq m
      (vl-catch-all-apply 'urb:ppto-process-item (list item vocab dwg)))
    (if (vl-catch-all-error-p m)
      (setq *urb-ppto-item-errs*
        (cons
          (list (nth 0 item) (nth 1 item) (vl-catch-all-error-message m))
          *urb-ppto-item-errs*))
      (setq final (cons m final))))
  (urb:perf-log (strcat "match-all: "
    (itoa (- (getvar "MILLISECS") t0)) " ms, "
    (itoa (length raw)) " items"))
  (reverse final))

;; ---------- dialogo pre-exportacion de equivalencias ----------
;; Aparece SIEMPRE antes de escribir (pedido del usuario 2026-08-18):
;; muestra todas las vinculaciones de la corrida -- [PEND] sin actividad,
;; [AUTO] resueltas por el matcher, [GUARD] por equivalencia guardada,
;; [NUEVA] asignadas en esta sesion. El toggle "Ver solo pendientes"
;; filtra la lista. Aceptar exporta; CANCELAR ABORTA sin escribir nada.
(defun urb:ppto-write-match-dcl ()
  (urb:write-dialog-dcl
    "urb_ppto_match"
    '*urb-ppto-match-dcl-ok*
    (list
      "urb_ppto_match : dialog { label = \"Vinculacion con el presupuesto\";"
      ": text { label = \"Seleccione un concepto del plano, luego su actividad del presupuesto, y pulse Asignar.\"; }"
      ": text { label = \"La asignacion queda guardada dentro del libro y no se vuelve a preguntar.\"; }"
      ": row {"
      ": list_box { key = \"pend\"; label = \"Conceptos del plano\"; width = 62; height = 17; }"
      ": list_box { key = \"cand\"; label = \"Actividad del presupuesto (mismo capitulo y unidad)\"; width = 66; height = 17; }"
      "}"
      ": row { : button { key = \"asignar\"; label = \"Asignar\"; } : button { key = \"quitar\"; label = \"Quitar asignacion\"; } : button { key = \"verppto\"; label = \"Ver presupuesto\"; } : button { key = \"param\"; label = \"Parametricas\"; } : toggle { key = \"vista\"; label = \"Ver solo pendientes\"; } }"
      ": text { key = \"estado\"; width = 110; }"
      ": text { label = \"Aceptar = exportar al libro. Cancelar = NO exportar nada.\"; }"
      "ok_cancel; }")))

(defun urb:pmd-vista-groups (/ g out)
  (setq out nil)
  (foreach g *urb-pmd-groups*
    (if (or (not *urb-pmd-solo-pend*)
            (= (nth 4 g) "PENDIENTE")
            (assoc (nth 0 g) *urb-pmd-decisions*))
      (setq out (cons g out))))
  (reverse out))

(defun urb:pmd-labels (/ g d out estado)
  (setq out nil)
  (foreach g *urb-pmd-vista*
    (setq d (cdr (assoc (nth 0 g) *urb-pmd-decisions*)))
    (setq estado
      (cond
        (d "[NUEVA] ")
        ((= (nth 4 g) "PENDIENTE") "[PEND]  ")
        ((= (nth 4 g) "ASIGNADA") "[GUARD] ")
        (T "[AUTO]  ")))
    (setq out
      (cons
        (strcat estado (nth 1 g) " | " (nth 2 g) " [" (nth 3 g) "]  =>  "
          (cond
            (d d)
            ((= (nth 4 g) "PENDIENTE") "(sin actividad)")
            (T (nth 5 g))))
        out)))
  (reverse out))

(defun urb:pmd-estado (/ g pendientes)
  (setq pendientes 0)
  (foreach g *urb-pmd-groups*
    (if (and (= (nth 4 g) "PENDIENTE")
             (not (assoc (nth 0 g) *urb-pmd-decisions*)))
      (setq pendientes (1+ pendientes))))
  (set_tile "estado"
    (strcat (itoa (length *urb-pmd-groups*)) " concepto(s) en la corrida; "
      (itoa pendientes) " sin actividad ([PEND] saldra [SIN MATCH]); "
      (itoa (length *urb-pmd-decisions*)) " asignacion(es) nueva(s).")))

(defun urb:pmd-refill (/ etiqueta)
  (setq *urb-pmd-vista* (urb:pmd-vista-groups))
  (start_list "pend")
  (foreach etiqueta (urb:pmd-labels) (add_list etiqueta))
  (end_list)
  (start_list "cand")
  (end_list)
  (set_tile "vista" (if *urb-pmd-solo-pend* "1" "0"))
  (urb:pmd-estado))

(defun urb:pmd-toggle-vista (valor)
  (setq *urb-pmd-solo-pend* (= valor "1"))
  (urb:pmd-refill))

(defun urb:pmd-select (idx / g capitulo entry)
  (setq g (nth idx *urb-pmd-vista*))
  (if g
    (progn
      (setq capitulo (urb:ppto-caps-de (nth 1 g)))
      (setq *urb-pmd-cands* nil)
      (foreach entry *urb-pmd-vocab*
        (if (and (urb:ppto-cap-match-p (nth 0 entry) capitulo)
                 (= (nth 1 entry) (nth 3 g)))
          (setq *urb-pmd-cands* (cons (nth 2 entry) *urb-pmd-cands*))))
      (setq *urb-pmd-cands* (reverse *urb-pmd-cands*))
      (start_list "cand")
      (foreach entry *urb-pmd-cands* (add_list entry))
      (end_list))))

(defun urb:pmd-asignar (pend-idx cand-idx / g)
  (setq g (nth pend-idx *urb-pmd-vista*))
  (if (and g (nth cand-idx *urb-pmd-cands*))
    (progn
      (setq *urb-pmd-decisions*
        (cons (cons (nth 0 g) (nth cand-idx *urb-pmd-cands*))
          (vl-remove (assoc (nth 0 g) *urb-pmd-decisions*)
            *urb-pmd-decisions*)))
      (urb:pmd-refill))))

(defun urb:pmd-quitar (pend-idx / g)
  (setq g (nth pend-idx *urb-pmd-vista*))
  (if g
    (progn
      (setq *urb-pmd-decisions*
        (vl-remove (assoc (nth 0 g) *urb-pmd-decisions*)
          *urb-pmd-decisions*))
      (urb:pmd-refill))))

;; ---------- vista "Ver presupuesto": arbol con codigos + vinculos ----------
;; Muestra el presupuesto completo (capitulos nivel 3, subsecciones nivel 4
;; y actividades nivel 5 con su CODIGO) y, al seleccionar una actividad,
;; que conceptos del plano estan vinculados a ella y cuanta cantidad total
;; le aportan en esta corrida. Solo lectura; se abre desde el dialogo de
;; vinculacion.
(defun urb:ppto-write-view-dcl ()
  (urb:write-dialog-dcl
    "urb_ppto_view"
    '*urb-ppto-view-dcl-ok*
    (list
      "urb_ppto_view : dialog { label = \"Presupuesto y lo vinculado desde el plano\";"
      ": text { label = \"Seleccione una actividad (nivel con codigo) para ver que le llega del plano.\"; }"
      ": row {"
      ": list_box { key = \"arbol\"; label = \"Presupuesto: codigo | actividad [unidad]\"; width = 80; height = 22; }"
      ": list_box { key = \"vinc\"; label = \"Vinculado desde el plano (cantidad total)\"; width = 58; height = 22; }"
      "}"
      ": text { key = \"vinfo\"; width = 130; }"
      "ok_only; }")))

;; espec EFECTIVA de una vinculacion: la decision de la sesion (si existe)
;; pisa lo que trajo la pasada de match
(defun urb:ppv-espec (m / d)
  (setq d
    (if (boundp '*urb-pmd-decisions*)
      (cdr (assoc (nth 0 m) *urb-pmd-decisions*)) nil))
  (if d d (nth 5 m)))

(defun urb:ppv-links (capitulo desc / m out)
  ;; capitulo "*" (actividad de hoja por secciones): recibe de CUALQUIER red
  (setq out nil)
  (foreach m *urb-ppto-matches*
    (if (and (= (urb:ppv-espec m) desc)
             (or (= capitulo "*")
                 (member capitulo (urb:ppto-caps-de (nth 1 m)))))
      (setq out (cons m out))))
  (reverse out))

(defun urb:ppv-labels (/ o out marca)
  (setq out nil)
  (foreach o *urb-ppto-outline*
    (cond
      ((= (nth 0 o) 3)
        (setq out (cons (strcat "===== " (nth 2 o) " =====") out)))
      ((= (nth 0 o) 4)
        (setq out (cons (strcat "  " (nth 1 o) "  " (nth 2 o)) out)))
      (T
        (setq marca
          (if (urb:ppv-links (nth 4 o) (nth 2 o)) "  <== PLANO" ""))
        (setq out
          (cons
            (strcat "      " (nth 1 o) "  " (nth 2 o)
              " [" (nth 3 o) "]" marca)
            out)))))
  (reverse out))

(defun urb:ppv-select (idx / o links m total etiqueta)
  (setq o (nth idx *urb-ppto-outline*))
  (start_list "vinc")
  (if (and o (= (nth 0 o) 5))
    (progn
      (setq links (urb:ppv-links (nth 4 o) (nth 2 o)) total 0.0)
      (if links
        (foreach m links
          (setq total (+ total (nth 6 m)))
          (add_list
            (strcat (nth 1 m) " | " (nth 2 m) "  =  "
              (rtos (nth 6 m) 2 2) " " (nth 3 m)
              "  (" (nth 4 m) ")")))
        (add_list "(nada vinculado desde este plano)"))
      (end_list)
      (set_tile "vinfo"
        (if links
          (strcat "Actividad " (nth 1 o) ": "
            (itoa (length links)) " concepto(s) del plano, total "
            (rtos total 2 2) " " (nth 3 o) ".")
          (strcat "Actividad " (nth 1 o)
            ": sin aportes de este plano en esta corrida."))))
    (progn
      (end_list)
      (set_tile "vinfo"
        "Seleccione una fila de actividad (las que tienen codigo y unidad)."))))

(defun urb:ppto-view-dialog (/ dcl etiqueta)
  (setq dcl (load_dialog (urb:ppto-write-view-dcl)))
  (if (and (> dcl 0) (new_dialog "urb_ppto_view" dcl))
    (progn
      (start_list "arbol")
      (foreach etiqueta (urb:ppv-labels) (add_list etiqueta))
      (end_list)
      (set_tile "vinfo"
        "Las actividades marcadas con <== PLANO reciben cantidades de este plano.")
      (action_tile "arbol" "(urb:ppv-select (atoi $value))")
      (start_dialog)))
  (if (> dcl 0) (unload_dialog dcl))
  (princ))

;; ---------- dialogo NUEVO PARAMETRO (estilo Valor calculado de Revit) ----------
;; Rediseno 2026-08-19 (pantallazo del usuario con tachones): ventana
;; MINIMA -- Nombre, "Se mide de cada", y una FORMULA con un desplegable
;; [+] que inserta el campo elegido (longitud, area, franja toperol...);
;; en el texto se agrega " / 0.20" o " * 2" a mano. La actividad destino
;; YA NO se elige aqui: es la actividad seleccionada en el arbol (la
;; ventana se abre desde Parametros, que es contextual a esa actividad).
(defun urb:ppto-write-param-dcl ()
  (urb:write-dialog-dcl
    "urb_ppto_param"
    '*urb-ppto-param-dcl-okD*
    (list
      "urb_ppto_param : dialog { label = \"Nuevo parametro\";"
      ": text { key = \"actx\"; width = 100; }"
      ": row { : edit_box { key = \"nombre\"; label = \"Nombre\"; edit_width = 32; } : popup_list { key = \"tipo\"; label = \"Se mide de cada\"; width = 24; } }"
      ": row { : edit_box { key = \"formula\"; label = \"Formula\"; edit_width = 44; } : popup_list { key = \"campos\"; label = \"+\"; width = 30; } }"
      ": text { key = \"pinfo\"; width = 104; }"
      ": row { : button { key = \"agregar\"; label = \"Crear parametro\"; } }"
      "ok_only; }")))

(defun urb:ppp-tipo (/ idx)
  (setq idx (atoi (get_tile "tipo")))
  (nth idx *urb-ppto-param-tipos*))

;; desplegable [+]: las magnitudes del tipo elegido en lenguaje normal;
;; elegir una INSERTA su codigo en la formula (luego se le agrega el
;; operador y el numero a mano: "/ 0.20", "* 2"...)
(defun urb:ppp-fill-campos (/ tdef m)
  (setq tdef (urb:ppp-tipo))
  (start_list "campos")
  (add_list "(elegir campo...)")
  (foreach m (nth 2 tdef) (add_list (urb:ppto-mag-label m)))
  (end_list)
  (set_tile "campos" "0"))

(defun urb:ppp-insertar-campo (/ tdef mags idx codigo actual)
  (setq tdef (urb:ppp-tipo))
  (setq mags (nth 2 tdef))
  (setq idx (1- (atoi (get_tile "campos"))))   ; 0 = "(elegir campo...)"
  (setq codigo (if (>= idx 0) (nth idx mags) nil))
  (if codigo
    (progn
      (setq actual (urb:safe-string (get_tile "formula") ""))
      (set_tile "formula"
        (strcat actual (if (= actual "") "" " ") codigo))
      (set_tile "campos" "0")
      (urb:ppp-preview))))

;; interpreta el texto de la formula: MAGNITUD op numero, numero * MAGNITUD,
;; solo MAGNITUD (= x 1.0), y MAGNITUD op MAGNITUD. Operadores: * / + -
;; (suma y resta desde v4.44, pedido del usuario: TOPEROL_ML + GUIA_ML).
;; Devuelve (codigo-magnitud oper factor) con oper "X"/"D"/"S"/"R" y
;; factor NUMERO o CODIGO de la segunda magnitud; nil si no se entiende.
(defun urb:ppp-parse-formula (texto mags / s pos oper izq der mag-code
                              num-val par simbolo)
  (setq s (vl-string-trim " " (urb:safe-string texto "")))
  (cond
    ((= s "") nil)
    (T
      ;; primer operador presente (las magnitudes no llevan + - * /)
      (setq pos nil oper nil)
      (foreach par '(("+" . "S") ("-" . "R") ("/" . "D") ("*" . "X"))
        (if (null pos)
          (progn
            (setq simbolo (vl-string-search (car par) s))
            (if simbolo (setq pos simbolo oper (cdr par))))))
      (cond
        ((null pos)
          (if (member (strcase s) mags) (list (strcase s) "X" 1.0) nil))
        (T
          (setq izq (vl-string-trim " " (substr s 1 pos)))
          (setq der (vl-string-trim " " (substr s (+ pos 2))))
          (cond
            ((and (member (strcase izq) mags) (member (strcase der) mags))
              (list (strcase izq) oper (strcase der)))
            ((member (strcase izq) mags)
              (setq mag-code (strcase izq) num-val (urb:parse-real der))
              (if (and num-val (> num-val 0.0))
                (list mag-code oper num-val) nil))
            ;; numero primero: solo operaciones conmutativas (x, +)
            ((and (member oper '("X" "S")) (member (strcase der) mags))
              (setq mag-code (strcase der) num-val (urb:parse-real izq))
              (if (and num-val (> num-val 0.0))
                (list mag-code oper num-val) nil))
            (T nil)))))))

;; representa el factor de una parametrica (numero o segunda magnitud)
(defun urb:ppp-factor-str (factor)
  (if (numberp factor) (rtos factor 2 4) (urb:ppto-mag-label factor)))

;; simbolo legible de la operacion guardada
(defun urb:ppp-oper-str (oper / o)
  (setq o (urb:safe-string oper "X"))
  (cond
    ((= o "D") " / ") ((= o "S") " + ") ((= o "R") " - ") (T " x ")))

;; interpretacion en vivo en la linea de info
(defun urb:ppp-preview (/ tdef mags parsed)
  (setq tdef (urb:ppp-tipo))
  (setq mags (nth 2 tdef))
  (setq parsed (urb:ppp-parse-formula (get_tile "formula") mags))
  (set_tile "pinfo"
    (if parsed
      (strcat "Cantidad = " (urb:ppto-mag-label (nth 0 parsed))
        (urb:ppp-oper-str (nth 1 parsed))
        (urb:ppp-factor-str (nth 2 parsed))
        "  (por cada " (nth 0 tdef) ")")
      "Inserte campos con el desplegable + y arme la formula: CAMPO / 0.20, CAMPO * 2, CAMPO + CAMPO...")))

(defun urb:ppp-agregar (/ tdef mags parsed nombre)
  (setq tdef (urb:ppp-tipo))
  (setq mags (nth 2 tdef))
  (setq parsed (urb:ppp-parse-formula (get_tile "formula") mags))
  (setq nombre (urb:safe-string (get_tile "nombre") ""))
  (cond
    ((or (not (boundp '*urb-ppp-pre-act*)) (null *urb-ppp-pre-act*))
      (set_tile "pinfo"
        "Sin actividad destino: cierre y seleccione la actividad en el arbol antes de pulsar +."))
    ((null parsed)
      (set_tile "pinfo"
        "La formula no se entiende: inserte un campo con + y escriba CAMPO / 0.20 o CAMPO * 2."))
    (T
      ;; sin nombre escrito, el parametro se llama como su actividad
      (if (= nombre "") (setq nombre *urb-ppp-pre-act*))
      ;; modo EDICION: reemplaza la version vieja en vez de agregar otra
      (if (and (boundp '*urb-ppp-editando*) *urb-ppp-editando*)
        (progn
          (setq *urb-ppto-param*
            (vl-remove *urb-ppp-editando* *urb-ppto-param*))
          (setq *urb-ppp-editando* nil)))
      (setq *urb-ppto-param*
        (append *urb-ppto-param*
          (list (list (nth 0 tdef) (nth 0 parsed) (nth 2 parsed)
            *urb-ppp-pre-act* (nth 1 parsed) nombre))))
      (urb:ppto-param-write *urb-ppto-wb* *urb-ppto-param*)
      (setq *urb-ppto-param-dirty* T)
      (set_tile "pinfo"
        (strcat "Guardado \"" nombre "\" -> " *urb-ppp-pre-act*
          ". Queda en el libro; la cantidad se mide con"
          " ACTUALIZAR (o al Aceptar la exportacion).")))))

;; sugerencia automatica (pedido 2026-08-18: "ese parametro deberia ya
;; estar creado pero no aparece" -- toperol/guia/adoquin/loseta/bordillo
;; son casos tan comunes que no hay que partir siempre de Area): por el
;; NOMBRE de la actividad destino, adivina la magnitud/operacion/factor
;; tipicos. Solo sugiere si esa magnitud existe en el tipo de elemento
;; actual; si no aplica ninguna regla, no toca nada (queda Area x 1.0).
(defun urb:ppp-sugerir (tdef texto um / mags norm um2)
  (setq mags (nth 2 tdef))
  (setq norm (urb:ppto-normalize texto))
  (setq um2 (strcase (urb:safe-string um "")))
  (cond
    ((and (vl-string-search "toperol" norm) (= um2 "UN")
          (member "TOPEROL_UND" mags))
      (list "TOPEROL_UND" "X" 1.0))
    ((and (vl-string-search "toperol" norm) (member "TOPEROL_ML" mags))
      (list "TOPEROL_ML" "D" 0.20))
    ((and (vl-string-search "guia" norm) (= um2 "UN")
          (member "GUIA_UND" mags))
      (list "GUIA_UND" "X" 1.0))
    ((and (vl-string-search "guia" norm) (member "GUIA_ML" mags))
      (list "GUIA_ML" "D" 0.20))
    ((and (vl-string-search "adoquin" norm) (= um2 "UN")
          (member "ADOQUIN_UND" mags))
      (list "ADOQUIN_UND" "X" 1.0))
    ((and (vl-string-search "adoquin" norm) (member "ADOQUIN_M2" mags))
      (list "ADOQUIN_M2" "X" 1.0))
    ((and (vl-string-search "loseta" norm) (vl-string-search "lisa" norm)
          (= um2 "UN") (member "LOSETA_LISA_UND" mags))
      (list "LOSETA_LISA_UND" "X" 1.0))
    ((and (vl-string-search "loseta" norm) (vl-string-search "lisa" norm)
          (member "LOSETA_LISA_M2" mags))
      (list "LOSETA_LISA_M2" "X" 1.0))
    ((and (vl-string-search "bordillo" norm) (member "BORDILLO_ML" mags))
      (list "BORDILLO_ML" "X" 1.0))
    ((and (vl-string-search "bordillo" norm) (member "LONGITUD" mags))
      (list "LONGITUD" "X" 1.0))
    (T nil)))

(defun urb:ppto-param-dialog (/ dcl dclfile tdef i pre-idx sug)
  (setq dclfile (urb:ppto-write-param-dcl))
  (if (null dclfile)
    (alert "No se pudo preparar la ventana de nuevo parametro (revise permisos de la carpeta temporal de Windows).")
    (progn
      (setq dcl (load_dialog dclfile))
      (if (and dcl (> dcl 0) (new_dialog "urb_ppto_param" dcl))
        (progn
          (set_tile "actx"
            (strcat "La cantidad va a la actividad: "
              (urb:safe-string
                (if (boundp '*urb-ppp-pre-act*) *urb-ppp-pre-act* nil)
                "(seleccione una actividad en el arbol)")
              (if (and (boundp '*urb-ppp-pre-um*) *urb-ppp-pre-um*)
                (strcat " [" *urb-ppp-pre-um* "]") "")))
          (start_list "tipo")
          (foreach tdef *urb-ppto-param-tipos* (add_list (nth 0 tdef)))
          (end_list)
          (set_tile "tipo" "0")
          ;; preseleccion del tipo por el capitulo de la actividad (con
          ;; capitulo comodin "*" no hay pista: queda el primero)
          (if (and (boundp '*urb-ppp-pre-cap*) *urb-ppp-pre-cap*)
            (progn
              (setq i 0 pre-idx nil)
              (foreach tdef *urb-ppto-param-tipos*
                (if (and (null pre-idx)
                         (member *urb-ppp-pre-cap*
                           (urb:ppto-caps-de (nth 1 tdef))))
                  (setq pre-idx i))
                (setq i (1+ i)))
              (if pre-idx (set_tile "tipo" (itoa pre-idx)))))
          (urb:ppp-fill-campos)
          (cond
            ;; modo EDICION: precargar nombre/tipo/formula del existente
            ((and (boundp '*urb-ppp-editando*) *urb-ppp-editando*)
              (setq i 0 pre-idx nil)
              (foreach tdef *urb-ppto-param-tipos*
                (if (and (null pre-idx)
                         (= (nth 0 tdef) (nth 0 *urb-ppp-editando*)))
                  (setq pre-idx i))
                (setq i (1+ i)))
              (if pre-idx
                (progn (set_tile "tipo" (itoa pre-idx))
                  (urb:ppp-fill-campos)))
              (set_tile "nombre"
                (urb:safe-string (nth 5 *urb-ppp-editando*) ""))
              (set_tile "formula"
                (strcat (nth 1 *urb-ppp-editando*)
                  (vl-string-translate "x" "*"
                    (urb:ppp-oper-str (nth 4 *urb-ppp-editando*)))
                  (if (numberp (nth 2 *urb-ppp-editando*))
                    (rtos (nth 2 *urb-ppp-editando*) 2 4)
                    (nth 2 *urb-ppp-editando*)))))
            (T
              ;; formula sugerida por el nombre de la actividad destino
              (setq tdef (urb:ppp-tipo))
              (setq sug
                (urb:ppp-sugerir tdef
                  (urb:safe-string
                    (if (boundp '*urb-ppp-pre-act*) *urb-ppp-pre-act* nil) "")
                  (urb:safe-string
                    (if (boundp '*urb-ppp-pre-um*) *urb-ppp-pre-um* nil) "")))
              (if sug
                (set_tile "formula"
                  (strcat (nth 0 sug) (if (= (nth 1 sug) "D") " / " " * ")
                    (rtos (nth 2 sug) 2 4))))))
          (urb:ppp-preview)
          (action_tile "tipo" "(urb:ppp-fill-campos) (urb:ppp-preview)")
          (action_tile "formula" "(urb:ppp-preview)")
          (action_tile "campos" "(urb:ppp-insertar-campo)")
          (action_tile "agregar" "(urb:ppp-agregar)")
          (start_dialog)))
      (if (and dcl (> dcl 0)) (unload_dialog dcl))))
  (princ))

;; ---------- previsualizacion de la tabla a exportar ----------
;; Muestra las filas exactas que se escribiran en TablaMemorias, con
;; toggles para mostrar/ocultar columnas EN LA VISTA (las 12 columnas del
;; libro son fijas: contrato con los SUMIFS del presupuesto).
(setq *urb-ppto-prev-cols* '(T T T nil nil nil T T T T nil nil))

(setq *urb-ppto-prev-heads*
  '("RED" "CONCEPTO" "ESPECIFICACION" "ID" "DESDE" "HASTA" "ETAPA"
    "SUBETAPA" "UM" "CANTIDAD" "DWG" "HANDLE"))
;; anchos fijos por columna (caracteres) para que la lista se lea en
;; columnas aun con fuente proporcional
(setq *urb-ppto-prev-anchos*
  '(15 30 38 12 7 7 6 5 4 11 14 8))

(defun urb:ppto-pad (texto ancho / s)
  (setq s (urb:safe-string texto ""))
  (if (> (strlen s) ancho)
    (strcat (substr s 1 (- ancho 1)) "~")
    (progn
      (while (< (strlen s) ancho) (setq s (strcat s " ")))
      s)))

(defun urb:ppto-write-prev-dcl ()
  (urb:write-dialog-dcl
    "urb_ppto_prev"
    '*urb-ppto-prev-dcl-ok*
    (list
      "urb_ppto_prev : dialog { label = \"Previsualizacion de la exportacion\";"
      ": text { key = \"pinfo\"; width = 150; }"
      ": row { : toggle { key = \"c1\"; label = \"RED\"; } : toggle { key = \"c2\"; label = \"CONCEPTO\"; } : toggle { key = \"c3\"; label = \"ESPECIFICACION\"; } : toggle { key = \"c4\"; label = \"ID\"; } : toggle { key = \"c5\"; label = \"DESDE\"; } : toggle { key = \"c6\"; label = \"HASTA\"; } : toggle { key = \"c7\"; label = \"ETAPA\"; } : toggle { key = \"c8\"; label = \"SUBETAPA\"; } : toggle { key = \"c9\"; label = \"UM\"; } : toggle { key = \"c10\"; label = \"CANTIDAD\"; } : toggle { key = \"c11\"; label = \"DWG\"; } : toggle { key = \"c12\"; label = \"HANDLE\"; } }"
      ": row { : popup_list { key = \"fred\"; label = \"Filtrar red\"; width = 26; } : edit_box { key = \"ftxt\"; label = \"Buscar texto\"; edit_width = 34; } : button { key = \"aplicar\"; label = \"Aplicar filtro\"; } : spacer { width = 4; } : button { key = \"actualizar\"; label = \"ACTUALIZAR cantidades del modelo\"; } }"
      ": list_box { key = \"filas\"; label = \"Filas que se escribiran en TablaMemorias\"; width = 150; height = 24; }"
      ": text { label = \"Las 12 columnas del libro son fijas (contrato con los SUMIFS); los toggles y filtros solo cambian esta vista.\"; }"
      "ok_only; }")))

(defun urb:ppto-prev-row-label (fila / i out d clave celda)
  (setq clave (urb:ppto-equiv-key (nth 0 fila) (nth 1 fila)))
  (setq d
    (if (boundp '*urb-pmd-decisions*)
      (cdr (assoc clave *urb-pmd-decisions*)) nil))
  (setq i 0 out "")
  (repeat 12
    (if (nth i *urb-ppto-prev-cols*)
      (progn
        (setq celda
          (cond
            ((and (= i 2) d) d)
            ((numberp (nth i fila)) (rtos (nth i fila) 2 3))
            (T (urb:safe-string (nth i fila) ""))))
        (setq out
          (strcat out
            (urb:ppto-pad celda (nth i *urb-ppto-prev-anchos*)) " "))))
    (setq i (1+ i)))
  out)

(defun urb:ppto-prev-head-label (/ i out)
  (setq i 0 out "")
  (repeat 12
    (if (nth i *urb-ppto-prev-cols*)
      (setq out
        (strcat out
          (urb:ppto-pad (nth i *urb-ppto-prev-heads*)
            (nth i *urb-ppto-prev-anchos*)) " ")))
    (setq i (1+ i)))
  out)

(defun urb:ppto-prev-pasa-filtro (fila etiqueta / red-f txt-f)
  (setq red-f
    (if (and (boundp '*urb-ppto-prev-fred*) *urb-ppto-prev-fred*
             (/= *urb-ppto-prev-fred* "TODAS"))
      *urb-ppto-prev-fred* nil))
  (setq txt-f
    (if (boundp '*urb-ppto-prev-ftxt*)
      (strcase (urb:safe-string *urb-ppto-prev-ftxt* "")) ""))
  (and
    (or (null red-f) (= (nth 0 fila) red-f))
    (or (= txt-f "")
        (vl-string-search txt-f (strcase etiqueta)))))

(defun urb:ppto-prev-fill (/ fila n total etiqueta)
  (start_list "filas")
  (add_list (urb:ppto-prev-head-label))
  (setq n 0 total 0)
  (if (boundp '*urb-ppto-final-prev*)
    (foreach fila *urb-ppto-final-prev*
      (setq total (1+ total))
      (setq etiqueta (urb:ppto-prev-row-label fila))
      (if (urb:ppto-prev-pasa-filtro fila etiqueta)
        (progn (add_list etiqueta) (setq n (1+ n))))))
  (end_list)
  (set_tile "pinfo"
    (strcat "Mostrando " (itoa n) " de " (itoa total)
      " fila(s) a escribir. Las asignaciones de esta sesion YA se"
      " reflejan; parametricas nuevas y elementos recien modelados"
      " entran con ACTUALIZAR o al Aceptar.")))

(defun urb:ppto-prev-toggle (idx valor)
  (setq *urb-ppto-prev-cols*
    (urb:list-set-extended *urb-ppto-prev-cols* idx (= valor "1")))
  (urb:ppto-prev-fill))

(defun urb:ppto-prev-aplicar (/ idx)
  (setq idx (atoi (get_tile "fred")))
  (setq *urb-ppto-prev-fred* (nth idx *urb-ppto-prev-reds*))
  (setq *urb-ppto-prev-ftxt* (get_tile "ftxt"))
  (urb:ppto-prev-fill))

;; devuelve el status de start_dialog: 1 = OK, 3 = ACTUALIZAR cantidades
(defun urb:ppto-prev-dialog (/ dcl i fila done)
  (setq *urb-ppto-prev-fred* "TODAS" *urb-ppto-prev-ftxt* "")
  ;; redes presentes en la corrida para el filtro
  (setq *urb-ppto-prev-reds* (list "TODAS"))
  (if (boundp '*urb-ppto-final-prev*)
    (foreach fila *urb-ppto-final-prev*
      (if (not (member (nth 0 fila) *urb-ppto-prev-reds*))
        (setq *urb-ppto-prev-reds*
          (append *urb-ppto-prev-reds* (list (nth 0 fila)))))))
  (setq done 0)
  (setq dcl (load_dialog (urb:ppto-write-prev-dcl)))
  (if (and (> dcl 0) (new_dialog "urb_ppto_prev" dcl))
    (progn
      (setq i 0)
      (repeat 12
        (set_tile (strcat "c" (itoa (1+ i)))
          (if (nth i *urb-ppto-prev-cols*) "1" "0"))
        (setq i (1+ i)))
      (start_list "fred")
      (foreach fila *urb-ppto-prev-reds* (add_list fila))
      (end_list)
      (set_tile "fred" "0")
      (urb:ppto-prev-fill)
      (action_tile "c1" "(urb:ppto-prev-toggle 0 $value)")
      (action_tile "c2" "(urb:ppto-prev-toggle 1 $value)")
      (action_tile "c3" "(urb:ppto-prev-toggle 2 $value)")
      (action_tile "c4" "(urb:ppto-prev-toggle 3 $value)")
      (action_tile "c5" "(urb:ppto-prev-toggle 4 $value)")
      (action_tile "c6" "(urb:ppto-prev-toggle 5 $value)")
      (action_tile "c7" "(urb:ppto-prev-toggle 6 $value)")
      (action_tile "c8" "(urb:ppto-prev-toggle 7 $value)")
      (action_tile "c9" "(urb:ppto-prev-toggle 8 $value)")
      (action_tile "c10" "(urb:ppto-prev-toggle 9 $value)")
      (action_tile "c11" "(urb:ppto-prev-toggle 10 $value)")
      (action_tile "c12" "(urb:ppto-prev-toggle 11 $value)")
      (action_tile "fred" "(urb:ppto-prev-aplicar)")
      (action_tile "aplicar" "(urb:ppto-prev-aplicar)")
      (action_tile "actualizar" "(done_dialog 3)")
      (setq done (start_dialog))))
  (if (> dcl 0) (unload_dialog dcl))
  done)

;; ---------- previsualizacion en el NAVEGADOR (2026-08-18) ----------
;; DCL no puede dibujar lineas de tabla ni colorear encabezados (pedido del
;; usuario tras ver la lista "desordenada"), asi que la previsualizacion se
;; genera como pagina HTML autonoma y se abre en el navegador por defecto:
;; tabla real con bordes, encabezado azul, filas cebra, orden por clic en
;; el encabezado, buscador, filtro por red y desplegable de columnas.
;; Es solo VISTA: cerrarla no toca nada; el libro se escribe al Aceptar.
(defun urb:ppto-html-esc (s / out i c)
  (setq s (urb:safe-string s "") out "" i 1)
  (while (<= i (strlen s))
    (setq c (substr s i 1))
    (setq out
      (strcat out
        (cond ((= c "&") "&amp;") ((= c "<") "&lt;")
              ((= c ">") "&gt;") (T c))))
    (setq i (1+ i)))
  out)

(defun urb:ppto-prev-html (/ file f reds fila clave d celda linea i n h)
  (setq file (urb:temp-file "urb_ppto_preview" ".html"))
  (setq f (open file "w"))
  (if (null f)
    nil
    (progn
      (setq reds nil)
      (if (boundp '*urb-ppto-final-prev*)
        (foreach fila *urb-ppto-final-prev*
          (if (not (member (nth 0 fila) reds))
            (setq reds (append reds (list (nth 0 fila)))))))
      (write-line "<!doctype html>" f)
      (write-line "<html><head><meta charset='windows-1252'>" f)
      (write-line "<title>Previsualizacion exportacion al presupuesto</title>" f)
      (write-line "<style>" f)
      (write-line "body{font-family:'Segoe UI',Arial,sans-serif;margin:0;background:#f4f6f9;color:#1c2733;}" f)
      (write-line "#top{background:#1f4e79;color:#fff;padding:10px 16px;}" f)
      (write-line "#top h1{font-size:17px;margin:0 0 4px 0;}" f)
      (write-line "#top .sub{font-size:12px;color:#cfe0f0;}" f)
      (write-line "#bar{background:#fff;border-bottom:2px solid #1f4e79;padding:8px 16px;display:flex;gap:14px;align-items:center;flex-wrap:wrap;}" f)
      (write-line "#bar label{font-size:13px;}" f)
      (write-line "#bar input,#bar select{padding:4px 6px;border:1px solid #9db4c8;border-radius:3px;font-size:13px;}" f)
      (write-line "#count{font-size:13px;font-weight:600;color:#1f4e79;margin-left:auto;}" f)
      (write-line "details{position:relative;font-size:13px;}" f)
      (write-line "summary{cursor:pointer;padding:4px 10px;border:1px solid #9db4c8;border-radius:3px;background:#eef3f8;user-select:none;}" f)
      (write-line "details div{position:absolute;top:110%;left:0;background:#fff;border:1px solid #9db4c8;border-radius:4px;box-shadow:0 4px 14px rgba(0,0,0,.18);padding:8px 12px;z-index:5;white-space:nowrap;}" f)
      (write-line "details div label{display:block;padding:2px 0;font-size:13px;}" f)
      (write-line "table{border-collapse:collapse;width:100%;font-size:12.5px;background:#fff;}" f)
      (write-line "th{background:#2e6da4;color:#fff;padding:6px 9px;text-align:left;cursor:pointer;position:sticky;top:0;border:1px solid #245a8c;white-space:nowrap;}" f)
      (write-line "th:hover{background:#1f4e79;}" f)
      (write-line "td{border:1px solid #d4dde6;padding:4px 9px;}" f)
      (write-line "tbody tr:nth-child(even) td{background:#eef3f8;}" f)
      (write-line "td.num{text-align:right;font-variant-numeric:tabular-nums;font-weight:600;}" f)
      (write-line ".h{display:none;}" f)
      (write-line "</style></head><body>" f)
      (write-line "<div id='top'><h1>Filas que se escribiran en TablaMemorias</h1>" f)
      (write-line
        (strcat "<div class='sub'>Plano: "
          (urb:ppto-html-esc (getvar "DWGNAME"))
          "&nbsp;&nbsp;|&nbsp;&nbsp;Libro: "
          (urb:ppto-html-esc
            (if (and (boundp '*urb-ppto-path*) *urb-ppto-path*)
              (strcat (vl-filename-base *urb-ppto-path*)
                (urb:safe-string (vl-filename-extension *urb-ppto-path*) ""))
              "?"))
          "&nbsp;&nbsp;|&nbsp;&nbsp;Esta pagina es solo VISTA: para escribir"
          " al libro vuelva a Civil 3D y pulse Aceptar."
          " Ordene con clic en el encabezado.</div></div>") f)
      (write-line "<div id='bar'>" f)
      (write-line "<label>Buscar: <input id='q' oninput='flt()' placeholder='texto en cualquier columna'></label>" f)
      (write-line "<label>Red: <select id='fred' onchange='flt()'>" f)
      (write-line "<option>TODAS</option>" f)
      (foreach linea reds
        (write-line
          (strcat "<option>" (urb:ppto-html-esc linea) "</option>") f))
      (write-line "</select></label>" f)
      (write-line "<details><summary>Columnas &#9662;</summary><div>" f)
      (setq i 0)
      (foreach h *urb-ppto-prev-heads*
        (write-line
          (strcat "<label><input type='checkbox' "
            (if (member i '(3 4 5 10 11)) "" "checked ")
            "onchange='tc(" (itoa i) ",this.checked)'> " h "</label>") f)
        (setq i (1+ i)))
      (write-line "</div></details>" f)
      (write-line "<span id='count'></span>" f)
      (write-line "</div>" f)
      (write-line "<table id='t'><thead><tr>" f)
      (setq i 0)
      (foreach h *urb-ppto-prev-heads*
        (write-line
          (strcat "<th onclick='srt(" (itoa i) ")'>" h "</th>") f)
        (setq i (1+ i)))
      (write-line "</tr></thead><tbody>" f)
      (setq n 0)
      (if (boundp '*urb-ppto-final-prev*)
        (foreach fila *urb-ppto-final-prev*
          (setq n (1+ n))
          (setq clave (urb:ppto-equiv-key (nth 0 fila) (nth 1 fila)))
          (setq d
            (if (boundp '*urb-pmd-decisions*)
              (cdr (assoc clave *urb-pmd-decisions*)) nil))
          (setq linea "<tr>" i 0)
          (repeat 12
            (setq celda
              (cond
                ((and (= i 2) d) d)
                ((numberp (nth i fila)) (rtos (nth i fila) 2 3))
                (T (urb:safe-string (nth i fila) ""))))
            (setq linea
              (strcat linea
                (if (= i 9) "<td class='num'>" "<td>")
                (urb:ppto-html-esc celda) "</td>"))
            (setq i (1+ i)))
          (write-line (strcat linea "</tr>") f)))
      (write-line "</tbody></table>" f)
      (write-line "<script>" f)
      (write-line "var T=document.getElementById('t');" f)
      (write-line "function rows(){return Array.prototype.slice.call(T.tBodies[0].rows);}" f)
      (write-line "function flt(){var q=document.getElementById('q').value.toLowerCase();var r=document.getElementById('fred').value;var n=0;rows().forEach(function(tr){var ok=(r=='TODAS'||tr.cells[0].textContent==r)&&(q==''||tr.textContent.toLowerCase().indexOf(q)>=0);tr.style.display=ok?'':'none';if(ok)n++;});document.getElementById('count').textContent='Mostrando '+n+' de '+rows().length+' filas';}" f)
      (write-line "function tc(i,on){var all=T.rows;for(var k=0;k<all.length;k++){var c=all[k].cells[i];if(c)c.classList.toggle('h',!on);}}" f)
      (write-line "var dir={};" f)
      (write-line "function srt(i){var rs=rows();var d=dir[i]=!dir[i];rs.sort(function(a,b){var x=a.cells[i].textContent,y=b.cells[i].textContent;var nx=parseFloat(x),ny=parseFloat(y);if(!isNaN(nx)&&!isNaN(ny))return d?nx-ny:ny-nx;return d?x.localeCompare(y):y.localeCompare(x);});rs.forEach(function(r){T.tBodies[0].appendChild(r);});}" f)
      (write-line "[3,4,5,10,11].forEach(function(i){tc(i,false);});" f)
      (write-line "flt();" f)
      (write-line "</script></body></html>" f)
      (close f)
      file)))

(defun urb:ppto-prev-abrir (/ file)
  (setq file (urb:ppto-prev-html))
  (if file
    (progn (startapp "explorer" (strcat "\"" file "\"")) file)
    nil))

;; ---------- dialogo PRINCIPAL sobre el ARBOL del presupuesto ----------
;; (rediseno 2026-08-18 pedido del usuario tras validar la vista en vivo):
;; a la izquierda el presupuesto completo (codigos, niveles, unidades) con
;; su estado de vinculo; a la derecha lo que le llega del plano y los
;; conceptos disponibles para asignar. Desde aqui tambien se crean
;; parametricas apuntando a la actividad seleccionada y se previsualiza la
;; tabla a exportar. Aceptar exporta; Cancelar ABORTA.
;; Rediseno 2026-08-19 (pedido del usuario, pantallazos marcados): fuera
;; las lineas de trazabilidad/estado y los botones de cambiar hoja/libro
;; (viven en el boton Vinculacion de la cinta); fuera la lista de
;; "Conceptos del plano disponibles" -- ahora un boton [+] junto a
;; "Vinculado desde el plano" abre la ventana PARAMETROS, donde se asigna,
;; se quita y se crean parametricas (que aparecen ahi con su NOMBRE).
(defun urb:ppto-write-match2-dcl ()
  (urb:write-dialog-dcl
    "urb_ppto_match2"
    '*urb-ppto-match2-dcl-okC*
    (list
      "urb_ppto_match2 : dialog { label = \"Vinculacion con el presupuesto\";"
      ": row {"
      ": list_box { key = \"arbol\"; label = \"Presupuesto: codigo | actividad [unidad]\"; width = 76; height = 22; }"
      ": column {"
      ": row { : text { label = \"Vinculado desde el plano\"; } : spacer { width = 24; } : button { key = \"mas\"; label = \"+\"; width = 6; } }"
      ": list_box { key = \"vinc\"; width = 56; height = 20; }"
      "}"
      "}"
      ": row { : button { key = \"prever\"; label = \"Previsualizar (navegador)\"; } : button { key = \"actualizar\"; label = \"ACTUALIZAR del modelo\"; } }"
      "ok_cancel; }")))

;; ---------- ventana PARAMETROS (se abre con el boton [+]) ----------
;; Lista los "parametros" del plano asignables a la actividad seleccionada
;; (conceptos medidos de la misma unidad + parametricas definidas hacia esa
;; actividad, con su NOMBRE). Desde aqui se asigna, se quita y se crean
;; parametricas nuevas.
(defun urb:ppto-write-params-dcl ()
  (urb:write-dialog-dcl
    "urb_ppto_params"
    '*urb-ppto-params-dcl-ok*
    (list
      "urb_ppto_params : dialog { label = \"Parametros\";"
      ": text { key = \"pact\"; width = 100; }"
      ": list_box { key = \"plist\"; label = \"Parametros del plano (misma unidad que la actividad)\"; width = 100; height = 14; }"
      ": row { : button { key = \"pasignar\"; label = \"Asignar a esta actividad\"; } : button { key = \"pquitar\"; label = \"Quitar asignacion\"; } : button { key = \"pnuevo\"; label = \"Nuevo parametro...\"; } : button { key = \"peditar\"; label = \"Editar parametro...\"; } : button { key = \"pborrar\"; label = \"Eliminar parametrica\"; } }"
      ": text { key = \"pestado\"; width = 100; }"
      "ok_only; }")))

;; grupos de conceptos del plano candidatos para una actividad
;; (mismo capitulo y misma UM); cada uno con su etiqueta de estado
(defun urb:pm2-cands (capitulo um / m out espec-ef)
  ;; capitulo "*" (actividad de hoja por secciones): acepta conceptos de
  ;; CUALQUIER red del plano con la misma unidad
  (setq out nil)
  (foreach m *urb-ppto-matches*
    (if (and (or (= capitulo "*")
                 (member capitulo (urb:ppto-caps-de (nth 1 m))))
             (= (nth 3 m) (strcase um)))
      (setq out (cons m out))))
  (reverse out))

(defun urb:pm2-cand-label (m / d)
  (setq d
    (if (boundp '*urb-pmd-decisions*)
      (cdr (assoc (nth 0 m) *urb-pmd-decisions*)) nil))
  (strcat
    (cond
      (d "[NUEVA] ")
      ((= (nth 4 m) "PENDIENTE") "[PEND]  ")
      ((= (nth 4 m) "ASIGNADA") "[GUARD] ")
      (T "[AUTO]  "))
    (nth 1 m) " | " (nth 2 m) "  ("
    (rtos (nth 6 m) 2 2) " " (nth 3 m) ")"
    (if (or d (/= (nth 4 m) "PENDIENTE"))
      (strcat "  hoy => "
        (if d d (nth 5 m)))
      "")))

(defun urb:pm2-fila-actividad (idx / o)
  (setq o (nth idx *urb-ppto-outline*))
  (if (and o (= (nth 0 o) 5)) o nil))

(defun urb:pm2-refill-arbol (/ etiqueta pos)
  (setq pos (get_tile "arbol"))
  (start_list "arbol")
  (foreach etiqueta (urb:ppv-labels) (add_list etiqueta))
  (end_list)
  (if (/= pos "") (set_tile "arbol" pos)))

;; (urb:pm2-estado se elimino en v4.42: la linea de estado salio del
;; dialogo principal a pedido del usuario)

(defun urb:pm2-select (idx / links m total p nombre con-link algo)
  (setq *urb-pm2-act* (urb:pm2-fila-actividad idx))
  (start_list "vinc")
  (if *urb-pm2-act*
    (progn
      (setq links
        (urb:ppv-links (nth 4 *urb-pm2-act*) (nth 2 *urb-pm2-act*))
        total 0.0 algo nil)
      (foreach m links
        (setq total (+ total (nth 6 m)) algo T)
        (add_list
          (strcat (nth 1 m) " | " (nth 2 m) "  =  "
            (rtos (nth 6 m) 2 2) " " (nth 3 m))))
      ;; parametricas hacia esta actividad SIN fila medida (magnitud 0 en
      ;; el modelo): antes desaparecian en silencio y el usuario creia que
      ;; la asignacion se habia perdido (reporte 2026-08-19)
      (foreach p *urb-ppto-param*
        (if (= (nth 3 p) (nth 2 *urb-pm2-act*))
          (progn
            (setq con-link nil)
            (foreach m links
              (if (= (nth 2 m) (nth 3 p)) (setq con-link T)))
            (if (not con-link)
              (progn
                (setq algo T)
                (setq nombre (urb:safe-string (nth 5 p) ""))
                (add_list
                  (strcat "[PARAMETRICA] "
                    (if (/= nombre "") nombre (nth 3 p))
                    "  =  0 (la magnitud vale 0 en el modelo hoy;"
                    " la cantidad entra al modelarla + ACTUALIZAR)")))))))
      (if (not algo)
        (add_list "(sin aportes del plano; use el boton + para vincular)"))))
  (end_list))

(defun urb:pm2-idx-actual (/ v)
  (setq v (get_tile "arbol"))
  (if (/= v "") (atoi v) -1))

;; ---------- logica de la ventana PARAMETROS ----------
;; *urb-pm2-plist* corre paralela a la lista visible: cada entrada es
;; (M . match) para un concepto MEDIDO del plano, o (P . parametrica)
;; para una parametrica definida hacia esta actividad que aun no tiene
;; fila medida en la corrida (su cantidad entra con ACTUALIZAR).
(defun urb:pm2-param-de-concepto (m / p out)
  ;; parametrica cuyo destino es exactamente este concepto (las filas
  ;; parametricas llevan concepto = texto de la actividad destino)
  (foreach p *urb-ppto-param*
    (if (and (null out) (= (nth 3 p) (nth 2 m)))
      (setq out p)))
  out)

(defun urb:pm2-params-fill (/ m p etiqueta nombre cubiertas)
  (setq *urb-pm2-plist* nil cubiertas nil)
  (start_list "plist")
  (foreach m (urb:pm2-cands (nth 4 *urb-pm2-act*) (nth 3 *urb-pm2-act*))
    (setq p (urb:pm2-param-de-concepto m))
    (if p (setq cubiertas (cons (nth 3 p) cubiertas)))
    (setq etiqueta
      (if (and p (/= (urb:safe-string (nth 5 p) "") ""))
        (strcat (urb:pm2-cand-label m) "  [parametrica: " (nth 5 p) "]")
        (urb:pm2-cand-label m)))
    (add_list etiqueta)
    (setq *urb-pm2-plist* (cons (cons 'M m) *urb-pm2-plist*)))
  ;; parametricas definidas hacia ESTA actividad sin fila medida aun
  (foreach p *urb-ppto-param*
    (if (and (= (nth 3 p) (nth 2 *urb-pm2-act*))
             (not (member (nth 3 p) cubiertas)))
      (progn
        (setq nombre (urb:safe-string (nth 5 p) ""))
        (add_list
          (strcat "[PARAMETRICA] "
            (if (/= nombre "") nombre (nth 3 p))
            "  --  " (urb:ppto-mag-label (nth 1 p))
            (urb:ppp-oper-str (nth 4 p))
            (urb:ppp-factor-str (nth 2 p))
            "  (cantidad entra con ACTUALIZAR)"))
        (setq *urb-pm2-plist* (cons (cons 'P p) *urb-pm2-plist*)))))
  (if (null *urb-pm2-plist*)
    (add_list "(no hay parametros del plano con esta unidad; cree uno con Nuevo parametro...)"))
  (end_list)
  (setq *urb-pm2-plist* (reverse *urb-pm2-plist*)))

(defun urb:pm2-params-sel (/ v)
  (setq v (get_tile "plist"))
  (if (/= v "") (nth (atoi v) *urb-pm2-plist*) nil))

(defun urb:pm2-params-asignar (/ sel m)
  (setq sel (urb:pm2-params-sel))
  (cond
    ((null sel)
      (set_tile "pestado" "Seleccione un parametro de la lista."))
    ((eq (car sel) 'P)
      (set_tile "pestado"
        "Esa parametrica ya apunta a esta actividad; su cantidad entra con ACTUALIZAR."))
    (T
      (setq m (cdr sel))
      (setq *urb-pmd-decisions*
        (cons (cons (nth 0 m) (nth 2 *urb-pm2-act*))
          (vl-remove (assoc (nth 0 m) *urb-pmd-decisions*)
            *urb-pmd-decisions*)))
      (urb:pm2-params-fill)
      (set_tile "pestado"
        (strcat "Asignado a: " (nth 2 *urb-pm2-act*))))))

(defun urb:pm2-params-quitar (/ sel m)
  (setq sel (urb:pm2-params-sel))
  (cond
    ((or (null sel) (not (eq (car sel) 'M)))
      (set_tile "pestado"
        "Seleccione el concepto medido cuya asignacion NUEVA quiere quitar."))
    ((not (assoc (nth 0 (cdr sel)) *urb-pmd-decisions*))
      (set_tile "pestado"
        "Ese concepto no tiene asignacion nueva en esta sesion (los AUTO se corrigen reasignandolos a otra actividad)."))
    (T
      (setq m (cdr sel))
      (setq *urb-pmd-decisions*
        (vl-remove (assoc (nth 0 m) *urb-pmd-decisions*)
          *urb-pmd-decisions*))
      (urb:pm2-params-fill)
      (set_tile "pestado" "Asignacion quitada."))))

(defun urb:pm2-params-nuevo ()
  (setq *urb-ppp-pre-cap* (nth 4 *urb-pm2-act*)
        *urb-ppp-pre-act* (nth 2 *urb-pm2-act*)
        *urb-ppp-pre-um* (nth 3 *urb-pm2-act*)
        *urb-ppp-editando* nil)
  (urb:ppto-param-dialog)
  (setq *urb-ppp-pre-cap* nil *urb-ppp-pre-act* nil *urb-ppp-pre-um* nil)
  (urb:pm2-params-fill)
  (set_tile "pestado"
    "Si creo un parametro, ya aparece en la lista con su nombre; la cantidad se mide con ACTUALIZAR."))

;; editar una parametrica existente (pedido 2026-08-19): abre la misma
;; ventana precargada (nombre, tipo, formula); al Crear se REEMPLAZA la
;; version vieja en vez de agregar otra
(defun urb:pm2-params-editar (/ sel p)
  (setq sel (urb:pm2-params-sel))
  (setq p
    (cond
      ((null sel) nil)
      ((eq (car sel) 'P) (cdr sel))
      (T (urb:pm2-param-de-concepto (cdr sel)))))
  (if (null p)
    (set_tile "pestado"
      "Seleccione una parametrica (las marcadas [PARAMETRICA] o [parametrica: ...]).")
    (progn
      (setq *urb-ppp-pre-cap* (nth 4 *urb-pm2-act*)
            *urb-ppp-pre-act* (nth 3 p)
            *urb-ppp-pre-um* (nth 3 *urb-pm2-act*)
            *urb-ppp-editando* p)
      (urb:ppto-param-dialog)
      (setq *urb-ppp-pre-cap* nil *urb-ppp-pre-act* nil
            *urb-ppp-pre-um* nil *urb-ppp-editando* nil)
      (urb:pm2-params-fill)
      (set_tile "pestado" "Edicion aplicada (si pulso Crear parametro)."))))

(defun urb:pm2-params-borrar (/ sel p)
  (setq sel (urb:pm2-params-sel))
  (setq p
    (cond
      ((null sel) nil)
      ((eq (car sel) 'P) (cdr sel))
      (T (urb:pm2-param-de-concepto (cdr sel)))))
  (if (null p)
    (set_tile "pestado"
      "Seleccione una parametrica (las marcadas [PARAMETRICA] o [parametrica: ...]).")
    (progn
      (setq *urb-ppto-param* (vl-remove p *urb-ppto-param*))
      (urb:ppto-param-write *urb-ppto-wb* *urb-ppto-param*)
      (setq *urb-ppto-param-dirty* T)
      (urb:pm2-params-fill)
      (set_tile "pestado" "Parametrica eliminada."))))

;; abre la ventana PARAMETROS para la actividad seleccionada en el arbol
(defun urb:pm2-params-window (/ dclfile dcl)
  (cond
    ((null *urb-pm2-act*)
      (alert "Seleccione primero una actividad del presupuesto (fila con codigo y unidad) y luego pulse +."))
    (T
      (setq dclfile (urb:ppto-write-params-dcl))
      (if (null dclfile)
        (alert "No se pudo preparar la ventana de parametros (revise permisos de la carpeta temporal de Windows).")
        (progn
          (setq dcl (load_dialog dclfile))
          (if (and dcl (> dcl 0) (new_dialog "urb_ppto_params" dcl))
            (progn
              (set_tile "pact"
                (strcat "Actividad: " (nth 2 *urb-pm2-act*)
                  " [" (nth 3 *urb-pm2-act*) "]"))
              (urb:pm2-params-fill)
              (set_tile "pestado"
                "Asigne un parametro medido, o cree uno nuevo con formula.")
              (action_tile "pasignar" "(urb:pm2-params-asignar)")
              (action_tile "pquitar" "(urb:pm2-params-quitar)")
              (action_tile "pnuevo" "(urb:pm2-params-nuevo)")
              (action_tile "peditar" "(urb:pm2-params-editar)")
              (action_tile "pborrar" "(urb:pm2-params-borrar)")
              (start_dialog)))
          (if (and dcl (> dcl 0)) (unload_dialog dcl))
          ;; refrescar el dialogo principal con lo decidido
          (urb:pm2-refill-arbol)
          (urb:pm2-select (urb:pm2-idx-actual)))))))

;; (urb:pm2-elegir-hoja y urb:pm2-parametrica se eliminaron en v4.42:
;; cambiar hoja/libro vive en el boton Vinculacion de la cinta, y las
;; parametricas se crean desde la ventana Parametros del boton [+])

;; Devuelve (cons 'OK decisiones) si el usuario Acepta (decisiones puede
;; ser nil), o 'CANCELADO si cancela -- en ese caso NO se exporta nada.
;; Blindado (2026-08-18, mismo bug real de "Elegir hoja" v4.36): este
;; dialogo se REABRE cada vez que se usa "Cambiar hoja"/"ACTUALIZAR", asi
;; que si el .dcl temporal falla al escribirse en una reapertura, pasar
;; nil a load_dialog crasheaba "bad argument type: stringp nil" en vez de
;; avisar. Se comprueba el archivo antes.
(defun urb:ppto-match-dialog (vocab / m pendientes dcl done dclfile)
  ;; OJO: *urb-pmd-decisions* NO se reinicia aqui -- lo hace urb:ppto-run
  ;; antes del bucle, para que las asignaciones sobrevivan al ACTUALIZAR
  (setq *urb-pmd-vocab* vocab
        *urb-pm2-act* nil *urb-pm2-cands* nil)
  (setq done 0)
  (setq dclfile (urb:ppto-write-match2-dcl))
  (if (null dclfile)
    (alert "No se pudo preparar el dialogo de vinculacion (revise permisos de la carpeta temporal de Windows) -- reintente.")
    (setq dcl (load_dialog dclfile)))
  (if (and dcl (> dcl 0) (new_dialog "urb_ppto_match2" dcl))
    (progn
      (urb:pm2-refill-arbol)
      (action_tile "arbol" "(urb:pm2-select (atoi $value))")
      ;; [+]: ventana PARAMETROS de la actividad seleccionada (asignar,
      ;; quitar, crear parametrica, eliminar parametrica)
      (action_tile "mas" "(urb:pm2-params-window)")
      ;; previsualizacion: se genera la pagina HTML y se abre en el
      ;; navegador SIN cerrar este dialogo (es solo vista)
      (action_tile "prever"
        "(if (not (urb:ppto-prev-abrir)) (alert \"No se pudo generar la pagina de previsualizacion.\"))")
      ;; ACTUALIZAR: cierra con status 3 -> urb:ppto-run re-mide el MODELO
      ;; (elementos nuevos), rehace el match conservando las asignaciones
      ;; de la sesion y reabre este dialogo.
      (action_tile "actualizar" "(done_dialog 3)")
      (setq done (start_dialog))))
  (if (and dcl (> dcl 0)) (unload_dialog dcl))
  (cond
    ((= done 1) (cons 'OK *urb-pmd-decisions*))
    ((= done 3) 'ACTUALIZAR)
    (T 'CANCELADO)))

;; ---------- nucleo de la exportacion (lo envuelve c:PPTOEXPORTAR) ----------
(defun urb:ppto-run (wb / lo vocab raw rows item m final huerfanas dwg total
                     borradas por-red red-count espec result resdlg
                     decisiones d app calc-prev pe-old res-pe)
  (if (not (urb:ppto-check-pozo-depths))
    (setq *urb-ppto-last-summary* '(DATOS-POZOS-INVALIDOS))
    (progn
  (setq lo (urb:ppto-memorias-table wb))
  (setq vocab (if lo (urb:ppto-read-vocab wb) nil))
  (if (and lo vocab)
    (progn
              ;; 1) filas CAD en formato largo. El vocabulario, el libro y
              ;; las actividades parametricas quedan en globales porque los
              ;; generadores y los dialogos los necesitan.
              (setq *urb-ppto-stage* "generacion de filas CAD")
              (setq *urb-ppto-vocab* vocab
                    *urb-ppto-wb* wb
                    *urb-ppto-param* (urb:ppto-param-read wb)
                    *urb-ppto-param-dirty* nil)
              (setq raw
                (append
                  (urb:rows-timed "vias" 'urb:ppto-rows-vias)
                  (urb:rows-timed "andenes" 'urb:ppto-rows-andenes)
                  (urb:rows-timed "prefabs" 'urb:ppto-rows-prefabs)
                  (urb:rows-timed "rampas" 'urb:ppto-rows-rampas)
                  (urb:rows-timed "tramos" 'urb:ppto-rows-tramos)
                  (urb:rows-timed "puntos" 'urb:ppto-rows-puntos)
                  (urb:rows-timed "mobiliario" 'urb:ppto-rows-mobiliario)
                  (urb:rows-timed "senderos" 'urb:ppto-rows-senderos)
                  ;; 2026-09-14 (reporte del usuario: "sigue sin traerme lo
                  ;; referente a zonas verdes"). urb:ppto-rows-zonasverdes
                  ;; SI existia y SI emitia bien (2 bloques, 523,90 m2
                  ;; comprobados), pero estaba en urb:track-collect-rows -el
                  ;; colector del comando de busqueda- y NO en esta lista, que
                  ;; es la que usa la exportacion. Por eso la zona verde nunca
                  ;; llegaba al libro, ni siquiera como huerfana.
                  (urb:rows-timed "zonasverdes" (quote urb:ppto-rows-zonasverdes))
                  (urb:rows-timed "bioswale" 'urb:ppto-rows-bioswale)
                  (urb:rows-timed "canuela-plu" 'urb:ppto-rows-canuela-plu)
                  (urb:rows-timed "senalizacion" 'urb:ppto-rows-senalizacion)))
              ;; 2) match contra el vocabulario vivo (equivalencias del
              ;; LIBRO primero, cascada automatica despues)
              (setq *urb-ppto-stage* "match contra vocabulario")
              (setq dwg (vl-filename-base (getvar "DWGNAME")))
              (setq *urb-ppto-equiv* (urb:ppto-equiv-read wb))
              (setq final (urb:ppto-match-all raw vocab dwg))
              ;; snapshot para la previsualizacion dentro del dialogo
              (setq *urb-ppto-final-prev* final)
              ;; 2b) dialogo SIEMPRE antes de escribir (salvo corridas
              ;; headless con *urb-ppto-sin-dialogo* T): muestra todas las
              ;; vinculaciones, permite asignar/corregir y CANCELAR aborta.
              ;; El boton ACTUALIZAR (previsualizacion) devuelve 'ACTUALIZAR:
              ;; se re-mide el MODELO (elementos nuevos/etc.), se rehace el
              ;; match conservando las asignaciones de la sesion, y se
              ;; reabre el dialogo.
              (setq *urb-pmd-decisions* nil)
              (setq resdlg 'ACTUALIZAR)
              (while (or (eq resdlg 'ACTUALIZAR) (eq resdlg 'CAMBIAR-HOJA))
                (setq resdlg
                  (if (and (boundp '*urb-ppto-sin-dialogo*)
                           *urb-ppto-sin-dialogo*)
                    (cons 'OK nil)
                    (urb:ppto-match-dialog vocab)))
                (cond
                  ((eq resdlg 'ACTUALIZAR)
                    (prompt "\nActualizando cantidades desde el modelo...")
                    (setq *urb-ppto-param-dirty* nil)
                    (setq *urb-ppto-param* (urb:ppto-param-read wb))
                    (setq raw
                      (append
                        (urb:ppto-rows-vias)
                        (urb:ppto-rows-andenes)
                        (urb:ppto-rows-prefabs)
                        (urb:ppto-rows-rampas)
                        (urb:ppto-rows-tramos)
                        (urb:ppto-rows-puntos)
                  (urb:ppto-rows-mobiliario)
                  (urb:ppto-rows-senderos)
                  (urb:ppto-rows-bioswale)
                  (urb:ppto-rows-canuela-plu)
    (urb:ppto-rows-senalizacion)))
                    (setq final (urb:ppto-match-all raw vocab dwg))
                    (setq *urb-ppto-final-prev* final))
                  ;; el usuario eligio otra hoja del presupuesto (boton
                  ;; "Cambiar hoja..."): la preferencia ya quedo guardada en
                  ;; el libro; aqui solo se relee el vocabulario nuevo y se
                  ;; rehace el match -- las filas del modelo NO cambian.
                  ((eq resdlg 'CAMBIAR-HOJA)
                    (prompt "\nReleyendo el presupuesto de la hoja elegida...")
                    (setq vocab (urb:ppto-read-vocab wb))
                    (if vocab
                      (progn
                        (setq *urb-ppto-vocab* vocab)
                        (setq final (urb:ppto-match-all raw vocab dwg))
                        (setq *urb-ppto-final-prev* final))
                      (progn
                        (prompt "\nOJO: la hoja elegida no se pudo leer; sigue con el vocabulario anterior.")
                        (setq resdlg 'ACTUALIZAR)))))) ; fuerza otra vuelta con lo anterior
              (cond
                ((eq resdlg 'CANCELADO)
                (progn
                  (prompt
                    "\nExportacion CANCELADA: no se escribio nada en el libro.")
                  (if (not (and (boundp '*urb-ppto-sin-dialogo*)
                                *urb-ppto-sin-dialogo*))
                    (alert
                      (strcat "Exportacion CANCELADA."
                        "\n\nNO se escribio nada en el libro."
                        "\nLas asignaciones que ya habia guardadas en el"
                        "\nlibro se conservan; las nuevas de esta sesion"
                        "\nse descartaron.")))
                  (setq *urb-ppto-last-summary*
                    (list 'CANCELADO-POR-USUARIO))))
                ;; el usuario pidio cambiar de LIBRO: urb:ppto-run no es
                ;; dueno del ciclo de vida de Excel.Application (eso lo
                ;; abre/cierra c:PPTOEXPORTAR), asi que aqui solo se avisa
                ;; con un sentinel -- no se escribe nada y c:PPTOEXPORTAR
                ;; se encarga de pedir el archivo nuevo y reintentar.
                ((eq resdlg 'CAMBIAR-LIBRO)
                  (prompt "\nSe pidio cambiar de libro desde la vinculacion.")
                  (setq *urb-ppto-last-summary*
                    (list 'CAMBIAR-LIBRO-SOLICITADO)))
                (T
                (progn
                  (setq decisiones (cdr resdlg))
                  (if decisiones
                    (progn
                      (foreach d decisiones
                        (setq *urb-ppto-equiv*
                          (cons d
                            (vl-remove (assoc (car d) *urb-ppto-equiv*)
                              *urb-ppto-equiv*))))
                      (urb:ppto-equiv-write wb *urb-ppto-equiv*)
                      (setq final (urb:ppto-match-all raw vocab dwg))))
                  ;; si en el dialogo se crearon/eliminaron parametricas,
                  ;; hay que REGENERAR las filas antes de escribir
                  (if (and (boundp '*urb-ppto-param-dirty*)
                           *urb-ppto-param-dirty*)
                    (progn
                      (setq *urb-ppto-param-dirty* nil)
                      (setq *urb-ppto-param* (urb:ppto-param-read wb))
                      (setq raw
                        (append
                          (urb:ppto-rows-vias)
                          (urb:ppto-rows-andenes)
                          (urb:ppto-rows-prefabs)
                          (urb:ppto-rows-rampas)
                          (urb:ppto-rows-tramos)
                          (urb:ppto-rows-puntos)
                  (urb:ppto-rows-mobiliario)
                  (urb:ppto-rows-senderos)
                  (urb:ppto-rows-bioswale)
                  (urb:ppto-rows-canuela-plu)
    (urb:ppto-rows-senalizacion)))
                      (setq final (urb:ppto-match-all raw vocab dwg))))
                  (setq huerfanas *urb-ppto-huerfanas*
                        total *urb-ppto-total*
                        por-red *urb-ppto-por-red*)
                  (if *urb-ppto-item-errs*
                    (progn
                      (prompt (strcat "\nOJO: "
                        (itoa (length *urb-ppto-item-errs*))
                        " fila(s) con error interno, NO exportadas:"))
                      (foreach item *urb-ppto-item-errs*
                        (prompt (strcat "\n  "
                          (urb:safe-string (nth 0 item) "?")
                          " | " (urb:safe-string (nth 1 item) "?")
                          " | " (urb:safe-string (nth 2 item) "?"))))))
                  ;; 3) escribir + guardar
                  ;; OJO velocidad (2026-08-18): el libro real tiene SUMIFS
                  ;; que dependen de TablaMemorias -- con calculo automatico,
                  ;; CADA fila insertada (ListRows.Add) dispara un recalculo
                  ;; completo, y una exportacion de ~110 filas tardaba
                  ;; 15-30+ minutos. Se pone en manual solo durante la
                  ;; escritura y se recalcula UNA vez antes de guardar.
                  ;; -4135 = xlCalculationManual, -4105 = xlCalculationAutomatic
                  ;; (constantes de Excel; AutoLISP no las trae predefinidas,
                  ;; se usan los valores numericos como en xlSheetVeryHidden
                  ;; ya usado arriba en el archivo).
                  (setq *urb-ppto-stage* "escritura en TablaMemorias")
                  (setq app (vl-catch-all-apply
                    '(lambda () (vlax-get-property wb 'Application))))
                  (if (vl-catch-all-error-p app) (setq app nil))
                  (setq calc-prev
                    (if app
                      (vl-catch-all-apply
                        '(lambda () (vlax-get-property app 'Calculation)))
                      nil))
                  (if (and app (not (vl-catch-all-error-p calc-prev)))
                    (vl-catch-all-apply
                      '(lambda () (vlax-put-property app 'Calculation -4135))))
                  ;; sin atrapar aqui: si esto lanza error, debe propagar
                  ;; igual que antes hacia el catch-all de c:PPTOEXPORTAR
                  ;; (no intentar Guardar sobre una escritura a medias). El
                  ;; modo de calculo queda restaurado por la red de
                  ;; seguridad en c:PPTOEXPORTAR aunque esto falle aqui.
                  ;; v4.71: snapshot de que filas del ppto alimentaba el
                  ;; export ANTERIOR de este DWG (para ponerlas en cero
                  ;; si el modelo ya no las trae) -- ANTES del reemplazo
                  (setq pe-old
                    (vl-catch-all-apply 'urb:ppto-pe-old-rows
                      (list lo dwg)))
                  (if (vl-catch-all-error-p pe-old) (setq pe-old nil))
                  (setq borradas (urb:ppto-write-rows lo final dwg))
                  ;; 2026-09-04: tabla agregada para el libro optimizado
                  ;; (LOOKUP binario) -- no-op si el libro no la tiene
                  (setq *urb-ppto-stage* "tabla agregada URB_AGG")
                  (vl-catch-all-apply 'urb:ppto-write-agg (list wb final))
                  ;; v4.71: volcar las cantidades agregadas en las celdas
                  ;; de POR EJECUTAR (el ppto reestructurado guarda
                  ;; valores, no formulas). Blindado: si falla, la
                  ;; TablaMemorias ya quedo bien escrita.
                  (setq *urb-ppto-stage* "cantidades en POR EJECUTAR")
                  (setq res-pe
                    (vl-catch-all-apply 'urb:ppto-write-pe
                      (list wb lo vocab pe-old)))
                  (if (vl-catch-all-error-p res-pe)
                    (prompt (strcat
                      "\nOJO: no se pudieron volcar las cantidades en la"
                      " hoja POR EJECUTAR: "
                      (vl-catch-all-error-message res-pe)
                      " (TablaMemorias SI quedo escrita).")))
                  (setq *urb-ppto-stage* "recalculo final")
                  (if app
                    (progn
                      (vl-catch-all-apply
                        '(lambda () (vlax-invoke-method app 'CalculateFull)))
                      (vl-catch-all-apply
                        '(lambda () (vlax-put-property app 'Calculation
                          (if (and (not (vl-catch-all-error-p calc-prev))
                                   calc-prev)
                            calc-prev -4105))))))
                  (setq *urb-ppto-stage* "guardado del libro")
                  (setq result (vl-catch-all-apply
                    '(lambda () (vlax-invoke-method wb 'Save))))
                  (if (vl-catch-all-error-p result)
                    (prompt (strcat "\nOJO: el libro no se pudo guardar: "
                      (vl-catch-all-error-message result)))
                    (prompt "\nLibro guardado."))
                  ;; 4) reporte
                  (prompt (strcat "\n--- EXPORTACION PPTO (" dwg ") ---"))
                  (prompt (strcat "\nFilas escritas: " (itoa (length final))
                    " (reemplazaron " (itoa borradas) " del mismo DWG)."
                    " Cantidad total control: " (rtos total 2 3)))
                  (foreach item por-red
                    (prompt (strcat "\n  " (car item) ": "
                      (itoa (cdr item)) " fila(s)")))
                  (if huerfanas
                    (progn
                      (prompt (strcat "\nHUERFANAS ("
                        (itoa (length huerfanas))
                        ") - escritas en MEMORIAS marcadas [SIN MATCH], NO suman:"))
                      (foreach item huerfanas
                        (prompt (strcat "\n  " (nth 0 item) " | " (nth 1 item)
                          " | candidatas: " (itoa (nth 2 item))
                          " | handle " (nth 3 item)))))
                    (prompt "\nSin huerfanas: todo matcheo contra el presupuesto."))
                  (setq *urb-ppto-last-summary*
                    (list 'filas (length final) 'borradas borradas
                          'huerfanas (length huerfanas)
                          'errores-items (length *urb-ppto-item-errs*)
                          'primer-error
                          (if *urb-ppto-item-errs*
                            (nth 2 (car *urb-ppto-item-errs*)) "ninguno")))
                  ;; confirmacion VISIBLE (pedido 2026-08-18: "no me bota
                  ;; ningun mensaje de si quedo bien o mal")
                  (if (not (and (boundp '*urb-ppto-sin-dialogo*)
                                *urb-ppto-sin-dialogo*))
                    (alert
                      (strcat
                        (if (vl-catch-all-error-p result)
                          "EXPORTACION ESCRITA pero el libro NO SE PUDO GUARDAR (cierrelo si esta abierto y reintente)."
                          "EXPORTACION CORRECTA: libro guardado.")
                        "\n\nLibro: "
                        (if (and (boundp '*urb-ppto-path*) *urb-ppto-path*)
                          (strcat (vl-filename-base *urb-ppto-path*)
                            (urb:safe-string
                              (vl-filename-extension *urb-ppto-path*) ""))
                          "?")
                        "\nFilas escritas en TablaMemorias: "
                        (itoa (length final))
                        "\nReemplazaron " (itoa borradas)
                        " fila(s) anteriores de este mismo plano (" dwg ")."
                        "\nHuerfanas [SIN MATCH] (escritas pero NO suman): "
                        (itoa (length huerfanas))
                        (if *urb-ppto-item-errs*
                          (strcat "\nOJO: "
                            (itoa (length *urb-ppto-item-errs*))
                            " fila(s) con error interno NO exportadas"
                            " (detalle en la linea de comandos).")
                          "")
                        "\n\nLas asignaciones y parametricas quedaron"
                        "\nguardadas DENTRO del libro.")))))))
    (setq *urb-ppto-last-summary*
      (list 'SIN-TABLA-O-VOCAB
        (if lo 'tabla-ok 'sin-tabla)
        (if vocab 'vocab-ok 'sin-vocab))))
    ))
  *urb-ppto-last-summary*)

;; ---------- comando unico ----------
;; Unico comando expuesto en la cinta (pedido 2026-08-18: quitar el
;; desplegable con 7 items, dejar solo "Exportar al PRESUPUESTO"). Cuando
;; el libro NO se puede abrir por cualquier motivo -- sin configurar, ruta
;; rota, o bloqueado por otra sesion -- ya no se queda en un simple alert
;; sin salida: abre la MISMA ventana de gestion de PPTOLIBRO (cambiar
;; libro, elegir hoja, desvincular, reintentar) para que el usuario pueda
;; resolverlo ahi mismo. Si elige "Reintentar abrir" (o cambia el libro/la
;; hoja y despues Reintentar), se vuelve a intentar sin salir del comando.
(defun c:PPTOEXPORTAR (/ path attach app wb propia result seguir gestion
                       mensaje nuevo)
  (vl-load-com)
  (setq *urb-cotas-avisado* nil)
  ;; 2026-09-13 (reporte del usuario): el usuario corrigio las cotas de
  ;; DOM41 (terreno 2561.295, clave 2558.58 -> 2.715 m) y el aviso le
  ;; seguia mostrando prof=2559.65, el valor viejo. Era orden: la
  ;; auditoria corria aqui y el recalculo mucho despues, dentro de
  ;; urb:q-collect-all. Ahora se rederiva PRIMERO y se audita sobre el
  ;; dato ya al dia, asi que un pozo recien corregido no vuelve a salir.
  (urb:q-refresh-puntos)
  (setq seguir (urb:ppto-check-pozo-depths))
  (if (not seguir) (setq *urb-ppto-last-summary* '(DATOS-POZOS-INVALIDOS)))
  (setq *urb-ppto-headless*
    (and (boundp '*urb-ppto-sin-dialogo*) *urb-ppto-sin-dialogo*))
  (while seguir
    (setq path (urb:ppto-config-read))
    (cond
      ((or (= path "") (null (findfile path)))
        (if *urb-ppto-headless*
          (progn
            (prompt
              (if (= path "") "\nExportacion cancelada: sin libro configurado."
                (strcat "\nNo existe el libro: " path)))
            (setq seguir nil))
          (progn
            (setq gestion
              (urb:ppto-libro-gestionar
                (if (= path "") nil
                  "El archivo configurado ya no existe en esa ruta.")))
            (if (not (eq gestion 'REINTENTAR)) (setq seguir nil)))))
      (T
        (setq *urb-ppto-path* path)
        (setq attach (urb:ppto-attach-excel path)
              app (nth 0 attach) wb (nth 1 attach) propia (nth 2 attach))
        (cond
          ((null wb)
            (setq mensaje (urb:safe-string (nth 2 attach) "Sin Excel."))
            (setq *urb-ppto-last-summary* (list 'SIN-EXCEL mensaje))
            (prompt (strcat "\n" mensaje))
            (if *urb-ppto-headless*
              (setq seguir nil)
              (progn
                (setq gestion
                  (urb:ppto-libro-gestionar
                    (strcat "NO se pudo abrir el libro: " mensaje)))
                (if (not (eq gestion 'REINTENTAR)) (setq seguir nil)))))
          (T
            ;; el nucleo va envuelto: pase lo que pase, la instancia PROPIA
            ;; de Excel se cierra (sin esto, un error dejaba un EXCEL
            ;; huerfano con el libro bloqueado -- visto 2026-08-17)
            (setq result (vl-catch-all-apply 'urb:ppto-run (list wb)))
            ;; red de seguridad: si algo broto ANTES de que urb:ppto-run
            ;; alcanzara a restaurar el modo de calculo (p.ej. error en la
            ;; escritura misma), nunca dejar el libro del usuario en
            ;; manual. -4105 = xlCalculationAutomatic. No-op si ya estaba.
            (vl-catch-all-apply
              '(lambda () (vlax-put-property app 'Calculation -4105)))
            (if propia
              (progn
                (vl-catch-all-apply
                  '(lambda () (vlax-invoke-method wb 'Close :vlax-false)))
                (vl-catch-all-apply '(lambda () (vlax-invoke-method app 'Quit)))
                (vlax-release-object wb)
                (vlax-release-object app) (gc) (gc)))
            (cond
              ((vl-catch-all-error-p result)
                (setq *urb-ppto-last-summary*
                  (list 'ERROR (vl-catch-all-error-message result)
                    'etapa (urb:safe-string *urb-ppto-stage* "?")))
                (prompt (strcat "\nERROR EN EXPORTACION: "
                  (vl-catch-all-error-message result)
                  " -- revise y reintente (el libro pudo quedar sin guardar)."))
                (if (not *urb-ppto-headless*)
                  (alert
                    (strcat "ERROR EN LA EXPORTACION (etapa: "
                      (urb:safe-string *urb-ppto-stage* "?") "):\n\n"
                      (vl-catch-all-error-message result)
                      "\n\nNo se dio por buena: el libro pudo quedar sin"
                      "\nguardar. Revise y reintente.")))
                (setq seguir nil))
              ;; pidio "Cambiar libro..." desde la vinculacion: pregunta el
              ;; archivo nuevo AQUI (c:PPTOEXPORTAR es quien controla el
              ;; ciclo de vida de Excel.Application, no urb:ppto-run) y
              ;; deja el bucle vivo para reintentar con la ruta nueva.
              ((equal result (list 'CAMBIAR-LIBRO-SOLICITADO))
                (setq nuevo
                  (getfiled "Seleccione el nuevo libro del presupuesto (Excel)"
                    (if (/= path "") path "") "xlsx;xlsm" 0))
                (if nuevo
                  (progn
                    (urb:ppto-config-write nuevo)
                    (prompt (strcat "\nLibro vinculado en este PC: " nuevo)))
                  (setq seguir nil)))
              ;; el libro se abrio bien pero no se reconocio ningun
              ;; presupuesto adentro (ni NIVEL ni por secciones): antes el
              ;; comando terminaba en silencio y el usuario quedaba SIN
              ;; ninguna ventana para corregirlo (visto en vivo 2026-08-19
              ;; con PEATONAL 3 Y 4.xlsx) -- ahora se abre la MISMA
              ;; ventana de gestion (Cambiar libro/Elegir hoja/
              ;; Desvincular/Reintentar) en vez de dejar al usuario sin
              ;; salida.
              ((and (listp result) (eq (car result) 'SIN-TABLA-O-VOCAB))
                (if *urb-ppto-headless*
                  (setq seguir nil)
                  (progn
                    (setq gestion
                      (urb:ppto-libro-gestionar
                        (if (eq (nth 2 result) 'sin-vocab)
                          "No se encontro presupuesto en este libro (ni con NIVEL ni por secciones DESCRIPCION/UM). Puede elegir la hoja correcta, cambiar de libro, o desvincular."
                          "No se pudo validar la tabla MEMORIAS/TablaMemorias de este libro. Puede cambiar de libro o desvincular.")))
                    (if (not (eq gestion 'REINTENTAR)) (setq seguir nil)))))
              (T (setq seguir nil))))))))
  (princ))

;; ---------- gestion VISIBLE del vinculo con el libro (2026-08-18) ----------
;; Pedido del usuario: "como se que presupuesto esta vinculado, en que hoja
;; o tabla esta... quiero ver todos esos datos y si quiero cambiar el libro
;; que me deje". PPTOLIBRO abre un dialogo que valida el libro configurado
;; en este PC y muestra: ruta, tabla de escritura, hoja del presupuesto con
;; su numero de actividades, y cuantas asignaciones/parametricas viven
;; guardadas dentro del libro. Desde ahi se cambia o desvincula.
;; Desvincular SOLO borra la ruta recordada en este PC (%APPDATA%): el
;; libro conserva intactos su tabla MEMORIAS, las asignaciones (hoja
;; URB_EQUIVALENCIAS) y las parametricas (URB_PARAMETRICAS).
(defun urb:ppto-libro-info (path / attach app wb propia lo filas vocab
                            equiv params lineas result)
  ;; valida ABRIENDO el libro (instancia propia oculta si hace falta) y
  ;; devuelve la lista de lineas de estado; nunca deja Excel huerfano
  (setq attach (urb:ppto-attach-excel path)
        app (nth 0 attach) wb (nth 1 attach) propia (nth 2 attach))
  (if (null wb)
    (list (strcat "PROBLEMA al abrir el libro: "
            (urb:safe-string (nth 2 attach) "?")))
    (progn
      (setq result
        (vl-catch-all-apply
          '(lambda ()
            (setq lo (urb:ppto-memorias-table wb))
            (setq filas
              (if lo
                (vl-catch-all-apply
                  '(lambda ()
                    (vlax-get-property
                      (vlax-get-property lo 'ListRows) 'Count)))
                nil))
            (if (vl-catch-all-error-p filas) (setq filas nil))
            (setq vocab (urb:ppto-read-vocab wb))
            (setq equiv (urb:ppto-equiv-read wb))
            (setq params (urb:ppto-param-read wb))
            (setq lineas
              (list
                (if lo
                  (strcat "Tabla de escritura: hoja MEMORIAS, tabla"
                    " TablaMemorias -- OK"
                    (if filas
                      (strcat " (" (itoa filas) " fila(s) exportadas hoy)")
                      ""))
                  "PROBLEMA: no se valido la tabla MEMORIAS/TablaMemorias (detalle en la linea de comandos).")
                (if vocab
                  (strcat "Presupuesto leido: hoja \""
                    (urb:safe-string *urb-ppto-vocab-hoja* "?")
                    "\" con " (itoa (length vocab))
                    " actividades (encabezados NIVEL/DESCRIPCION/UM).")
                  "PROBLEMA: ninguna hoja tiene encabezados NIVEL/DESCRIPCION/UM (no hay presupuesto que leer).")
                (strcat "Guardado dentro del libro: "
                  (itoa (length equiv)) " asignacion(es) manual(es) y "
                  (itoa (length params)) " parametrica(s).")))
            T)))
      (if propia
        (progn
          (vl-catch-all-apply
            '(lambda () (vlax-invoke-method wb 'Close :vlax-false)))
          (vl-catch-all-apply '(lambda () (vlax-invoke-method app 'Quit)))
          (vlax-release-object wb)
          (vlax-release-object app) (gc) (gc)))
      (if (vl-catch-all-error-p result)
        (list (strcat "PROBLEMA validando el libro: "
                (vl-catch-all-error-message result)))
        lineas))))

(defun urb:ppto-write-libro-dcl ()
  (urb:write-dialog-dcl
    "urb_ppto_libro"
    '*urb-ppto-libro-dcl-ok*
    (list
      "urb_ppto_libro : dialog { label = \"Presupuesto: libro vinculado\";"
      ": text { key = \"extra\"; width = 130; }"
      ": text { key = \"ruta\"; width = 130; }"
      ": text { key = \"l1\"; width = 130; }"
      ": text { key = \"l2\"; width = 130; }"
      ": text { key = \"l3\"; width = 130; }"
      ": text { label = \"Desvincular solo hace que este PC olvide la ruta: el libro conserva su tabla MEMORIAS,\"; }"
      ": text { label = \"las asignaciones y las parametricas (viven dentro del archivo y viajan con el).\"; }"
      ": text { label = \"El presupuesto se relee EN VIVO en cada exportacion: editar una fila (renombrar, cambiar UM) se refleja solo.\"; }"
      ": row { : button { key = \"cambiar\"; label = \"Cambiar libro...\"; } : button { key = \"hoja\"; label = \"Elegir hoja del presupuesto...\"; } : button { key = \"reintentar\"; label = \"Reintentar abrir\"; } : button { key = \"desvincular\"; label = \"Desvincular este PC\"; } }"
      "ok_cancel; }")))

;; extra: linea opcional arriba de todo (p.ej. el motivo por el que se llego
;; aqui -- un intento de exportacion fallido). nil/"" no la muestra.
(defun urb:ppto-libro-dialog (path lineas extra / dcl done dclfile)
  (setq done 0)
  (setq dclfile (urb:ppto-write-libro-dcl))
  (if (null dclfile)
    (alert "No se pudo preparar la ventana de gestion del libro (revise permisos de la carpeta temporal de Windows).")
    (progn
      (setq dcl (load_dialog dclfile))
      (if (and (> dcl 0) (new_dialog "urb_ppto_libro" dcl))
        (progn
          (set_tile "extra" (urb:safe-string extra ""))
          (set_tile "ruta"
            (if (= path "") "SIN LIBRO VINCULADO en este PC."
              (strcat "Libro: " path)))
          (set_tile "l1" (urb:safe-string (nth 0 lineas) ""))
          (set_tile "l2" (urb:safe-string (nth 1 lineas) ""))
          (set_tile "l3" (urb:safe-string (nth 2 lineas) ""))
          (action_tile "cambiar" "(done_dialog 2)")
          (action_tile "hoja" "(done_dialog 4)")
          (action_tile "desvincular" "(done_dialog 3)")
          (action_tile "reintentar" "(done_dialog 5)")
          (setq done (start_dialog))))
      (if (and dcl (> dcl 0)) (unload_dialog dcl))))
  done)

;; abre el libro (instancia propia si hace falta), deja elegir la hoja del
;; presupuesto entre las candidatas y GUARDA la eleccion en el propio
;; libro (Save explicito -- no depende de si el Close final guarda o no).
(defun urb:ppto-libro-elegir-hoja (path / attach app wb propia candidatas
                                   elegida result)
  (setq attach (urb:ppto-attach-excel path)
        app (nth 0 attach) wb (nth 1 attach) propia (nth 2 attach))
  (if (null wb)
    (alert (strcat "No se pudo abrir el libro:\n\n"
      (urb:safe-string (nth 2 attach) "?")))
    (progn
      (setq result
        (vl-catch-all-apply
          '(lambda ()
            (setq candidatas (urb:ppto-vocab-candidatas wb))
            (cond
              ((null candidatas)
                (alert "Ninguna hoja del libro tiene encabezados NIVEL/DESCRIPCION/UM arriba de la fila 15."))
              (T
                (setq elegida
                  (urb:ppto-elegir-hoja-dialog candidatas
                    (strcat "Hoja actual guardada: \""
                      (urb:safe-string
                        (urb:ppto-cfg-get wb "HOJA_PRESUPUESTO")
                        "(ninguna todavia)")
                      "\". Elija la hoja del presupuesto.")))
                (if elegida
                  (progn
                    (urb:ppto-cfg-set wb "HOJA_PRESUPUESTO" (car elegida))
                    (vl-catch-all-apply
                      '(lambda () (vlax-invoke-method wb 'Save)))))))
            T)))
      (if propia
        (progn
          (vl-catch-all-apply
            '(lambda () (vlax-invoke-method wb 'Close :vlax-false)))
          (vl-catch-all-apply '(lambda () (vlax-invoke-method app 'Quit)))
          (vlax-release-object wb)
          (vlax-release-object app) (gc) (gc)))
      (if (vl-catch-all-error-p result)
        (alert (strcat "PROBLEMA eligiendo la hoja:\n\n"
          (vl-catch-all-error-message result))))
      elegida)))

;; nucleo interactivo compartido entre PPTOLIBRO (standalone) y
;; PPTOEXPORTAR (cuando el libro no se pudo abrir): SIEMPRE deja al usuario
;; en una ventana con acciones -- nunca un mensaje sin salida (pedido
;; 2026-08-18: "independientemente que abra o no el archivo, quiero que
;; igual salga ese desplegable"). mensaje-extra (opcional) se muestra solo
;; en la primera vuelta, arriba de todo -- para explicar POR QUE se llego
;; aqui (p.ej. el error de un intento de exportacion fallido).
;; Devuelve 'REINTENTAR (el usuario cambio algo y hay que reintentar abrir
;; el libro), 'DESVINCULADO, o 'CERRADO (no hay nada mas que hacer).
(defun urb:ppto-libro-gestionar (mensaje-extra / path lineas done nuevo
                                 seguir resultado primera)
  (setq seguir T resultado 'CERRADO primera T)
  (while seguir
    (setq path (urb:ppto-config-read))
    (setq lineas
      (cond
        ((= path "")
          (list "Use \"Cambiar libro...\" para elegir el archivo de Excel del presupuesto." "" ""))
        ((null (findfile path))
          (list "PROBLEMA: el archivo configurado NO existe en esa ruta." "" ""))
        (T
          (prompt "\nValidando el libro (se abre un Excel oculto un momento)...")
          (urb:ppto-libro-info path))))
    (setq done
      (urb:ppto-libro-dialog path lineas (if primera mensaje-extra "")))
    (setq primera nil)
    (cond
      ((= done 2)
        (setq nuevo
          (getfiled "Seleccione el libro del presupuesto (Excel)"
            (if (/= path "") path "") "xlsx;xlsm" 0))
        (if nuevo
          (progn
            (urb:ppto-config-write nuevo)
            (prompt (strcat "\nLibro vinculado en este PC: " nuevo))))
        ;; el bucle reabre el dialogo mostrando la validacion del nuevo
        )
      ((= done 4)
        (if (and (/= path "") (findfile path))
          (progn
            (prompt "\nAbriendo el libro para elegir la hoja...")
            (urb:ppto-libro-elegir-hoja path))
          (alert "Primero vincule un libro (\"Cambiar libro...\").")))
      ((= done 5) (setq resultado 'REINTENTAR seguir nil))
      ((= done 3)
        (urb:ppto-config-write "")
        (prompt "\nLibro DESVINCULADO de este PC (el archivo no se toco).")
        (alert
          (strcat "Libro desvinculado de este PC."
            "\n\nEl archivo de Excel NO se modifico: conserva su tabla"
            "\nMEMORIAS, las asignaciones y las parametricas."
            "\nAl volver a vincularlo (o vincular otro libro) todo"
            "\nfunciona igual, porque eso vive dentro del archivo."))
        (setq resultado 'DESVINCULADO seguir nil))
      (T (setq seguir nil))))
  resultado)

(defun c:PPTOLIBRO ()
  (vl-load-com)
  (urb:ppto-libro-gestionar nil)
  (princ))

;; acceso directo al desvinculo desde la cinta (mismo efecto que el boton
;; "Desvincular este PC" de PPTOLIBRO, con la misma explicacion)
(defun c:PPTODESVINCULAR (/ path)
  (setq path (urb:ppto-config-read))
  (if (= path "")
    (alert "Este PC no tiene libro del presupuesto vinculado.")
    (progn
      (urb:ppto-config-write "")
      (prompt (strcat "\nLibro DESVINCULADO de este PC: " path))
      (alert
        (strcat "Libro desvinculado de este PC:\n" path
          "\n\nEl archivo de Excel NO se modifico: conserva su tabla"
          "\nMEMORIAS, las asignaciones y las parametricas."
          "\nAl volver a vincularlo todo funciona igual."))))
  (princ))

;; ---------- VINCULACION: boton propio (2026-08-19, pedido del usuario:
;; "que quede en un boton aparte a presupuesto... que me deje elegir el
;; archivo y la hoja... tambien una previsualizacion de como se veria el
;; presupuesto"). Aqui SOLO se prepara y revisa el vinculo; exportar
;; cantidades sigue siendo el boton Presupuesto (PPTOEXPORTAR). ----------
(defun urb:ppto-write-vinc-dcl ()
  (urb:write-dialog-dcl
    "urb_ppto_vinc"
    '*urb-ppto-vinc-dcl-ok*
    (list
      "urb_ppto_vinc : dialog { label = \"Vinculacion del presupuesto\";"
      ": text { key = \"ruta\"; width = 130; }"
      ": text { key = \"l1\"; width = 130; }"
      ": text { key = \"l2\"; width = 130; }"
      ": list_box { key = \"arbol\"; label = \"Previsualizacion: asi se leera el presupuesto (capitulos y actividades con su unidad)\"; width = 130; height = 20; }"
      ": row { : button { key = \"cambiar\"; label = \"Cambiar libro...\"; } : button { key = \"hoja\"; label = \"Elegir hoja...\"; } : button { key = \"desvincular\"; label = \"Desvincular este PC\"; } }"
      ": text { label = \"Aqui solo se prepara y revisa el vinculo; exportar cantidades es el boton Presupuesto.\"; }"
      "ok_cancel; }")))

;; arbol de previsualizacion SIN marcas de vinculo (urb:ppv-labels exige
;; *urb-ppto-matches* de una corrida de exportacion; aqui no hay corrida)
(defun urb:ppto-vinc-labels (/ o out)
  (setq out nil)
  (foreach o *urb-ppto-outline*
    (cond
      ((= (nth 0 o) 3)
        (setq out (cons (strcat "===== " (nth 2 o) " =====") out)))
      ((= (nth 0 o) 4)
        (setq out (cons (strcat "  " (nth 1 o) "  " (nth 2 o)) out)))
      (T
        (setq out
          (cons
            (strcat "      " (nth 1 o) "  " (nth 2 o) " [" (nth 3 o) "]")
            out)))))
  (reverse out))

;; abre el libro, valida la tabla, lee el vocabulario (puede preguntar la
;; hoja o la red si aplica) y arma la previsualizacion.
;; Devuelve (linea1 linea2 labels); nunca deja Excel huerfano.
(defun urb:ppto-vinc-info (path / attach app wb propia lo vocab labels
                           lineas result)
  (setq attach (urb:ppto-attach-excel path)
        app (nth 0 attach) wb (nth 1 attach) propia (nth 2 attach))
  (if (null wb)
    (list (strcat "PROBLEMA al abrir el libro: "
            (urb:safe-string (nth 2 attach) "?")) "" nil)
    (progn
      (setq result
        (vl-catch-all-apply
          '(lambda ()
            (setq lo (urb:ppto-memorias-table wb))
            (setq vocab (urb:ppto-read-vocab wb))
            (setq labels (if vocab (urb:ppto-vinc-labels) nil))
            (setq lineas
              (list
                (if lo
                  "Tabla de escritura: hoja MEMORIAS, tabla TablaMemorias -- OK."
                  "PROBLEMA: no se valido la tabla MEMORIAS (detalle en la linea de comandos).")
                (if vocab
                  (strcat "Presupuesto: hoja \""
                    (urb:safe-string *urb-ppto-vocab-hoja* "?") "\" -- "
                    (itoa (length vocab)) " actividades leidas.")
                  "PROBLEMA: no se reconocio presupuesto en el libro (use Elegir hoja, Elegir elemento-red o Cambiar libro).")))
            T)))
      (if propia
        (progn
          (vl-catch-all-apply
            '(lambda () (vlax-invoke-method wb 'Close :vlax-false)))
          (vl-catch-all-apply '(lambda () (vlax-invoke-method app 'Quit)))
          (vlax-release-object wb)
          (vlax-release-object app) (gc) (gc)))
      (if (vl-catch-all-error-p result)
        (list (strcat "PROBLEMA leyendo el libro: "
                (vl-catch-all-error-message result)) "" nil)
        (list (nth 0 lineas) (nth 1 lineas) labels)))))

(defun urb:ppto-vinc-dialog (path datos / dcl dclfile done lbl)
  (setq done 0)
  (setq dclfile (urb:ppto-write-vinc-dcl))
  (if (null dclfile)
    (alert "No se pudo preparar la ventana de vinculacion (revise permisos de la carpeta temporal de Windows).")
    (progn
      (setq dcl (load_dialog dclfile))
      (if (and dcl (> dcl 0) (new_dialog "urb_ppto_vinc" dcl))
        (progn
          (set_tile "ruta"
            (if (= path "") "SIN LIBRO VINCULADO en este PC."
              (strcat "Libro: " path)))
          (set_tile "l1" (urb:safe-string (nth 0 datos) ""))
          (set_tile "l2" (urb:safe-string (nth 1 datos) ""))
          (start_list "arbol")
          (if (nth 2 datos)
            (foreach lbl (nth 2 datos) (add_list lbl))
            (add_list "(sin presupuesto que previsualizar)"))
          (end_list)
          (action_tile "cambiar" "(done_dialog 2)")
          (action_tile "hoja" "(done_dialog 4)")
          (action_tile "desvincular" "(done_dialog 3)")
          (setq done (start_dialog))))
      (if (and dcl (> dcl 0)) (unload_dialog dcl))))
  done)

(defun c:PPTOVINCULAR (/ path datos done nuevo seguir)
  (vl-load-com)
  (setq seguir T)
  (while seguir
    (setq path (urb:ppto-config-read))
    (setq datos
      (cond
        ((= path "")
          (list "Use \"Cambiar libro...\" para elegir el archivo de Excel del presupuesto." "" nil))
        ((null (findfile path))
          (list "PROBLEMA: el archivo configurado NO existe en esa ruta." "" nil))
        (T
          (prompt "\nLeyendo el libro (se abre un Excel oculto un momento)...")
          (urb:ppto-vinc-info path))))
    (setq done (urb:ppto-vinc-dialog path datos))
    (cond
      ((= done 2)
        (setq nuevo
          (getfiled "Seleccione el libro del presupuesto (Excel)"
            (if (/= path "") path "") "xlsx;xlsm" 0))
        (if nuevo
          (progn
            (urb:ppto-config-write nuevo)
            (prompt (strcat "\nLibro vinculado en este PC: " nuevo)))))
      ((= done 4)
        (if (and (/= path "") (findfile path))
          (urb:ppto-libro-elegir-hoja path)
          (alert "Primero vincule un libro (\"Cambiar libro...\").")))
      ((= done 3)
        (urb:ppto-config-write "")
        (prompt "\nLibro DESVINCULADO de este PC (el archivo no se toco).")
        (alert
          (strcat "Libro desvinculado de este PC."
            "\n\nEl archivo de Excel NO se modifico: conserva su tabla"
            "\nMEMORIAS, las asignaciones y las parametricas."))
        (setq seguir nil))
      (T (setq seguir nil))))
  (princ))

(defun urb:unique-enames (entities / result ename)
  (foreach ename entities
    (if (and (urb:valid-ename-p ename) (not (member ename result)))
      (setq result (cons ename result))))
  (reverse result)
)

(defun urb:quantity-scope-command
  (/ selection entities index ename choice value updated)
  (prompt
    "\nSeleccione elementos cuantificables para incluir o excluir del presupuesto: ")
  (setq selection (ssget))
  (if selection
    (progn
      (setq entities
        (urb:unique-enames
          (append
            (urb:selected-roads selection)
            (urb:selected-anden-parents selection)
            (urb:selected-prefabs selection)
            (urb:selected-green-zones selection)
            (urb:selected-mp-entities selection))))
      ;; Si la seleccion no pertenece a una categoria conocida, no se marca:
      ;; evita aplicar alcance por accidente a textos o geometria auxiliar.
      (if entities
        (progn
          (initget "Incluir Excluir")
          (setq choice
            (getkword
              "\nEstado de cantidades [Incluir/Excluir] <Excluir>: "))
          (if (null choice) (setq choice "Excluir"))
          (setq value (if (= choice "Incluir") "SI" "NO"))
          (foreach ename entities
            (urb:set-xdata-strings ename "URB_Q_SCOPE" (list value))
            (setq updated (1+ (if updated updated 0))))
          (prompt
            (strcat "\nAlcance actualizado: " (itoa updated)
              " elemento(s) quedaron "
              (if (= value "SI") "incluidos." "excluidos."))))
        (prompt
          "\nLa seleccion no contiene vias, andenes, zonas verdes, prefabricados ni elementos de red reconocidos.")))
    (prompt "\nNo se seleccionaron elementos."))
  (princ)
)

;; ------------------------------------------------------------------
;; 2026-09-07 (pedido del usuario: "poder hacer tablas o esquemas como
;; los del plano"): CUADROS DE RED generados desde el MODELO como tablas
;; de AutoCAD (misma maquinaria vla-AddTable de la tabla de verificacion
;; de vias). Capa propia URB-CUADROS para prender/apagar.
(defun urb:cuadro-tabla-base (point titulo headers filas / table n cols
   th rh cw r c item)
  (urb:ensure-layer "URB-CUADROS" 4 T)
  (setq th (* 0.60 (max 0.20 (getvar "TEXTSIZE")))
        rh (* th 2.2)
        cw (* th 9.0)
        cols (length headers)
        n (+ 2 (length filas)))
  (setq table (vla-AddTable (urb:space) (vlax-3d-point point) n cols rh cw))
  (vla-put-Layer table "URB-CUADROS")
  (vla-put-Color table 256)
  (vl-catch-all-apply 'vla-put-RegenerateTableSuppressed (list table :vlax-true))
  (vl-catch-all-apply 'vla-MergeCells (list table 0 0 0 (1- cols)))
  (urb:set-table-text-safe table 0 0 titulo)
  (setq c 0)
  (foreach item headers
    (urb:set-table-text-safe table 1 c item)
    (setq c (1+ c)))
  (setq r 2)
  (foreach item filas
    (setq c 0)
    (foreach v item
      (urb:set-table-text-safe table r c (urb:safe-string v ""))
      (setq c (1+ c)))
    (setq r (1+ r)))
  (vl-catch-all-apply 'vla-put-RegenerateTableSuppressed (list table :vlax-false))
  (vl-catch-all-apply 'vla-RecomputeTableBlock (list table :vlax-true))
  table)

;; numero del ID para ordenar ("AC-102" -> 102; sin numero -> 999999)
(defun urb:cuadro-id-num (id / i c num)
  (setq num "" i 1)
  (while (<= i (strlen id))
    (setq c (substr id i 1))
    (if (vl-string-search c "0123456789") (setq num (strcat num c)))
    (setq i (1+ i)))
  (if (= num "") 999999 (atoi num)))

(defun urb:cuadro-accesorios (/ ss i en atts ed p filas point)
  (setq ss (ssget "_X" '((0 . "INSERT") (2 . "MP_PUNTO_ACC_ACU*"))) i 0 filas nil)
  (if (null ss)
    (prompt "\nNo hay accesorios de acueducto en el modelo.")
    (progn
      (while (< i (sslength ss))
        (setq en (ssname ss i)
              atts (mp:att-alist en)
              ed (entget en)
              p (cdr (assoc 10 ed)))
        (setq filas (cons
          (list (mp:getval "ID" atts "")
                (mp:acc-tipo-token (mp:getval "TIPO_ACCESORIO" atts ""))
                (mp:getval "DIAMETRO" atts "")
                (mp:getval "DIAMETRO_SALIDA" atts "")
                (mp:getval "MATERIAL" atts "")
                (rtos (car p) 2 2)
                (rtos (cadr p) 2 2))
          filas))
        (setq i (1+ i)))
      (setq filas (vl-sort filas
        '(lambda (a b) (< (urb:cuadro-id-num (car a))
                          (urb:cuadro-id-num (car b))))))
      (setq point (getpoint "\nPunto de insercion del cuadro: "))
      (if point
        (progn
          (urb:cuadro-tabla-base (trans point 1 0)
            (strcat "CUADRO DE ACCESORIOS - ACUEDUCTO ("
              (itoa (length filas)) ")")
            '("NODO" "TIPO" "D (pulg)" "D SALIDA" "MATERIAL" "ESTE" "NORTE")
            filas)
          (prompt (strcat "\nCuadro creado con " (itoa (length filas))
            " accesorios (capa URB-CUADROS.")))))))

(defun urb:cuadro-tramos-alc (patron red-label / ss i en atts filas point)
  (setq ss (ssget "_X" (list (cons 0 "INSERT") (cons 2 patron))) i 0 filas nil)
  (if (null ss)
    (prompt (strcat "\nNo hay tramos de " red-label " en el modelo."))
    (progn
      (while (< i (sslength ss))
        (setq en (ssname ss i)
              atts (mp:att-alist en))
        (setq filas (cons
          (list (mp:getval "POZO_INI" atts "")
                (mp:getval "POZO_FIN" atts "")
                (mp:getval "LONGITUD" atts "")
                (mp:getval "COTA_CLAVE_INI" atts "")
                (mp:getval "COTA_CLAVE_FIN" atts "")
                (mp:getval "PENDIENTE_CALCULADA" atts
                  (mp:getval "PENDIENTE" atts ""))
                (mp:getval "DIAMETRO" atts "")
                (mp:getval "MATERIAL" atts ""))
          filas))
        (setq i (1+ i)))
      (setq filas (vl-sort filas
        '(lambda (a b) (< (urb:cuadro-id-num (car a))
                          (urb:cuadro-id-num (car b))))))
      (setq point (getpoint "\nPunto de insercion del cuadro: "))
      (if point
        (progn
          (urb:cuadro-tabla-base (trans point 1 0)
            (strcat "CUADRO DE TRAMOS - " red-label " ("
              (itoa (length filas)) ")")
            '("POZO INI" "POZO FIN" "LONG (m)" "CLAVE INI" "CLAVE FIN"
              "PEND (%)" "D (pulg)" "MATERIAL")
            filas)
          (prompt (strcat "\nCuadro creado con " (itoa (length filas))
            " tramos (capa URB-CUADROS).")))))))

(defun urb:cuadro-pozos (/ ss i en atts bname filas point red)
  (setq ss (ssget "_X" '((0 . "INSERT")
             (2 . "MP_PUNTO_POZO_SAN,MP_PUNTO_POZO_PLU"))) i 0 filas nil)
  (if (null ss)
    (prompt "\nNo hay pozos en el modelo.")
    (progn
      (while (< i (sslength ss))
        (setq en (ssname ss i)
              atts (mp:att-alist en)
              bname (strcase (vla-get-EffectiveName
                (vlax-ename->vla-object en))))
        (setq red (if (vl-string-search "_PLU" bname) "PLUVIAL" "SANITARIO"))
        (setq filas (cons
          (list (mp:getval "ID" atts "")
                red
                (mp:getval "COTA_TN_INI" atts "")
                (mp:getval "COTA_CLAVE_INI" atts "")
                (mp:getval "PROFUNDIDAD" atts "")
                (mp:getval "DIAMETRO" atts ""))
          filas))
        (setq i (1+ i)))
      (setq filas (vl-sort filas
        '(lambda (a b) (< (urb:cuadro-id-num (car a))
                          (urb:cuadro-id-num (car b))))))
      (setq point (getpoint "\nPunto de insercion del cuadro: "))
      (if point
        (progn
          (urb:cuadro-tabla-base (trans point 1 0)
            (strcat "CUADRO DE POZOS DE ALCANTARILLADO ("
              (itoa (length filas)) ")")
            '("POZO" "RED" "COTA TAPA" "COTA CLAVE" "PROF (m)" "D (pulg)")
            filas)
          (prompt (strcat "\nCuadro creado con " (itoa (length filas))
            " pozos (capa URB-CUADROS).")))))))

(defun urb:cuadros-red-command (/ kw)
  (initget "Accesorios TramosSanitario TramosPluvial TramosAcueducto Pozos")
  (setq kw (getkword (strcat "\nCuadro a generar "
    "[Accesorios/TramosSanitario/TramosPluvial/TramosAcueducto/Pozos]"
    " <Accesorios>: ")))
  (if (null kw) (setq kw "Accesorios"))
  (cond
    ((= kw "Accesorios") (urb:cuadro-accesorios))
    ((= kw "TramosSanitario")
      (urb:cuadro-tramos-alc "MP_TRAMO_SAN_*" "ALC. SANITARIO"))
    ((= kw "TramosPluvial")
      (urb:cuadro-tramos-alc "MP_TRAMO_PLU_*" "ALC. PLUVIAL"))
    ((= kw "TramosAcueducto")
      (urb:cuadro-tramos-alc "MP_TRAMO_ACU_*" "ACUEDUCTO"))
    ((= kw "Pozos") (urb:cuadro-pozos)))
  (princ))

;; PERFIL ESQUEMATICO del movimiento de tierras de una via (2026-09-07,
;; pedido del usuario: "un corte como el de redes"): TN vs rasante vs
;; fondo de estructura a lo largo de la via, con exageracion vertical,
;; leido de las filas YA CALCULADAS de la verificacion (URB_VIA_AUDIT --
;; si no existen, correr primero Memoria de via). Capa URB-VIA-PERFIL.
(defun urb:via-perfil-esquema-command (/ sel be ldat audit rows point exv
   base-z s0 z0 pts-tn pts-ras pts-fon row st tn ras fon x fila minz maxz
   ln tx last-st paso)
  (setq sel (entsel "\nSeleccione la VIA (su bloque): "))
  (if (null sel)
    (prompt "\nNada seleccionado.")
    (progn
      (setq be (urb:road-parent-from-entity (car sel)))
      (if (null be) (setq be (car sel)))
      (setq ldat (vl-catch-all-apply 'vlax-ldata-get
        (list be "URB_VIA_AUDIT")))
      (if (or (vl-catch-all-error-p ldat) (null ldat))
        (prompt (strcat "\nEsta via no tiene la verificacion calculada -- "
          "corra primero URBANISMO > Cantidades > Memoria de via."))
        (progn
          (setq audit (car ldat))
          (setq point (getpoint "\nPunto de insercion del perfil: "))
          (if point
            (progn
              (setq point (trans point 1 0))
              (setq exv 5.0)  ;; exageracion vertical 5x (H 1:1)
              ;; base: cota minima redondeada hacia abajo
              (setq minz nil maxz nil)
              (foreach row audit
                (foreach v (list (nth 1 row) (nth 2 row) (nth 3 row))
                  (if (numberp v)
                    (progn
                      (if (or (null minz) (< v minz)) (setq minz v))
                      (if (or (null maxz) (> v maxz)) (setq maxz v))))))
              (setq base-z (- (float (fix minz)) 1.0))
              (urb:ensure-layer "URB-VIA-PERFIL" 4 T)
              (setq pts-tn nil pts-ras nil pts-fon nil last-st 0.0)
              (foreach row audit
                (setq st (nth 0 row) tn (nth 1 row)
                      ras (nth 2 row) fon (nth 3 row))
                (setq x (+ (car point) st) last-st st)
                (if (numberp tn)
                  (setq pts-tn (cons (list x (+ (cadr point)
                    (* exv (- tn base-z)))) pts-tn)))
                (if (numberp ras)
                  (setq pts-ras (cons (list x (+ (cadr point)
                    (* exv (- ras base-z)))) pts-ras)))
                (if (numberp fon)
                  (setq pts-fon (cons (list x (+ (cadr point)
                    (* exv (- fon base-z)))) pts-fon))))
              ;; polilineas: TN verde, rasante roja, fondo amarilla
              (foreach fila (list (list pts-tn 3) (list pts-ras 1)
                                  (list pts-fon 2))
                (if (> (length (car fila)) 1)
                  (progn
                    (entmake (append
                      (list '(0 . "LWPOLYLINE") '(100 . "AcDbEntity")
                            (cons 8 "URB-VIA-PERFIL")
                            (cons 62 (cadr fila))
                            '(100 . "AcDbPolyline")
                            (cons 90 (length (car fila))) '(70 . 0))
                      (mapcar '(lambda (p) (cons 10 p))
                        (reverse (car fila))))))))
              ;; reticula: linea base + verticales cada 20 m con abscisa,
              ;; y cotas de referencia cada 1 m (exageradas)
              (entmake (list '(0 . "LINE") (cons 8 "URB-VIA-PERFIL")
                (cons 62 8)
                (cons 10 (list (car point) (cadr point) 0.0))
                (cons 11 (list (+ (car point) last-st) (cadr point) 0.0))))
              (setq st 0.0)
              (while (<= st (+ last-st 0.01))
                (entmake (list '(0 . "LINE") (cons 8 "URB-VIA-PERFIL")
                  (cons 62 8)
                  (cons 10 (list (+ (car point) st) (cadr point) 0.0))
                  (cons 11 (list (+ (car point) st)
                    (+ (cadr point) (* exv (- (+ maxz 0.5) base-z))) 0.0))))
                (entmake (list '(0 . "TEXT") (cons 8 "URB-VIA-PERFIL")
                  (cons 62 8)
                  (cons 10 (list (+ (car point) st)
                    (- (cadr point) 1.2) 0.0))
                  (cons 40 0.6) (cons 50 (/ pi 2.0))
                  (cons 1 (urb:format-station st))))
                (setq st (+ st 20.0)))
              (setq z0 (float (fix minz)) paso 1.0)
              (while (<= z0 (+ maxz 0.5))
                (entmake (list '(0 . "TEXT") (cons 8 "URB-VIA-PERFIL")
                  (cons 62 8)
                  (cons 10 (list (- (car point) 4.0)
                    (+ (cadr point) (* exv (- z0 base-z))) 0.0))
                  (cons 40 0.6) (cons 1 (rtos z0 2 0))))
                (setq z0 (+ z0 paso)))
              (entmake (list '(0 . "TEXT") (cons 8 "URB-VIA-PERFIL")
                (cons 62 4)
                (cons 10 (list (car point)
                  (+ (cadr point) (* exv (- (+ maxz 1.2) base-z))) 0.0))
                (cons 40 1.0)
                (cons 1 (strcat "PERFIL MT VIA | TN=verde Rasante=rojo "
                  "Fondo estr.=amarillo | V x" (rtos exv 2 0)))))
              (prompt (strcat "\nPerfil esquematico creado ("
                (itoa (length audit)) " estaciones, capa URB-VIA-PERFIL)."))))))))
  (princ))

;; v4.73.0 -- Diagnostico y consulta sin recalcular ni escribir el dibujo.
(defun urb:q-integrity-controls (records / result record handle seen key)
  (foreach record records
    (setq handle (nth 8 record))
    (cond
      ((or (not (numberp (nth 7 record))) (< (nth 7 record) -1e-9))
        (setq result (cons (urb:q-control-row "ALTA" (nth 0 record) handle
          (nth 2 record) "Cantidad negativa o no numerica."
          "Revisar geometria, datos y memoria antes de exportar.") result)))
      ((not (urb:q-approved-status-p (nth 9 record)))
        (setq key (list handle (nth 9 record)))
        (if (not (member key seen))
          (progn
            (setq seen (cons key seen))
            (setq result (cons (urb:q-control-row "ALTA" (nth 0 record) handle
              (nth 2 record) (strcat "Cantidad sin aprobar: " (nth 9 record))
              "Revisar el elemento con EDITAR y consultar su memoria.") result)))))))
  (reverse result))

(defun urb:q-collect-readonly
  (/ anden via prefab green network records controls duplicates)
  (setq anden (urb:q-collect-andenes)
        via (urb:q-collect-vias)
        prefab (urb:q-collect-prefabricados)
        green (urb:q-collect-green-zones)
        network (urb:q-collect-networks)
        records (append (nth 0 anden) (nth 0 via) (nth 0 prefab)
                        (nth 0 green) (nth 0 network))
        controls (append (nth 2 anden) (nth 2 via) (nth 2 prefab)
                         (nth 2 green) (nth 4 network) (urb:q-scope-controls))
        duplicates (urb:q-duplicate-road-id-controls records)
        records (nth 0 duplicates)
        controls (append controls (nth 1 duplicates) (urb:q-integrity-controls records)))
  (list records controls))

(defun urb:q-report-dialog (title rows / filename dcl result index row running *error*)
  ;; Fila = severidad, categoria, handle, elemento, hallazgo, accion.
  (defun *error* (msg)
    (if dcl (unload_dialog dcl))
    (if filename (vl-file-delete filename))
    (if msg (prompt (strcat "\nConsulta: " msg))) (princ))
  (setq filename (urb:temp-file "urb_diagnostico" ".dcl"))
  (if (urb:write-lines filename
    '("urb_report : dialog { label = \"Revision de cantidades\";"
      ": text { key = \"titulo\"; width = 100; }"
      ": text { label = \"Estado | Grupo | Handle | Elemento | Hallazgo\"; }"
      ": list_box { key = \"filas\"; width = 110; height = 23; }"
      ": row { : button { key = \"detalle\"; label = \"Ver detalle\"; }"
      ": button { key = \"localizar\"; label = \"Seleccionar objeto y cerrar\"; }"
      ": button { key = \"cancel\"; label = \"Cerrar\"; is_cancel = true; } } }"))
    (progn
      (setq dcl (load_dialog filename) running T index 0)
      (while (and running (>= dcl 0) (new_dialog "urb_report" dcl))
        (set_tile "titulo" title)
        (start_list "filas")
        (foreach row rows
          (add_list (strcat (nth 0 row) " | " (nth 1 row) " | " (nth 2 row)
                     " | " (nth 3 row) " | " (nth 4 row))))
        (end_list)
        (if rows (set_tile "filas" (itoa index))
          (progn (mode_tile "detalle" 1) (mode_tile "localizar" 1)))
        (action_tile "filas" "(setq index (atoi $value))")
        (action_tile "detalle" "(done_dialog 2)")
        (action_tile "localizar" "(done_dialog 3)")
        (action_tile "cancel" "(done_dialog 0)")
        (setq result (start_dialog) row (if rows (nth index rows) nil))
        (cond
          ((and (= result 2) row)
            (alert (strcat (nth 3 row) "\nHandle: " (nth 2 row) "\n\n"
                     (nth 4 row) "\n\n" (nth 5 row))))
          ((and (= result 3) row)
            (if (and (/= (nth 2 row) "") (handent (nth 2 row)))
              (progn (sssetfirst nil (ssadd (handent (nth 2 row))))
                     (setq running nil))
              (alert "El registro no tiene un objeto seleccionable en este dibujo.")))
          (T (setq running nil))))
      (if (>= dcl 0) (unload_dialog dcl))
      (setq dcl nil)))
  (if filename (vl-file-delete filename))
  (princ))

(defun urb:q-diagnostic-command (/ result records controls)
  (prompt "\nRevisando cantidades guardadas (sin recalcular)...")
  (setq result (vl-catch-all-apply 'urb:q-collect-readonly nil))
  (if (vl-catch-all-error-p result)
    (alert (strcat "No se pudo completar el diagnostico. No se modificaron cantidades.\n"
             (vl-catch-all-error-message result)))
    (progn
      (setq records (car result) controls (cadr result))
      (urb:q-report-dialog
        (strcat "Motor " *urb-version* " | " (itoa (length records)) " cantidades | "
          (itoa (urb:q-approved-record-count records)) " aprobadas | "
          (itoa (length controls)) " observaciones. No evalua correspondencia con Excel.")
        controls)))
  (princ))

(defun urb:q-trace-command
  (/ picked en handle result rows record pair audit data previous-filter)
  (if (setq picked (entsel "\nSeleccione el bloque del elemento para consultar sus cantidades: "))
    (progn
      (setq en (car picked) handle (urb:q-handle en)
            previous-filter *urb-q-only-ename*
            *urb-q-only-ename* en
            result (vl-catch-all-apply 'urb:q-collect-readonly nil)
            *urb-q-only-ename* previous-filter)
      (if (vl-catch-all-error-p result)
        (alert (strcat "Consulta incompleta: " (vl-catch-all-error-message result)))
        (progn
          (foreach record (car result)
            (if (= handle (nth 8 record))
              (setq rows (cons (urb:q-control-row (nth 9 record) (nth 0 record) handle
                (nth 2 record) (strcat (rtos (nth 7 record) 2 6) " " (nth 6 record))
                (strcat "Especificacion: " (nth 3 record) "\nEtapa/subetapa: "
                  (nth 4 record) "/" (nth 5 record) "\nReferencia: " (nth 10 record)
                  " " (nth 11 record))) rows))))
          (setq data (mp:read-cant-data en))
          (if (mp:cant-patch-valid-p data)
            (foreach pair data
              (setq rows (cons (urb:q-control-row "DATO" "Red" handle (car pair)
                (mp:safe-str (cdr pair)) "Valor guardado del elemento; no se ha recalculado.") rows))))
          (setq audit (urb:get-xdata-strings en "URB_DATA_AUDIT"))
          (if audit
            (setq rows (cons (urb:q-control-row "INFO" "Ultima escritura" handle
              (strcat "Motor " (nth 1 audit)) (nth 2 audit)
              "Fecha local en formato AAAAMMDD.HHMMSS. Es una escritura de datos, no una certificacion de calculo.") rows)))
          (urb:q-report-dialog (strcat "Consulta del elemento " handle " | motor " *urb-version*)
            (reverse rows))))))
  (princ))

(defun urb:quality-selftests (/ merged negative zero)
  ;; Autoprueba pura y repetible; no crea entidades ni abre Excel.
  (setq merged (mp:cant-merge '(("ID" . "A") ("OCULTO" . "123"))
                            '(("id" . "B")))
        negative (urb:q-record "TEST" "" "X" "" "1" "1" "M3" -5 "" "OK" "" "")
        zero (urb:q-record "TEST" "" "X" "" "1" "1" "M3" 0 "" "OK" "" ""))
  (list
    (list "Parche conserva campos ocultos" (equal (cdr (assoc "OCULTO" merged)) "123"))
    (list "Parche normaliza claves" (equal (cdr (assoc "ID" merged)) "B"))
    (list "Parche permite vaciado explicito"
      (equal (cdr (assoc "ID" (mp:cant-merge merged '(("ID" . ""))))) ""))
    (list "Rechaza datos mal formados" (not (mp:cant-patch-valid-p '(("ID" "valor")))))
    (list "Rechaza lista punteada" (not (mp:cant-patch-valid-p '(("ID" . "A") . "B"))))
    (list "Acepta parche vacio" (mp:cant-patch-valid-p nil))
    (list "Cantidad negativa bloqueada" (not (urb:q-approved-status-p (nth 9 negative))))
    (list "Cantidad cero permitida" (urb:q-approved-status-p (nth 9 zero)))
    (list "Diagnostico detecta negativo" (= 1 (length (urb:q-integrity-controls (list negative)))))
    (list "Cama: espesor minimo" (equal 0.1 (mp:pipe-bedding-thickness 0.2) 1e-9))
    (list "Cama: espesor intermedio" (equal 0.125 (mp:pipe-bedding-thickness 0.5) 1e-9))
    (list "Cama: espesor maximo" (equal 0.15 (mp:pipe-bedding-thickness 1.0) 1e-9))
    (list "Volumen de zanja constante" (equal 20.0 (mp:integrate-trench-volume '(2.0 2.0 2.0) 10.0 1.0) 1e-9))
    (list "Volumen de zanja variable" (equal 25.0 (mp:integrate-trench-volume '(1.0 3.0 3.0) 10.0 1.0) 1e-9))
    (list "Prefab legado sardinel conserva VIA"
      (= (urb:prefab-destino-red "" "Sardinel") "VIA"))
    (list "Prefab bordillo puede ir a VIA"
      (= (urb:prefab-destino-red "Via" "Bordillo") "VIA"))
    (list "Prefab bordillo puede ir a ANDEN"
      (= (urb:prefab-destino-red "Anden" "Bordillo") "ANDEN"))
    (list "Rampa vehicular va a su capitulo"
      (= (urb:rampa-red "RAMPA-VEHICULAR") "RAMPA-VEHICULAR"))
    (list "Paso peatonal va a su capitulo"
      (= (urb:rampa-red "PASO-PEATONAL") "PASO-PEATONAL"))
    (list "Tipologias de areas son las tres solicitadas"
      (equal *urb-elem-categorias*
        '("Andenes" "Senderos" "Equipamientos")))
    (list "Entrante de contenedor se reconoce como vacio concavo"
      (and
        (urb:polygon-concave-p
          '((0.0 0.0) (4.0 0.0) (4.0 4.0)
            (2.0 4.0) (2.0 2.0) (0.0 2.0)))
        (not (urb:polygon-concave-p
          '((0.0 0.0) (4.0 0.0) (4.0 2.0) (0.0 2.0))))))
    ;; 2026-09-08: con un ENTRANTE alrededor de un contenedor, las dos
    ;; aristas del entrante (1,0 m) son mas cortas que las puntas reales
    ;; del anden (2,0 m). La heuristica vieja las tomaba por puntas y
    ;; dejaba el fondo del entrante como prefabricado suelto (segmentos
    ;; 4 y 5); las puntas correctas son la 1 (x=20) y la 7 (x=0).
    (list "Puntas del anden se eligen por extremo, no por longitud"
      (and
        (equal '(7 1)
          (urb:costado-tip-segments
            '((0.0 0.0 0.0) (20.0 0.0 0.0) (20.0 2.0 0.0)
              (11.5 2.0 0.0) (11.5 1.0 0.0) (10.0 1.0 0.0)
              (10.0 2.0 0.0) (0.0 2.0 0.0))
            0.0))
        ;; rectangulo simple: mismo resultado que la heuristica anterior
        (equal '(3 1)
          (urb:costado-tip-segments
            '((0.0 0.0 0.0) (20.0 0.0 0.0) (20.0 2.0 0.0) (0.0 2.0 0.0))
            0.0))
        ;; sin eje dominante cae al respaldo por longitud y sigue vivo
        (urb:costado-tip-segments
          '((0.0 0.0 0.0) (20.0 0.0 0.0) (20.0 2.0 0.0) (0.0 2.0 0.0))
          nil)))
    ;; 2026-09-12: editar una via con "Textos por capa" volvia a pedir el
    ;; texto de cota siempre; si el clic no caia en un TEXT/MTEXT exacto,
    ;; el auto-detect tumbaba la edicion al flujo de PENDIENTE.
    (list "Editar una via por capa reusa la capa guardada"
      (and (urb:road-cota-capa-reusable-p
             "Textos por capa" "Textos por capa" "COTAS VIA|V-NODE-TEXT")
           ;; sin capa guardada si hay que preguntarla
           (not (urb:road-cota-capa-reusable-p
                  "Textos por capa" "Textos por capa" ""))
           ;; y tambien si el metodo viene de Pendiente
           (not (urb:road-cota-capa-reusable-p
                  "Textos por capa" "Pendiente" "COTAS VIA"))
           ;; con el metodo Pendiente no se reusa nada
           (not (urb:road-cota-capa-reusable-p
                  "Pendiente" "Textos por capa" "COTAS VIA"))))
    ;; 2026-09-12 (plano real): un anden que gira 23 grados en 190 m no se
    ;; puede modular con un solo eje -- las losetas del final quedan
    ;; torcidas. Se mide el giro del costado y, si es un corredor largo que
    ;; gira, se modula por tramos rectos.
    (list "Se detecta cuando el costado del anden gira"
      (and
        ;; costado recto: no gira
        (equal 0.0
          (urb:chain-direction-drift
            '((0.0 0.0 0.0) (10.0 0.0 0.0) (20.0 0.0 0.0))) 1e-9)
        ;; costado en L: gira 90 grados
        (equal (* 0.5 pi)
          (urb:chain-direction-drift
            '((0.0 0.0 0.0) (10.0 0.0 0.0) (10.0 10.0 0.0))) 1e-9)
        ;; recto largo: NO se modula por tramos
        (not (urb:anden-needs-segmented-p
               '((0.0 0.0 0.0) (30.0 0.0 0.0) (60.0 0.0 0.0))))
        ;; 2026-09-13: tambien los cortos deben respetar el eje local.
        (urb:anden-needs-segmented-p
               '((0.0 0.0 0.0) (5.0 0.0 0.0) (5.0 5.0 0.0)))
        ;; Curva S: mismo rumbo inicial/final no implica costado recto.
        (urb:anden-needs-segmented-p
               '((0.0 0.0) (20.0 0.0) (30.0 10.0) (40.0 0.0) (60.0 0.0)))
        ;; largo y girando: SI
        (urb:anden-needs-segmented-p
          '((0.0 0.0 0.0) (30.0 0.0 0.0) (60.0 0.0 0.0) (90.0 30.0 0.0)))))
    ;; 2026-09-21 (foto: anden visualmente recto con una cuna diagonal en
    ;; 0+145): un remate residual de centimetros no puede convertir todo el
    ;; material en dos orientaciones. El quiebre sostenido si debe hacerlo.
    (list "Un remate corto no parte un anden recto"
      (and
        (not
          (urb:anden-needs-segmented-p
            '((0.0 0.0 0.0) (99.596 0.0 0.0)
              (99.627 0.0065 0.0))))
        (< (urb:chain-off-axis-length
             '((0.0 0.0 0.0) (99.596 0.0 0.0)
               (99.627 0.0065 0.0))
             (* pi (/ 2.0 180.0)))
           0.04)
        (urb:anden-needs-segmented-p
          '((0.0 0.0 0.0) (50.0 0.0 0.0)
            (55.0 2.0 0.0) (80.0 12.0 0.0)))))
    (list "La fase de una cuna usa su extension real"
      (and
        ;; La cuna empieza 10 cm antes de la cuerda: su fase tambien.
        (equal '(nil -0.1)
          (urb:segment-phase-info 0.0 10.0 -0.1 10.1 0.0 20.0 nil)
          1e-9)
        ;; La misma geometria recorrida de derecha a izquierda invierte
        ;; el barrido local, pero conserva la estacion fisica -0.1.
        (equal '(T -0.1)
          (urb:segment-phase-info 20.0 10.0 9.9 20.1 0.0 20.0 nil)
          1e-9)
        ;; Invertir el patron conserva el extremo global de referencia.
        (equal '(T 9.9)
          (urb:segment-phase-info 0.0 10.0 -0.1 10.1 0.0 20.0 T)
          1e-9)))
    ;; 2026-09-12: un arco muestreado fino se reduce a pocos TRAMOS RECTOS,
    ;; para que el material no quede en abanico continuo (lo que el usuario
    ;; rechazo el 2026-08-09) ni torcido al final.
    (list "Un arco fino se simplifica a pocos tramos rectos"
      ((lambda (/ arco k simple)
        ;; cuarto de circulo de radio 20 muestreado cada ~2 grados
        (setq arco nil k 0)
        (repeat 46
          (setq arco
            (cons (list (* 20.0 (cos (* k (/ pi 90.0))))
                        (* 20.0 (sin (* k (/ pi 90.0)))) 0.0)
                  arco))
          (setq k (1+ k)))
        (setq arco (reverse arco))
        (setq simple (urb:chain-simplify-by-direction arco (* pi (/ 5.0 180.0))))
        (and
          ;; 5 grados contra tangente, no contra cuerda acumulada (~10).
          ;; En este muestreo de 2 grados resultan 16 vertices.
          (= (length simple) 16)
          (> (length simple) 2)
          ;; los extremos se conservan
          (equal (car arco) (car simple) 1e-6)
          (equal (last arco) (last simple) 1e-6)))))
    ;; 2026-09-12: el simbolo que se pasa del centro de un arco apretado
    ;; (radio menor que la distancia perpendicular a la que va la franja)
    ;; NO se dibuja: apilados, esos simbolos forman el disco que el usuario
    ;; vio como "un circulo" en las curvas.
    (list "Un simbolo fuera del anden no se dibuja"
      ((lambda (contorno / dentro fuera)
        (setq dentro (urb:point-in-region-polygons-p '(0.5 0.5) (list contorno)))
        (setq fuera (urb:point-in-region-polygons-p '(5.0 5.0) (list contorno)))
        (and dentro (not fuera)))
        '((0.0 0.0) (2.0 0.0) (2.0 2.0) (0.0 2.0))))
    ;; 2026-09-12: en un anden LARGO la cadena guia (la que marca por
    ;; donde corren la guia y el toperol) salia siendo una TAPA de
    ;; extremo. La tapa mide el ancho del anden (1,5 m) y pasaba el
    ;; filtro fijo de 0,5 m, y como la cercania al clic se medía con el
    ;; PUNTO MEDIO de la cadena, en 60 m de costado el medio quedaba a
    ;; 30 m del clic y la tapa ganaba. Con 1 sola arista el motor no
    ;; entraba a la ruta de offset y el toperol quedaba en una esquina.
    (list "La cadena guia es el costado largo, no la tapa del extremo"
      ((lambda (anillo clic / prev-pt prev-anchor prev-ch cadena)
        (setq prev-pt *urb-current-tactile-side-point*
              prev-anchor *urb-current-tactile-side-anchor*
              prev-ch *urb-current-tactile-side-choice*)
        (setq *urb-current-tactile-side-choice* nil)
        (setq *urb-current-tactile-side-point* clic
              *urb-current-tactile-side-anchor* nil)
        (setq cadena (urb:anden-tactile-chain anillo))
        (setq *urb-current-tactile-side-point* prev-pt
              *urb-current-tactile-side-anchor* prev-anchor)
        (setq *urb-current-tactile-side-choice* prev-ch)
        (and cadena
             ;; el costado (60 m), no la tapa (1,5 m)
             (equal 60.0 (urb:chain-total-length cadena) 0.01)
             ;; y con sus vertices intermedios, que es lo que necesita la
             ;; ruta de offset: con 1 sola arista se cae a la proyeccion
             (> (length (urb:open-chain-edges cadena)) 1)))
        '((0.0 0.0 0.0) (30.0 0.0 0.0) (60.0 0.0 0.0)
          (60.0 1.5 0.0) (30.0 1.5 0.0) (0.0 1.5 0.0))
        '(2.0 -3.0)))
    ;; 2026-09-08: alrededor del contenedor no va prefabricado. El
    ;; costado del lado con entrante (22 m) se parte en 10,0 m + 7,8 m:
    ;; se quitan los 2,2 m que ocupa el contenedor sobre el borde, tanto
    ;; el tramo que entra al hueco como el que corre TANGENTE a su cara.
    (list "El costado se interrumpe en el contenedor"
      ((lambda (tramos)
        (and (= (length tramos) 2)
             (equal 7.8 (urb:poly-chain-length (car tramos)) 0.01)
             (equal 10.0 (urb:poly-chain-length (cadr tramos)) 0.01)))
        (urb:chain-split-por-poligonos
          '((20.0 2.0 0.0) (11.5 2.0 0.0) (11.5 1.0 0.0)
            (10.0 1.0 0.0) (10.0 2.0 0.0) (0.0 2.0 0.0))
          '(((10.0 0.8) (12.2 0.8) (12.2 2.0) (10.0 2.0))))))
    (list "Sin contenedores el costado queda entero"
      ((lambda (tramos)
        (and (= (length tramos) 1)
             (equal 22.0 (urb:poly-chain-length (car tramos)) 0.01)))
        (urb:chain-split-por-poligonos
          '((20.0 2.0 0.0) (11.5 2.0 0.0) (11.5 1.0 0.0)
            (10.0 1.0 0.0) (10.0 2.0 0.0) (0.0 2.0 0.0))
          nil)))
    ;; 2026-09-08: el contorno del anden se sustituye por el borde de la
    ;; region ya recortada. Los trozos salen de vla-Explode sueltos y en
    ;; cualquier sentido; hay que volver a encadenarlos en un bucle unico.
    (list "Los trozos sueltos de la region vuelven a ser un bucle"
      ((lambda (loops)
        (and (= 1 (length loops))
             (= 4 (length (car loops)))
             (equal 8.0 (abs (urb:loop-signed-area (car loops))) 1e-9)))
        (urb:chain-loops-from-segments
          '(((0.0 0.0 0.0) (4.0 0.0 0.0) 0.0)
            ((4.0 2.0 0.0) (4.0 0.0 0.0) 0.0)
            ((4.0 2.0 0.0) (0.0 2.0 0.0) 0.0)
            ((0.0 0.0 0.0) (0.0 2.0 0.0) 0.0))
          1e-6)))
    (list "Con dos bucles se queda el mayor"
      ((lambda (loops)
        (and (= 2 (length loops))
             (equal 8.0
               (apply 'max
                 (mapcar '(lambda (l) (abs (urb:loop-signed-area l))) loops))
               1e-9)))
        (urb:chain-loops-from-segments
          '(((0.0 0.0 0.0) (4.0 0.0 0.0) 0.0)
            ((4.0 0.0 0.0) (4.0 2.0 0.0) 0.0)
            ((4.0 2.0 0.0) (0.0 2.0 0.0) 0.0)
            ((0.0 2.0 0.0) (0.0 0.0 0.0) 0.0)
            ((9.0 0.0 0.0) (10.0 0.0 0.0) 0.0)
            ((10.0 0.0 0.0) (10.0 1.0 0.0) 0.0)
            ((10.0 1.0 0.0) (9.0 0.0 0.0) 0.0))
          1e-6)))
    ;; al invertir el sentido, el arco tiene que seguir curvando igual:
    ;; el bulge cambia de signo Y se corre un vertice.
    (list "Al invertir el bucle el arco no se voltea"
      ((lambda (rev)
        (and (equal -1.0 (cdr (car rev)) 1e-9)
             (equal '(4.0 3.0) (car (car rev)) 1e-9)
             (equal (- (urb:loop-signed-area
                         '(((0.0 0.0) . 0.0) ((4.0 0.0) . 1.0) ((4.0 3.0) . 0.0))))
                    (urb:loop-signed-area rev) 1e-9)))
        (urb:loop-reverse
          '(((0.0 0.0) . 0.0) ((4.0 0.0) . 1.0) ((4.0 3.0) . 0.0)))))
    ;; 2026-09-10: en el toperol la textura son los PUNTOS, no el fondo --
    ;; el relleno gris uniforme de v4.83 se los comia. Franja clara, domos
    ;; oscuros. La GUIA conserva su tono por banda.
    (list "El toperol se lee por sus puntos, no por el fondo"
      (and (= 7 (urb:tactile-fill-color "TOPEROL" T))
           (= 7 (urb:tactile-fill-color "TOPEROL" nil))
           (= 8 (urb:tactile-symbol-color "TOPEROL" T))
           (= 8 (urb:tactile-symbol-color "TOPEROL" nil))
           ;; y el punto nunca queda del mismo tono que su fondo
           (/= (urb:tactile-fill-color "TOPEROL" T)
               (urb:tactile-symbol-color "TOPEROL" T))
           (= 8 (urb:tactile-fill-color "GUIA" T))
           (= 7 (urb:tactile-fill-color "GUIA" nil))
           (= 7 (urb:tactile-symbol-color "GUIA" T))
           (= 8 (urb:tactile-symbol-color "GUIA" nil))))
    (list "El domo de toperol tiene su tamano real"
      (equal 0.0125 *urb-toperol-radio* 1e-9))
    ;; 2026-09-10: el punteado por patron es lo que evita sembrar miles de
    ;; circulos (y con ellos el empacado de minutos). Solo se salta el
    ;; sembrado cuando el patron QUEDO puesto; ante la duda se siembra.
    ;; 2026-09-12: un fallo de patron en UNA pieza (contorno de curva) no
    ;; puede degradar el resto del anden a un circulo por domo. Solo se
    ;; declara "NO" si el patron fallo en el PRIMER intento del dibujo.
    (list "Un fallo de patron en una pieza no contamina el resto del anden"
      ((lambda (previo previoF / r)
        (setq r
          (and
            ;; primer intento del dibujo y falla -> el patron no esta: NO
            (progn (setq *urb-toperol-pattern-state* nil)
              (urb:toperol-degradar-si-primero)
              (= *urb-toperol-pattern-state* "NO"))
            ;; ya habia funcionado y falla una pieza -> sigue en SI
            (progn (setq *urb-toperol-pattern-state* "SI"
                         *urb-toperol-fallos-pieza* 0)
              (urb:toperol-degradar-si-primero)
              (and (= *urb-toperol-pattern-state* "SI")
                   (= *urb-toperol-fallos-pieza* 1)))))
        (setq *urb-toperol-pattern-state* previo
              *urb-toperol-fallos-pieza* previoF)
        r)
        *urb-toperol-pattern-state* *urb-toperol-fallos-pieza*))
    (list "Solo se salta el sembrado de domos si el patron quedo puesto"
      ((lambda (previo / r)
        (setq r
          (and (progn (setq *urb-toperol-pattern-state* "SI")
                 (urb:toperol-by-pattern-p "TOPEROL"))
               (progn (setq *urb-toperol-pattern-state* "NO")
                 (not (urb:toperol-by-pattern-p "TOPEROL")))
               (progn (setq *urb-toperol-pattern-state* nil)
                 (not (urb:toperol-by-pattern-p "TOPEROL")))
               ;; la guia nunca usa el patron de puntos
               (progn (setq *urb-toperol-pattern-state* "SI")
                 (not (urb:toperol-by-pattern-p "GUIA")))))
        (setq *urb-toperol-pattern-state* previo)
        r)
        *urb-toperol-pattern-state*))
    ;; 2026-09-08: el desarrollo completo de rampa (aletas laterales) solo
    ;; cabe si el extremo tiene ancho para las dos aletas y el paso es
    ;; largo -- la condicion "cuando son tramos largos" del usuario.
    (list "El desarrollo de rampa solo entra en pasos largos y anchos"
      (and
        ;; tapas de 3,00 m separadas 5,00 m entre puntos medios: cabe
        (urb:ramp-ends-fit-p
          (list (list '(0.0 0.0) 0.0 1.0 3.0 0)
                (list '(8.0 0.0) pi 1.0 3.0 2)) "PASO-PEATONAL")
        ;; mismo ancho pero 1,00 m entre puntos medios: no cabe
        (not (urb:ramp-ends-fit-p
          (list (list '(0.0 0.0) 0.0 1.0 3.0 0)
                (list '(2.0 0.0) pi 1.0 3.0 2)) "PASO-PEATONAL"))
        ;; largo suficiente pero tapa de 1,00 m: no caben las dos aletas
        (not (urb:ramp-ends-fit-p
          (list (list '(0.0 0.0) 0.0 1.0 1.0 0)
                (list '(8.0 0.0) pi 1.0 1.0 2)) "PASO-PEATONAL"))
        (equal 1.70 (urb:ramp-end-min-width "PASO-PEATONAL") 1e-9)
        ;; v4.95: el extremo suma la fila de alerta (1,30 + 0,20 + 0,20)
        (equal 3.90 (urb:ramp-end-min-length "PASO-PEATONAL") 1e-9)
        ;; 2026-09-10: el acceso vehicular pide MAS frente (dos aletas de 2,10
        ;; mas 1,00 de cara) -- esa misma tapa de 3,00 m ya no le sirve
        (not (urb:ramp-ends-fit-p
          (list (list '(0.0 0.0) 0.0 1.0 3.0 0)
                (list '(8.0 0.0) pi 1.0 3.0 2)) "RAMPA-VEHICULAR"))
        ;; con 6,00 m de tapa y 6,00 m entre puntos medios si cabe
        (urb:ramp-ends-fit-p
          (list (list '(0.0 0.0) 0.0 1.0 6.0 0)
                (list '(12.0 0.0) pi 1.0 6.0 2)) "RAMPA-VEHICULAR")
        (equal 5.20 (urb:ramp-end-min-width "RAMPA-VEHICULAR") 1e-6)
        (equal 4.30 (urb:ramp-end-min-length "RAMPA-VEHICULAR") 1e-6)))
    ;; 2026-09-10: con UNA sola cota de referencia la rasante se completa
    ;; con la pendiente ("tengo via al principio pero no al final").
    (list "Con una cota y la pendiente sale la cota del otro extremo"
      (and (equal 2561.00 (urb:cota-por-pendiente 2560.00 1.0 100.0) 1e-9)
           (equal 2559.00 (urb:cota-por-pendiente 2560.00 -1.0 100.0) 1e-9)
           ;; pendiente 0 = tramo horizontal, no un error
           (equal 2560.00 (urb:cota-por-pendiente 2560.00 0.0 100.0) 1e-9)))
    ;; 2026-09-11: la etiqueta de pozo trae tapa y batea en DOS renglones.
    ;; Antes se tomaba el ULTIMO numero del texto (siempre la de abajo).
    ;; Ahora hay un numero por renglon, en orden, y los codigos de formato
    ;; del MTEXT (\H0.7x; etc.) no se confunden con la cota.
    (list "La etiqueta de dos cotas da un numero por renglon"
      (and (equal '(2565.25 2562.25)
                  (urb:text-line-numbers "2565.25\\P2562.25") 1e-9)
           (equal '(2565.25 2562.25)
                  (urb:text-line-numbers "{\\H0.7x;2565.25}\\P{\\H0.7x;2562.25}") 1e-9)
           (equal '(2560.5) (urb:text-line-numbers "CT=2560.50") 1e-9)
           (null (urb:text-line-numbers "SIN COTA"))))
    (list "Caja CS276 recorta un metro por extremo"
      (equal 1.0 (mp:point-base-gap "CAMARA_CS276") 1e-9))
    (list "Pozo humedo recorta hasta radio real"
      (equal 0.60 (mp:point-base-gap "POZO_PLUVIAL") 1e-9))))

(defun urb:version-info-command (/ installed file line disk-version checks ok item)
  (setq installed (strcat (getenv "APPDATA")
    "/Autodesk/ApplicationPlugins/UrbanismoCantidades.bundle/Contents/urbanismo_cantidades.lsp"))
  (if (setq file (open installed "r"))
    (progn
      (while (and (null disk-version) (setq line (read-line file)))
        (if (vl-string-search "(setq *urb-version* " line)
          (setq disk-version (caddr (read line)))))
      (close file)))
  (setq checks (urb:quality-selftests) ok 0)
  (foreach item checks (if (cadr item) (setq ok (1+ ok))
    (prompt (strcat "\nAutoprueba con fallo: " (car item)))))
  (alert (strcat "Motor en esta sesion: " *urb-version*
    "\nEsquema: " *urb-schema-version* "\nAutoCAD: " (getvar "ACADVER")
    "\n\nMotor instalado en disco:\n" (if disk-version disk-version "No localizado")
    "\n\n" installed "\n\nAutoprueba de logica: " (itoa ok) "/" (itoa (length checks))
    " correctas. No valida este dibujo.\nTras instalar una entrega, reinicie Civil 3D."))
  (princ))


(defun urb:quantities-menu (/ action)
  (setq action
    (urb:simple-menu-dialog "urb_quantities"
      '(("diagnostic" "diagnostic") ("trace" "trace")
        ("table" "table") ("road" "road") ("road_audit" "road_audit")
        ("scope" "scope")
        ("excel" "excel") ("link_excel" "link_excel")
        ("update_excel" "update_excel")
        ("unlink_excel" "unlink_excel") ("network" "network")
        ("cuadros" "cuadros") ("via_perfil" "via_perfil"))))
  (cond
    ((or (null action) (= action "back")) "back")
    ((= action "diagnostic") (urb:q-diagnostic-command))
    ((= action "trace") (urb:q-trace-command))
    ((= action "table") (urb:insert-quantities-table-command))
    ((= action "road") (urb:road-quantity-command))
    ((= action "road_audit") (urb:road-audit-table-command))
    ((= action "scope") (urb:quantity-scope-command))
    ((= action "excel") (urb:excel-export-command))
    ((= action "link_excel") (urb:excel-link-command))
    ((= action "update_excel") (urb:excel-update-linked-command))
    ((= action "unlink_excel") (urb:excel-unlink-command))
    ((= action "network") (urb:export-networks-csv-command))
    ((= action "cuadros") (urb:cuadros-red-command))
    ((= action "via_perfil") (urb:via-perfil-esquema-command)))
  (if (or (null action) (= action "back")) "back" nil))

(defun urb:configuration-menu (/ action)
  ;; 2026-08-11: "Cargar perfiles base faltantes" y "Diagnosticar y migrar
  ;; redes" salieron del menu a pedido del usuario (las funciones siguen
  ;; existiendo por codigo); entro "Etapas y subetapas".
  ;; 2026-08-24 (pedido del usuario): menu compactado -- Perfiles, Tabla
  ;; de anchos y Referencia de relleno se unificaron en el hub
  ;; "Movimiento de tierras"; "Senderos y prefabricados" y "Recalcular
  ;; tramos" salieron del menu (redundantes -- las funciones siguen
  ;; existiendo por codigo); entro "Depurar dibujo".
  (setq action
    (urb:simple-menu-dialog "urb_config"
      '(("etapas_config" "etapas_config")
        ("diametros_config" "diametros_config")
        ("earthworks_config" "earthworks_config")
        ("tramo_appearance" "tramo_appearance")
        ("layers_organize" "layers_organize")
        ("purge_dwg" "purge_dwg") ("light_dwg" "light_dwg")
        ("version_info" "version_info"))))
  (cond
    ((or (null action) (= action "back")) "back")
    ((= action "etapas_config") (urb:etapas-manager-command))
    ((= action "diametros_config") (urb:diametros-manager-command))
    ((= action "earthworks_config") (urb:earthworks-config-command))
    ((= action "tramo_appearance")
      (mp:tramo-appearance-command))
    ((= action "layers_organize")
      ;; "command" no tolera invocarse via apply ("bad order function:
      ;; COMMAND", detectado 2026-08-24) -- llamada directa dentro del
      ;; lambda, solo el catch-all pasa por apply
      (vl-catch-all-apply '(lambda () (command "_URBLAYERFILTER")) nil)
      (princ))
    ((= action "purge_dwg") (urb:purge-command))
    ((= action "light_dwg") (urb:light-mode-command))
    ((= action "version_info") (urb:version-info-command)))
  (if (or (null action) (= action "back")) "back" nil))

(defun c:URBANISMO (/ action done result)
  (vl-catch-all-apply 'urb:migrate-current-drawing nil)
  (while (not done)
    (setq action
      (urb:simple-menu-dialog "urb_main"
        '(("create" "create") ("edit" "edit") ("stages" "stages")
          ("quantities" "quantities") ("config" "config"))))
    (cond
      ((null action) (setq done T))
      ((= action "create")
        (if (not (urb:string-equal-p (urb:create-menu) "back"))
          (setq done T)))
      ((= action "edit") (c:EDITAR) (setq done T))
      ((= action "stages") (urb:batch-stage-command) (setq done T))
      ((= action "quantities")
        (if (not (urb:string-equal-p (urb:quantities-menu) "back"))
          (setq done T)))
      ((= action "config")
        (if (not (urb:string-equal-p (urb:configuration-menu) "back"))
          (setq done T)))))
  (princ))

(defun urb:prune-properties-v4230
  (/ ss i en obj atts base bname blocks bdef item victims defs rec allowed
   changed sync-result refs doc)
  (setq *urb-prune-stage* "inicio")
  (setq allowed
    '("ETIQUETA" "PENDIENTE_VIS" "ETAPA" "SUBETAPA" "RED" "TIPO_RED"
      "SERIE" "CIRCUITO" "CIRCUITO_AP" "DESDE" "HASTA" "POZO_INI"
      "POZO_FIN" "DIAMETRO" "MATERIAL" "PENDIENTE" "CONDUCTORES"
      "CONDUCTOR" "DUCTOS" "DIAM_DUCTO" "MATERIAL_DUCTO" "LIBRES"
      "PROFUNDIDAD" "COTA_TN_INI" "COTA_TN_FIN" "COTA_CLAVE_INI"
      "COTA_CLAVE_FIN" "LONGITUD" "ANCHO_ZANJA" "EXCAVACION_M3"
      "CAMA_M3" "VOLUMEN_ELEMENTO_M3" "RELLENO_M3" "SOBRANTE_M3"
      "REPOSICION_M2" "MEMORIAS"))
  (setq doc (vl-catch-all-apply 'urb:doc nil))
  (if (or (vl-catch-all-error-p doc) (/= (type doc) 'VLA-OBJECT))
    (setq doc nil blocks nil ss nil)
    (setq blocks (vla-get-Blocks doc)
          ss (ssget "_X" '((0 . "INSERT")))))
  (setq i 0)
  ;; Respaldar primero la totalidad de datos de cada tramo en XDATA.
  (if ss
    (repeat (sslength ss)
      (setq *urb-prune-stage* (strcat "lectura tramo indice " (itoa i)))
      (setq en (ssname ss i)
            obj (vl-catch-all-apply 'vlax-ename->vla-object (list en)))
      (if (and obj (not (vl-catch-all-error-p obj))
               (urb:valid-vla-object-p obj))
        (progn
          (setq atts (vl-catch-all-apply 'mp:att-alist (list en))
                bname (vl-catch-all-apply 'vla-get-EffectiveName (list obj)))
          (if (or (vl-catch-all-error-p atts)
                  (vl-catch-all-error-p bname))
            (setq atts nil bname nil base nil)
            (setq base (mp:infer-base bname atts)))
          (if (and bname (mp:base-is-tramo base))
            (progn
              (setq *urb-prune-stage* (strcat "respaldo " bname))
              (mp:store-cant-data en atts)
              (setq refs (cons (list en bname base atts) refs))
              (if (not (assoc (strcase bname) defs))
                (setq defs
                  (cons (cons (strcase bname) (list bname base)) defs)))))))
      (setq i (1+ i))))
  ;; Limpiar definiciones compartidas y agregar solo el esquema publico.
  (foreach rec defs
    (setq bname (car (cdr rec)) base (cadr (cdr rec))
          bdef (vl-catch-all-apply 'vla-Item (list blocks bname))
          victims nil)
    (if (not (vl-catch-all-error-p bdef))
      (progn
        (setq *urb-prune-stage* (strcat "definicion " bname))
        (vlax-for item bdef
          (if (and (= (vla-get-ObjectName item) "AcDbAttributeDefinition")
                   (not (member (strcase (vla-get-TagString item)) allowed)))
            (setq victims (cons item victims))))
        (foreach item victims
          (if (urb:safe-delete item) (setq changed (1+ (if changed changed 0)))))
        (vl-catch-all-apply 'mp:ensure-block-schema (list bname base T))
        (setq sync-result
          (vl-catch-all-apply 'vl-cmdf (list "_.ATTSYNC" "_N" bname))))))
  ;; Restaurar valores publicos y mantener la copia tecnica completa.
  (foreach rec refs
    (setq en (car rec) atts (nth 3 rec))
    (setq *urb-prune-stage* "restauracion referencias")
    (if (entget en)
      (progn (mp:setatts en atts) (mp:store-cant-data en atts))))
  ;; Andenes: sus datos tecnicos ya estan en URB_ANDEN_BLOCK/MOV.
  (setq ss (ssget "_X" '((0 . "INSERT") (-3 ("URB_ANDEN_BLOCK")))) i 0)
  (if ss
    (repeat (sslength ss)
      (setq *urb-prune-stage* (strcat "anden indice " (itoa i)))
      (setq en (ssname ss i)
            obj (vl-catch-all-apply 'vlax-ename->vla-object (list en))
            victims nil bdef nil)
      (if (and obj (not (vl-catch-all-error-p obj))
               (urb:valid-vla-object-p obj))
        (setq bdef (vl-catch-all-apply 'vla-Item
          (list blocks (vla-get-EffectiveName obj)))))
      (if (and bdef (not (vl-catch-all-error-p bdef)))
        (progn
          (vlax-for item bdef
            (if (and (= (vla-get-ObjectName item) "AcDbAttributeDefinition")
                     (member (strcase (vla-get-TagString item))
                       '("PERIMETRO_M" "ANDEN_ELEVACION" "ANDEN_SENTIDO"
                         "MATERIAL" "FORMATO_LOSETA" "ANDEN_SUPERFICIE"
                         "ANDEN_RASANTE" "ANDEN_PEND_LONG" "ANDEN_PEND_TRANS"
                         "ANDEN_PEND_TOTAL" "ANDEN_METODO" "ANDEN_MUESTRAS"
                         "ANDEN_COBERTURA" "ANDEN_VIA_ID" "ANDEN_VIA_NOMBRE")))
              (setq victims (cons item victims))))
          (foreach item victims
            (if (urb:safe-delete item) (setq changed (1+ (if changed changed 0)))))
          (vl-catch-all-apply 'vl-cmdf
            (list "_.ATTSYNC" "_N" (vla-get-EffectiveName obj)))))
      (setq i (1+ i))))
  (if changed changed 0))

(defun urb:normalize-anden-prefab-draworder (/ andenes prefabs result)
  ;; El achurado del anden debe quedar detras y el prefabricado vinculado
  ;; delante. Corrige dibujos donde el orden se perdio al empaquetar o editar.
  (setq andenes
    (ssget "_X" '((0 . "INSERT") (-3 ("URB_ANDEN_BLOCK")))))
  (setq prefabs
    (ssget "_X" '((0 . "INSERT") (-3 ("URB_PREFAB_ANILLO")))))
  (if andenes
    (vl-catch-all-apply 'vl-cmdf
      (list "_.DRAWORDER" andenes "" "_Back")))
  (if prefabs
    (setq result
      (vl-catch-all-apply 'vl-cmdf
        (list "_.DRAWORDER" prefabs "" "_Front"))))
  (if (vl-catch-all-error-p result) nil
    (list (if andenes (sslength andenes) 0)
          (if prefabs (sslength prefabs) 0))))

(defun urb:purge-empty-hatches (/ ss i e d n)
  ;; Un HATCH sin bucles (DXF 91=0) no representa area y en Civil 3D puede
  ;; renderizarse como un disco gigante. Solo se elimina ese objeto invalido;
  ;; regiones, polilineas y hatches con contorno quedan intactos.
  (setq ss (ssget "_X" '((0 . "HATCH"))) i 0 n 0)
  (if ss
    (repeat (sslength ss)
      (setq e (ssname ss i) i (1+ i) d (entget e))
      (if (and (equal '(91 . 0) (assoc 91 d)) (entdel e))
        (setq n (1+ n)))))
  n)

(defun urb:migrate-current-drawing
  (/ ss i count hydro-rings road-properties road-upgrade pruned
     appearance-refresh tramo-refresh draworder-refresh)
  ;; MIGRACIONES AUTOMATICAS de dibujos hechos con versiones anteriores.
  ;; Corre al cargar el .lsp y al abrir el menu URBANISMO, y es idempotente
  ;; (si no hay nada que migrar, no toca nada). Patron establecido a
  ;; pedido del usuario: cada cambio de capas/estructura futuro agrega
  ;; aqui su migracion para que lo ya creado se actualice solo.
  ;; 1) Tablas de verificacion de vias: de URB-VIA a URB-VIA-TABLA
  ;;    (para poder apagarlas sin ocultar la via).
  (if (setq ss (ssget "_X" '((0 . "ACAD_TABLE") (8 . "URB-VIA"))))
    (progn
      (urb:ensure-layer "URB-VIA-TABLA" 4 T)
      (setq i 0 count 0)
      (repeat (sslength ss)
        (if (not (vl-catch-all-error-p
                   (vl-catch-all-apply
                     '(lambda ()
                        (vla-put-Layer
                          (vlax-ename->vla-object (ssname ss i))
                          "URB-VIA-TABLA")))))
          (setq count (1+ count)))
        (setq i (1+ i)))
      (if (> count 0)
        (prompt
          (strcat "\nMigracion automatica: " (itoa count)
                  " tabla(s) de verificacion movida(s) a URB-VIA-TABLA.")))))
  ;; 2) (2026-08-11) La tabla de verificacion ya no vive pegada a la via:
  ;;    se despliega bajo demanda desde Cantidades donde el usuario la
  ;;    quiera. Se retiran las tablas generadas por versiones anteriores,
  ;;    tanto las sueltas como las EMPACADAS dentro de los bloques
  ;;    URB_VIA_* (ahi es donde realmente quedaron; las hechas a mano no
  ;;    se tocan).
  (setq count
    (urb:purge-road-block-tables))
  ;; barrido extra por CAPA (2026-08-11 v2): las tablas mas viejas no
  ;; tienen xdata (se creaban sin etiquetar); la capa URB-VIA-TABLA solo
  ;; la usan las tablas de verificacion generadas, asi que todo ACAD_TABLE
  ;; suelto en esa capa tambien se retira. Reporte del usuario: la
  ;; migracion anterior solo borro 1 de varias.
  (if (and nil (setq ss (ssget "_X" '((0 . "ACAD_TABLE") (8 . "URB-VIA-TABLA")))))
    (progn
      (setq i 0)
      (repeat (sslength ss)
        (if (not (vl-catch-all-error-p
                   (vl-catch-all-apply
                     '(lambda ()
                        (vla-Delete (vlax-ename->vla-object (ssname ss i)))))))
          (setq count (1+ count)))
        (setq i (1+ i)))))
  (if (> count 0)
    (progn
      (vl-catch-all-apply
        '(lambda () (vla-Regen (urb:doc) 1)))
      (prompt
        (strcat "\nMigracion automatica: " (itoa count)
                " tabla(s) de verificacion retirada(s);"
                " despliegalas desde Cantidades cuando las necesites."))))
  ;; 3) Los pozos reales permanecen como bloques puntuales unicos y
  ;; compartibles. Se retiran de los bloques de tramo los circulos de
  ;; extremo que los hacian parecer duplicados.
  (setq hydro-rings
    (vl-catch-all-apply 'mp:repair-hydro-tramo-definitions nil))
  (if (and (numberp hydro-rings) (> hydro-rings 0))
    (progn
      (vla-Regen (urb:doc) 1)
      (prompt
        (strcat
          "\nMigracion automatica: " (itoa hydro-rings)
          " circulo(s) de extremo duplicado retirado(s) de tramos"
          " hidrosanitarios; los pozos unicos se conservaron."))))
  ;; 4) Propiedades compactas de vias existentes: conserva cantidades,
  ;; geometria y corte/relleno; retira los campos administrativos pedidos
  ;; y sustituye las frases contractuales por el nombre corto del material.
  (setq road-properties
    (vl-catch-all-apply 'urb:clean-existing-road-properties nil))
  (if (and (numberp road-properties) (> road-properties 0))
    (prompt
      (strcat
        "\nMigracion automatica: " (itoa road-properties)
        " propiedad(es) de via simplificada(s).")))
  (setq road-upgrade
    (vl-catch-all-apply 'urb:upgrade-existing-road-properties nil))
  (if (and (numberp road-upgrade) (> road-upgrade 0))
    (prompt
      (strcat "\nMigracion automatica: " (itoa road-upgrade)
        " ajuste(s) visual(es/de propiedades) aplicado(s) a vias.")))
  ;; 5) Una sola vez por dibujo: propiedades tecnicas de tramos/andenes se
  ;; respaldan en XDATA y se retiran de la paleta, conservando cantidades.
  (if (/= (urb:safe-string (urb:config-read "URB_MIGRATE_4230_PROPS") "") "OK")
    (progn
      (setq pruned (vl-catch-all-apply 'urb:prune-properties-v4230 nil))
      (if (not (vl-catch-all-error-p pruned))
        (progn
          (urb:config-write "URB_MIGRATE_4230_PROPS" "OK")
          (if (> pruned 0)
            (prompt
              (strcat "\nMigracion automatica: " (itoa pruned)
                " propiedad(es) tecnica(s) ocultada(s); datos respaldados.")))))))
  ;; 6) v4.75.0: corrige la doble fuente de configuracion visual, fuerza
  ;; 0.20/0.60 una sola vez y reconstruye las referencias para que la linea
  ;; y la LONGITUD terminen en la cara del pozo/caja, no en su centro.
  (if (/= (urb:safe-string
            (urb:config-read "URB_MIGRATE_4750_TRAMOS") "") "OK")
    (progn
      (setq *mp-vis-width* 0.20
            *mp-vis-tramo-text-height* 0.60)
      (mp:store-tramo-appearance-settings 0.20 0.60)
      (setq tramo-refresh
        (vl-catch-all-apply 'urb:q-refresh-network-segments nil))
      (setq appearance-refresh
        (vl-catch-all-apply 'mp:apply-tramo-appearance-to-drawing nil))
      (setq draworder-refresh
        (vl-catch-all-apply 'urb:normalize-anden-prefab-draworder nil))
      (if (and (not (vl-catch-all-error-p tramo-refresh))
               (= (cadr tramo-refresh) 0)
               (not (vl-catch-all-error-p appearance-refresh)))
        (progn
          (urb:config-write "URB_MIGRATE_4750_TRAMOS" "OK")
          (prompt
            (strcat "\nMigracion v4.75.0: redes unificadas a 0.20/0.60; "
              (itoa (car tramo-refresh))
              " tramo(s) ajustados hasta la cara de sus cajas.")))
        (prompt
          "\nMigracion v4.75.0 pendiente: use AJUSTES > Apariencia de tramos en Civil 3D completo."))))
  (princ))

(defun urb:remove-legacy-commands (/ command-symbol)
  ;; Al recargar el LSP, AutoCAD conserva en memoria las funciones C: que
  ;; desaparecieron del archivo. Se retiran expresamente. OJO (2026-08-11):
  ;; varios nombres viejos (c:VIA, c:ANDEN, c:PREFABRICADO, c:SUMIDERO,
  ;; c:LUMINARIA) SALIERON de esta lista porque volvieron a ser comandos
  ;; publicos oficiales -- son los puntos de enlace del RIBBON (ver bloque
  ;; "COMANDOS PUBLICOS DEL RIBBON" abajo).
  (foreach command-symbol
    '(c:CANTIDADES
      c:ACT_ETIQUETAS_CANTIDAD
      c:QREDES_CSV
      c:ACTUALIZAR
      c:MP_REPARAR_VISIBILIDAD
      c:MAIPORE_BLOQUES_REDES_ELECT
      c:PERFILES_BASE
      c:URBVERSION
      c:QVINCULAREXCEL
      c:QACTUALIZAREXCEL
      c:QDESVINCULAREXCEL
      c:TRAMO
      c:POZO_SANITARIO
      c:POZO_PLUVIAL
      c:CAMARA_ELECTRICA
      c:ACCESORIO_ACUEDUCTO
      ;; 2026-09-08: boton "Sendero" del ribbon eliminado (Tipo=Sendero
      ;; ya se crea desde ANDEN) -- limpia el comando si quedo en memoria
      ;; de una sesion con el lsp/bundle viejo.
      c:URBSENDERO)
    (vl-acad-undefun command-symbol))
  (princ))

;;; ============================================================
;;; COMANDOS PUBLICOS DEL RIBBON (2026-08-11)
;;; Cada boton de la pestana CANTIDADES dispara uno de estos. Son
;;; envoltorios de 1 linea: TODA la logica sigue en las funciones
;;; internas de siempre -- el ribbon depende del lsp, nunca al reves.
;;; Tambien sirven escritos a mano (VIA, ANDEN, QCUADRO...).
;;; ============================================================
;; Crear
(defun c:VIA () (urb:create-road) (princ))
(defun c:ANDEN () (urb:create-sidewalk-command) (princ))
(defun c:RAMPA () (urb:create-ramp-command) (princ))
(defun c:ZONAVERDE () (urb:create-green-zone-command) (princ))
(defun c:PREFABRICADO () (urb:create-precast-command) (princ))
(defun c:URBMOBILIARIO () (urb:mobiliario-command) (princ))
(defun c:URBBIOSWALE () (urb:bioswale-command) (princ))
(defun c:ZONAPARQUE () (urb:zona-parque-command) (princ))
;; Redes
(defun c:TSANITARIO () (urb:create-network-segment-direct "segment_sanitary") (princ))
(defun c:TPLUVIAL () (urb:create-network-segment-direct "segment_storm") (princ))
(defun c:TACUEDUCTO () (urb:create-network-segment-direct "segment_water") (princ))
(defun c:TMT () (urb:create-network-segment-direct "segment_mt") (princ))
(defun c:TBT () (urb:create-network-segment-direct "segment_bt") (princ))
(defun c:TAP () (urb:create-network-segment-direct "segment_ap") (princ))
(defun c:POZOSAN () (if (urb:confirm-meter-units) (urb:create-sanitary-manhole)) (princ))
(defun c:POZOPLU () (if (urb:confirm-meter-units) (urb:create-storm-manhole)) (princ))
(defun c:SUMIDERO () (if (urb:confirm-meter-units) (urb:create-inlet)) (princ))
;; 5.6.0: canuela de la red pluvial (boton del panel Pluvial). El nombre
;; CANUELA a secas ya lo retira la limpieza de comandos viejos del inicio.
(defun c:CANUELAPLU () (if (urb:confirm-meter-units) (urb:canuela-plu-command)) (princ))
(defun c:CAMARA () (if (urb:confirm-meter-units) (urb:create-electrical-chamber)) (princ))
(defun c:ACCESORIO () (if (urb:confirm-meter-units) (urb:create-water-accessory)) (princ))
(defun c:LUMINARIA () (if (urb:confirm-meter-units) (urb:create-luminaire)) (princ))
;; Editar
(defun c:ETAPAS () (urb:batch-stage-command) (princ))
;; Cantidades
(defun c:QCUADRO () (urb:insert-quantities-table-command) (princ))
(defun c:QMEMORIA () (urb:road-quantity-command) (princ))
(defun c:QVERIFICACION () (urb:road-audit-table-command) (princ))
(defun c:QALCANCE () (urb:quantity-scope-command) (princ))
(defun c:QCSV () (urb:export-networks-csv-command) (princ))
(defun c:FILTRAR () (urb:filtrar-command) (princ))
;; Excel
(defun c:QEXCEL () (urb:excel-export-command) (princ))
(defun c:QVINCULAR () (urb:excel-link-command) (princ))
(defun c:QACTUALIZAR () (urb:excel-update-linked-command) (princ))
(defun c:QDESVINCULAR () (urb:excel-unlink-command) (princ))
;; Configuracion
(defun c:PERFILES () (urb:manage-road-profiles) (princ))
(defun c:AJUSTES () (urb:configuration-menu) (princ))

;; Carga automatica de la pestana CANTIDADES del ribbon (cui parcial).
;; Busca primero la copia instalada por el bundle (existe en cualquier
;; maquina donde corrio INSTALAR.bat) y como respaldo el cui del repo via
;; findfile. Se carga por COM (MenuGroups.Load), que no necesita contexto
;; de comando -- funciona durante la carga automatica del autoloader.
(defun urb:ensure-ribbon (/ candidates path found result)
  (if (not (menugroup "CANTIDADES"))
    (progn
      ;; SIEMPRE el .cuix empaquetado (2026-08-11 v2): el convertidor de
      ;; .cui monoliticos es anterior al ribbon y descartaba los paneles
      ;; en silencio -- el .cui del repo es solo la FUENTE legible; lo que
      ;; se carga es el .cuix armado por armar_cuix.ps1.
      (setq candidates
        (list
          (strcat (urb:safe-string (getenv "APPDATA") "")
            "\\Autodesk\\ApplicationPlugins\\UrbanismoCantidades.bundle\\Contents\\cantidades.cuix")
          (findfile "cantidades.cuix")))
      (foreach path candidates
        (if (and path
                 (not (menugroup "CANTIDADES"))
                 (setq found (findfile path)))
          (progn
            (setq result
              (vl-catch-all-apply
                '(lambda ()
                   (vla-Load
                     (vla-get-MenuGroups (vlax-get-acad-object))
                     found))))
            (if (vl-catch-all-error-p result)
              (prompt
                (strcat "\nAviso: no se pudo cargar el ribbon CANTIDADES: "
                        (vl-catch-all-error-message result)))))))))
  (princ))

;; Auto-reparacion de TRUSTEDPATHS (2026-08-11): AutoCAD reescribe esa
;; variable al cerrar con lo que tenia en memoria, asi que agregarla por
;; registro desde afuera se pierde si habia una sesion abierta. Aqui, ya
;; ADENTRO de AutoCAD, se agrega la carpeta del bundle a la variable viva
;; (persiste al cerrar). Tras el primer "Always Load"/"Load Once" del
;; usuario, ninguna sesion futura vuelve a preguntar.
(defun urb:ensure-trusted-path (/ targets current target)
  ;; 2026-08-13: ademas del bundle, se confia el LABORATORIO de
  ;; verificacion (Documents\URBANISMO\work, con "..." = subcarpetas)
  ;; para que los harnesses headless (TESTING_CIVIL3D.md 3c/3d) carguen
  ;; sin el dialogo de seguridad. Auto-reparado en cada carga porque
  ;; AutoCAD reescribe TRUSTEDPATHS al salir.
  (setq targets
    (list
      (strcat (urb:safe-string (getenv "APPDATA") "")
        "\\Autodesk\\ApplicationPlugins\\UrbanismoCantidades.bundle\\Contents")
      (strcat (urb:safe-string (getenv "USERPROFILE") "")
        "\\Documents\\URBANISMO\\work\\...")))
  (setq current (urb:safe-string (getvar "TRUSTEDPATHS") ""))
  (foreach target targets
    (if (not (vl-string-search (strcase target) (strcase current)))
      (setq current
        (if (= current "") target (strcat current ";" target)))))
  (setvar "TRUSTEDPATHS" current)
  (princ))

;; Rescate manual de la pestana (2026-08-11 v3): CUILOAD por comando SI
;; fusiona la pestana del parcial a la cinta (a diferencia de
;; MenuGroups.Load por COM, que solo registra el menugroup). Se usa solo
;; si la pestana no aparecio tras reiniciar: escribir CARGARCINTA.
(defun c:CARGARCINTA (/ path old-filedia)
  (setq path
    (strcat (urb:safe-string (getenv "APPDATA") "")
      "\\Autodesk\\ApplicationPlugins\\UrbanismoCantidades.bundle\\Contents\\cantidades.cuix"))
  (if (not (findfile path))
    (prompt "\nNo se encontro cantidades.cuix en el bundle instalado; corra INSTALAR.bat.")
    (progn
      (setq old-filedia (getvar "FILEDIA"))
      (setvar "FILEDIA" 0)
      (if (menugroup "CANTIDADES")
        (command "_.CUIUNLOAD" "CANTIDADES"))
      (command "_.CUILOAD" path)
      (setvar "FILEDIA" old-filedia)
      (prompt
        (strcat "\nPestana CANTIDADES cargada."
          " Si no se ve: clic derecho sobre la cinta > Show Tabs > CANTIDADES."))))
  (princ))

(urb:remove-legacy-commands)
(mp:install-network-erase-reactor)
(vl-catch-all-apply 'urb:ensure-trusted-path nil)
(vl-catch-all-apply 'urb:refresh-etapas-catalog nil)
(vl-catch-all-apply 'urb:refresh-diametros-catalog nil)
(vl-catch-all-apply 'mp:load-tramo-appearance-settings nil)
(vl-catch-all-apply 'urb:load-geometric-settings nil)
(vl-catch-all-apply 'urb:purge-empty-hatches nil)
;; 5.7.2 (pedido del usuario): sin el globo "Unreconciled New Layers" en
;; cada apertura (el motor y los xrefs crean capas; avisarlo no aporta)
(vl-catch-all-apply 'setvar (list "LAYERNOTIFY" 0))
;; 2026-09-14 (medido: el motor tardaba 43,8 s en cargar sobre una copia
;; del maestro de 33 MB contra 1,5 s en dibujo limpio -- 42,4 s de
;; diferencia). urb:repair-anden-hatches recorre TODOS los bloques del
;; dibujo y TODOS los objetos de cada uno con un entget por objeto, y
;; corria en CADA carga del motor, o sea en CADA apertura de dibujo.
;; La reparacion es idempotente: una vez estabilizados los rellenos de un
;; dibujo con un esquema dado, repetirla no cambia nada. El sello cambia
;; solo cuando cambie el algoritmo de reparacion, no en cada entrega.
(vl-catch-all-apply 'urb:repair-anden-hatches-si-hace-falta nil)
(if (and (not *urb-suppress-auto-migration*)
         (/= (getenv "URB_TEST_SUPPRESS_AUTO_MIGRATION") "1"))
  (progn
    (vl-catch-all-apply 'urb:migrate-current-drawing nil)
    (setq *mp-electrical-display-migration-result*
      (vl-catch-all-apply 'mp:migrate-electrical-display nil))
    (setq *mp-wipeout-migration-result*
      (vl-catch-all-apply 'mp:migrate-network-wipeouts nil))
    (setq *mp-acc-look-migration-result*
      (vl-catch-all-apply 'mp:migrate-accessory-look nil))
    (if (vl-catch-all-error-p *mp-electrical-display-migration-result*)
      (prompt "\nActualizacion electrica pendiente: no se pudo completar; se reintentara al abrir."))))
(vl-catch-all-apply 'urb:install-memory-property-reactors nil)
;; OJO (2026-08-11 v3): urb:ensure-ribbon YA NO se llama automaticamente.
;; Si el lsp carga el cuix por COM ANTES que el Autoloader, el Autoloader
;; encuentra el menugroup ya cargado, no lo procesa, y la pestana queda
;; SIN fusionar a la cinta (auto-sabotaje detectado en la prueba en vivo).
;; En sesiones frescas el Autoloader (PackageContents) carga el cuix y
;; fusiona la pestana solo; si algo falla, el usuario tiene CARGARCINTA.

(princ
  (strcat
    "\nUrbanismo " *urb-version* " listo."
    " Comandos: URBANISMO, EDITAR y la pestana CANTIDADES del ribbon."))
(princ)
