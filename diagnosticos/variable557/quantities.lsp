(defun vq:run (/ rows ss i en obj h matches area expected count a block t0 result)
 (vc:log 'QUANTITIES_BEGIN)
 (setq rows (urb:ppto-rows-senderos) ss (ssget "_X" '((0 . "LWPOLYLINE") (-3 ("URB_SENDERO")))) i 0)
 (repeat (sslength ss)
  (setq en (ssname ss i) obj (vlax-ename->vla-object en) h (vla-get-Handle obj) area (vla-get-Area obj)
   expected (atof (rtos area 2 3)) count 0)
  (foreach row rows
   (if (and (= h (nth 9 row)) (= "M2" (nth 7 row)) (equal expected (nth 8 row) 1e-6)) (setq count (1+ count))))
  (vc:check (list 'EXPORT_AREA h expected) (> count 0))
  (setq i (1+ i)))
 (setq en (vc:poly '((1000 0) (1010 0) (1020 -8) (1030 0) (1040 0) (1040 2) (1030 2) (1020 10) (1010 2) (1000 2))))
 (urb:set-anden-data en "Loseta" "5" "5A" "No" "No" "40 x 40 cm" "No" "Seleccionar en dibujo" "Via creada")
 (setq t0 (getvar "MILLISECS") result (urb:build-anden-finish en "Loseta" "No" "No" "40 x 40 cm"))
 (vc:check 'ANDEN_VARIABLE_BUILD result)
 (if result
  (progn (setq block (urb:package-anden en)) (vc:check 'ANDEN_VARIABLE_BLOCK (urb:valid-vla-object-p block))
   (setq a (urb:block-attribute-values block))
   (vc:check 'ANDEN_VARIABLE_AREA (equal 240.0 (atof (cdr (assoc "AREA_SIN_SOBREANCHO_M2" a)))))))
 (vc:log (list 'ANDEN_VARIABLE_MS (- (getvar "MILLISECS") t0)))
 (command "_.QSAVE")
 (vc:log (list 'QUANTITIES_DONE 'FAILURES vc:fail)))
(setq vq:r (vl-catch-all-apply 'vq:run nil))
(if (vl-catch-all-error-p vq:r) (vc:log (list 'ERROR (vl-catch-all-error-message vq:r))))
(princ)
