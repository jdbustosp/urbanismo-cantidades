(vl-load-com)
(if (/= (strcase (strcat (getvar "DWGPREFIX") (getvar "DWGNAME"))) "C:\\USERS\\JUANBUSPER\\DOCUMENTS\\CHATGPT\\COMPLEMENTO AUTOCAD\\WORK\\VARIABLE557\\FIXTURE.DWG") (exit))
(setq vc:dir "C:/Users/juanbusper/Documents/ChatGPT/COMPLEMENTO AUTOCAD/work/variable557/" vc:fail 0 *urb-suppress-auto-migration* T)
(defun vc:log (x / f) (setq f (open (strcat vc:dir "result.txt") "a")) (write-line (vl-princ-to-string x) f) (close f))
(defun vc:check (label ok) (if (not ok) (setq vc:fail (1+ vc:fail))) (vc:log (list (if ok 'OK 'FAIL) label)))
(defun vc:poly (points / en) (setq en (urb:open-poly-from-points points 0.0)) (vla-put-Closed (vlax-ename->vla-object en) :vlax-true) en)
(defun vc:case (label source code / en obj data t0 end e count hatch area entry groups0)
 (setq obj (vla-Copy (vlax-ename->vla-object source)) en (vlax-vla-object->ename obj) data (entget en) area (vla-get-Area obj)
       entry (assoc code *urb-send-tipos*) groups0 (vla-get-Count (vla-get-Groups (urb:doc))) vc:queue (list en) t0 (getvar "MILLISECS") end (entlast))
 (urb:poly-element-draw entry "5" "5A" "Ninguno" "Ninguno" "Interno" "URB_SENDERO")
 (setq e (entnext end) count 0)
 (while e
  (if (= (cdr (assoc 0 (entget e))) "HATCH") (setq hatch (vlax-ename->vla-object e) count (1+ count)))
  (setq e (entnext e)))
 (vc:check (list label 'ONE_HATCH) (= count 1))
 (vc:check (list label 'METADATA) (= code (car (urb:get-xdata-strings en "URB_SENDERO"))))
 (vc:check (list label 'ONE_GROUP) (= (1+ groups0) (vla-get-Count (vla-get-Groups (urb:doc)))))
 (vc:check (list label 'SOURCE_GEOMETRY) (equal (vl-remove-if-not '(lambda (p) (member (car p) '(10 42 90 70))) data)
       (vl-remove-if-not '(lambda (p) (member (car p) '(10 42 90 70))) (entget en))))
 (if hatch
  (progn
   (vc:check (list label 'AREA) (equal area (vla-get-Area hatch) 1e-6))
   (vc:check (list label 'LAYER) (= (nth 6 entry) (vla-get-Layer hatch)))
   (vc:check (list label 'PATTERN) (= (if (= code "CICLORRUTA") "SOLID" "NET") (vla-get-PatternName hatch)))
   (vc:log (list label 'MS (- (getvar "MILLISECS") t0) 'AREA (rtos area 2 9) 'PER (vla-get-Length obj)))))
 en)
(defun vc:run (/ real pts wide concave curve row en)
 (vc:log 'BEGIN)
 (load (strcat vc:dir "baseline.lsp"))
 (setq real (handent "F3F") pts (urb:lwpoly-points-with-arcs real))
 (vc:log (list 'REAL_D21E9 'WIDTH_REJECT (urb:anden-width-anomaly-p pts) 'OLD_VALID (urb:anden-shape-ok-p pts) 'SELF_CROSS (urb:polygon-self-intersects-p pts)))
 (load (strcat vc:dir "candidate.lsp"))
 (vc:check 'VERSION (= *urb-version* "5.5.7"))
 ;; Solo se sustituyen entradas interactivas; validacion y constructor son reales.
 (defun urb:draw-closed-polyline (/ en) (setq en (car vc:queue) vc:queue (cdr vc:queue)) (if (and en (urb:anden-shape-ok-p (urb:lwpoly-points-with-arcs en))) en))
 (defun urb:pick-design-cotas () nil)
 (vc:check 'REAL_VALID (urb:anden-shape-ok-p pts))
 (vc:check 'CROSS_REJECT (not (urb:anden-shape-ok-p '((0 0) (10 10) (0 10) (10 0)))))
 (vc:case 'REAL_CICLORRUTA real "CICLORRUTA")
 (vc:case 'REAL_SENDERO real "SEND-ECO")
 (setq wide (vc:poly '((0 0) (10 0) (20 -8) (30 0) (40 0) (40 2) (30 2) (20 10) (10 2) (0 2))))
 (vc:case 'VARIABLE_2_A_18M wide "SEND-TROTE")
 (setq concave (vc:poly '((100 0) (120 0) (120 20) (116 20) (116 4) (104 4) (104 20) (100 20))))
 (vc:case 'CONCAVO_U concave "SEND-ECO")
 (setq curve (entmakex '((0 . "LWPOLYLINE") (100 . "AcDbEntity") (100 . "AcDbPolyline") (90 . 6) (70 . 1)
  (10 200.0 0.0) (42 . 0.3) (10 220.0 0.0) (42 . 0.0) (10 225.0 10.0) (42 . 0.0)
  (10 215.0 20.0) (42 . -0.2) (10 205.0 10.0) (42 . 0.0) (10 200.0 3.0) (42 . 0.0))))
 (vc:case 'CURVAS_VARIABLES curve "CICLORRUTA")
 (command "_.QSAVE")
 (vc:log (list 'DONE 'FAILURES vc:fail)))
(setq vc:r (vl-catch-all-apply 'vc:run nil))
(if (vl-catch-all-error-p vc:r) (vc:log (list 'ERROR (vl-catch-all-error-message vc:r))))
(princ)
