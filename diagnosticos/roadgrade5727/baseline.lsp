(vl-load-com)
(setq rg27:file "C:/Users/juanbusper/Documents/URBANISMO/work/roadgrade5727/baseline.txt")
(defun rg27:log (s / f) (setq f (open rg27:file "a")) (write-line s f) (close f))
(defun rg27:run (/ ss i en data records axis mov missing missing-axis complete
                  with-mov with-xdata with-ldata road-name status raw)
  (setq ss (ssget "_X" '((-3 ("URB_VIA")))))
  (setq i 0 missing 0 missing-axis 0 complete 0 with-mov 0 with-xdata 0 with-ldata 0)
  (if ss
    (repeat (sslength ss)
      (setq en (ssname ss i) i (1+ i)
            data (urb:get-xdata-strings en "URB_VIA")
            road-name (urb:safe-string (nth 1 data) "?")
            status (urb:safe-string (nth 19 data) "?")
            raw (urb:road-ldata-stored en "URB_VIA_RASANTE_FULL")
            mov (urb:road-movement-data en)
            records (vl-catch-all-apply 'urb:road-design-grade-records (list en data))
            axis (vl-catch-all-apply 'urb:road-axis-recover
              (list en data (urb:safe-string (nth 22 data) ""))))
      (if (and (not (vl-catch-all-error-p raw)) (urb:grade-records-valid-p raw))
        (setq with-ldata (1+ with-ldata)))
      (if (and (> (length data) 32) (/= (urb:safe-string (nth 32 data) "") ""))
        (setq with-xdata (1+ with-xdata)))
      (if mov (setq with-mov (1+ with-mov)))
      (if (or (vl-catch-all-error-p axis) (null axis))
        (setq missing-axis (1+ missing-axis)))
      (if (or (vl-catch-all-error-p records)
              (not (urb:grade-records-valid-p records)))
        (progn
          (setq missing (1+ missing))
          (rg27:log (strcat "NO_GRADE " (cdr (assoc 5 (entget en))) " " road-name
            " status=" status " data=" (itoa (length data))
            " mov=" (if mov "Y" "N")
            " type=" (cdr (assoc 0 (entget en)))))
          (rg27:log (strcat "FIELDS " (vl-princ-to-string data))))
        (setq complete (1+ complete)))))
  (rg27:log (strcat "SUMMARY roads=" (itoa i) " grade=" (itoa complete)
    " no_grade=" (itoa missing) " no_axis=" (itoa missing-axis)
    " mov=" (itoa with-mov) " xdata_grade=" (itoa with-xdata)
    " ldata_grade=" (itoa with-ldata)))
  (rg27:log "FINISHED"))
(rg27:log "STARTED")
(setq rg27:r (vl-catch-all-apply 'rg27:run nil))
(if (vl-catch-all-error-p rg27:r)
  (rg27:log (strcat "ERROR " (vl-catch-all-error-message rg27:r))))
(princ)
