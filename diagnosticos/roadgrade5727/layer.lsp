(vl-load-com)
(setq rg27:out "C:/Users/juanbusper/Documents/URBANISMO/work/roadgrade5727/layer.txt")
(defun rg27:log (s / f) (setq f (open rg27:out "a")) (write-line s f) (close f))
(setq rg27:road (handent "1E4E4C"))
(setq rg27:data (urb:get-xdata-strings rg27:road "URB_VIA"))
(setq rg27:axis (urb:road-axis-recover rg27:road rg27:data (nth 22 rg27:data)))
(setq rg27:fake (urb:replace-nth 8 "RG27_COTAS" rg27:data))
(setq rg27:seen nil *urb-road-grade-silent* T)
(defun urb:collect-cota-texts (layer) (setq rg27:seen layer) nil)
(urb:road-grade-records-from-layer rg27:axis rg27:fake)
(rg27:log (strcat "VERSION " *urb-version*))
(rg27:log (strcat "LAYER " (urb:safe-string rg27:seen "NIL")))
(rg27:log (if (= rg27:seen "RG27_COTAS") "PASS capa [8]" "FAIL capa [8]"))
(if (= rg27:seen "RG27_COTAS") (rg27:log "FINISHED"))
(princ)
