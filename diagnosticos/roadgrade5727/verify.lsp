(vl-load-com)
(setq rg27:result "C:/Users/juanbusper/Documents/URBANISMO/work/roadgrade5727/verify.txt"
      rg27:pass 0 rg27:fail 0)
(defun rg27:log (s / f) (setq f (open rg27:result "a")) (write-line s f) (close f))
(defun rg27:check (ok label)
  (if ok (setq rg27:pass (1+ rg27:pass)) (setq rg27:fail (1+ rg27:fail)))
  (rg27:log (strcat (if ok "PASS " "FAIL ") label)))
(defun rg27:run (/ road data raw axis poly full src packaged block-unpacked
                   near points auto z a axis-h)
  (rg27:check (= *urb-version* "5.7.27") "version")
  ;; Caso real del maestro: VIA-25 existe pero nunca recibio rasante.
  (setq road (handent "1E4E4C")
        data (if road (urb:get-xdata-strings road "URB_VIA")))
  (rg27:check (and road (= (nth 1 data) "VIA-25")
                   (null (urb:road-design-grade-records road data)))
    "baseline real: VIA-25 no tiene rasante")
  (setq raw (vl-catch-all-apply 'urb:anden-road-grade-for-quiet (list road)))
  (rg27:check (and (not (vl-catch-all-error-p raw)) (null raw))
    "via sin rasante se omite sin pedir clic durante busqueda automatica")
  (setq points (urb:lwpoly-points road))
  (setq raw (vl-catch-all-apply 'urb:anden-road-score (list road points)))
  (rg27:check (and (not (vl-catch-all-error-p raw)) (null raw))
    "via incompleta no puntua para anden sendero ni zona verde")
  ;; Solo en la COPIA local: dar a VIA-25 un perfil sintético con quiebre
  ;; y verificar que el empaquetado lo conserva íntegro.
  (setq poly road
        full '((0.0 2700.0) (219.5 2702.0) (439.0 2700.0))
        src '((0.0 2700.0 "VIA" "INICIO") (219.5 2702.0 "POZO" "P1")))
  (vlax-ldata-put poly "URB_VIA_RASANTE_FULL" full)
  (vlax-ldata-put poly "URB_VIA_RASANTE_SRC" src)
  (setq packaged (vl-catch-all-apply 'urb:package-road (list poly)))
  (if (vl-catch-all-error-p packaged)
    (rg27:log (strcat "PACKAGE_ERROR " (vl-catch-all-error-message packaged)
      " STAGE=" (urb:safe-string *urb-package-road-stage* "?")))
    (if (null packaged) (rg27:log "PACKAGE_RETURNED_NIL")))
  (rg27:check (and (not (vl-catch-all-error-p packaged)) packaged)
    "empaquetar via con rasante completa")
  (if (and packaged (not (vl-catch-all-error-p packaged)))
    (progn
      (setq packaged (urb:as-ename packaged))
      (rg27:check (equal (urb:road-ldata-stored packaged "URB_VIA_RASANTE_FULL") full)
        "bloque conserva las tres estaciones")
      (rg27:check (equal (urb:road-ldata-stored packaged "URB_VIA_RASANTE_SRC") src)
        "bloque conserva fuente de cotas")
      (rg27:check (equal (urb:road-design-grade-records packaged
                           (urb:get-xdata-strings packaged "URB_VIA")) full)
        "anden y areas leen perfil completo del bloque")
      (setq block-unpacked
        (vl-catch-all-apply 'urb:explode-road-block-boundary (list packaged)))
      (rg27:check (and (not (vl-catch-all-error-p block-unpacked)) block-unpacked
                       (equal (urb:road-ldata-stored block-unpacked "URB_VIA_RASANTE_FULL") full))
        "editar via conserva perfil al desempacar")))
  (rg27:log (strcat "SUMMARY pass=" (itoa rg27:pass) " fail=" (itoa rg27:fail)))
  (if (= rg27:fail 0) (rg27:log "FINISHED")))
(rg27:log "STARTED")
(setq rg27:r (vl-catch-all-apply 'rg27:run nil))
(if (vl-catch-all-error-p rg27:r)
  (rg27:log (strcat "ERROR " (vl-catch-all-error-message rg27:r))))
(princ)
