(vl-load-com)
(setq v11:out "C:/Users/juanbusper/Documents/URBANISMO/work/anden5711/result.txt"
      v11:pass 0 v11:fail 0)
(defun v11:log (msg / f)
  (setq f (open v11:out "a")) (write-line msg f) (close f))
(defun v11:check (ok msg)
  (if ok (setq v11:pass (1+ v11:pass)) (setq v11:fail (1+ v11:fail)))
  (v11:log (strcat (if ok "PASS " "FAIL ") msg)))
(defun v11:run (/ en len old sliced cut sample parts kept r t0 boundary chains
                      p1 p2 c1 c2 a b poly mid station)
  (if (/= (strcase (getvar "DWGNAME")) "FIXTURE.DWG")
    (vl-exit-with-error "Solo fixture de laboratorio"))
  (v11:check (= *urb-version* "5.7.11") "version")
  ;; Radio 360 m, cuarto de circulo = 565.486677646 m.
  (setq en (urb:poly-chain-polyline '((360.0 0.0 0.414213562373095) (0.0 360.0 0.0)))
        len (urb:curve-length en)
        old (urb:chain-subpoly en 0.0 len)
        sliced (urb:chain-slice-exact en 0.0 len))
  (v11:check (> (cdr (assoc 90 (entget old))) 2200) "baseline amplifies arc into over 2200 vertices")
  (entdel old)
  (v11:check (= (length sliced) 2) "565m arc retains two vertices")
  (v11:check (equal (urb:poly-chain-length sliced) (* 180.0 pi) 1e-7) "exact arc length")
  (setq cut (urb:chain-slice-exact en 100.0 300.0))
  (v11:check (equal (urb:poly-chain-length cut) 200.0 1e-7) "partial arc length without chord loss")
  ;; Rectangulo atraviesa el arco entre x=250 y x=260.
  (setq poly '((250.0 240.0) (260.0 240.0) (260.0 270.0) (250.0 270.0))
        parts (urb:prefab-split-exact sliced (list poly))
        kept (apply '+ (mapcar 'urb:poly-chain-length parts)))
  (v11:check (= (length parts) 2) "container splits curved curb into two exact arcs")
  (v11:check (and (< kept len) (> kept (- len 20.0))) "container cut length bounded")
  (foreach part parts
    (setq sample (urb:poly-chain-polyline part)
          mid (urb:curve-pt sample (* 0.5 (urb:curve-length sample))))
    (v11:check (not (urb:point-in-poly-2d mid poly)) "kept arc outside container")
    (entdel sample))
  (setq t0 (getvar "MILLISECS")
        r (urb:poly-costado-build sliced "Bordillo" "Interno" "1" "1" 1.0 "ANDEN"))
  (v11:log (strcat "CURB_MS=" (itoa (- (getvar "MILLISECS") t0))))
  (v11:check (and r (cadr r)) "565m curved curb builds as block")
  (v11:check (and r (equal (car r) len 1e-6)) "curb quantity preserves exact length")
  ;; Dos costados de corredor curvo, eleccion en mitad de cada arco.
  (setq boundary (urb:poly-chain-polyline
    '((360.0 0.0 0.414213562373095) (0.0 360.0 0.0)
      (0.0 364.0 -0.414213562373095) (364.0 0.0 0.0))))
  (vla-put-Closed (urb:as-vla-object boundary) :vlax-true)
  (setq chains (urb:lwpoly-points-with-arcs-fine boundary)
        p1 '(254.558441227 254.558441227)
        p2 '(257.386868352 257.386868352)
        *urb-current-tactile-side-point* nil *urb-current-tactile-side-choice* nil
        *urb-current-tactile-side-anchor* p1
        c1 (urb:anden-tactile-chain chains)
        *urb-current-tactile-side-anchor* p2
        c2 (urb:anden-tactile-chain chains))
  (v11:check (and c1 c2 (not (equal c1 c2))) "opposite anchors select opposite curved sides")
  (urb:set-tactile-side-data boundary p2)
  (v11:check (equal (urb:tactile-side-data boundary) p2 1e-7) "confirmed side persists")
  (entdel en) (entdel boundary)
  (v11:log (strcat "SUMMARY pass=" (itoa v11:pass) " fail=" (itoa v11:fail)))
  (if (= v11:fail 0) (v11:log "FINISHED")))
(setq v11:result (vl-catch-all-apply 'v11:run nil))
(if (vl-catch-all-error-p v11:result)
  (v11:log (strcat "ERROR " (vl-catch-all-error-message v11:result))))
(princ)
