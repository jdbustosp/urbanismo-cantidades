(setq logpath "C:/Users/juanbusper/Documents/URBANISMO/work/codex4810/native.txt")
(defun nl (s / f) (setq f (open logpath "a")) (write-line s f) (close f))
(defun nc (s ok) (nl (strcat (if ok "OK " "FALLO ") s)))
(nl "START")
(setq caught (vl-catch-all-apply '(lambda (/ en reg old count ss ref frames attrs)
  (load "C:/Users/juanbusper/Documents/URBANISMO/work/codex4810/current.lsp")
  (nc "carga final" (= *urb-version* "4.81.0"))
  (nc "fase blanca 1.0 queda 0.8" (equal (cdr (urb:composite-phase-state 1.0)) 0.8 1e-8))
  (urb:ensure-layer "URB-TEST-TOP" 8 T)
  (setq en (urb:ramp-quad-poly '(0 0 0) 0.7 1.0 0.0 0.0 3.0 0.2 "URB-TEST-TOP")
        reg (urb:add-region-from-object (urb:as-vla-object en)))
  (setq old (entlast))
  (setq count (vl-catch-all-apply 'urb:fill-tactile-symbols
    (list reg "TOPEROL" 0.7 "URB-TEST-TOP" 0.0 "TEST" 0.2)))
  (nl (strcat "TOP RETURN " (vl-princ-to-string count)))
  (setq ss (ssget "_X" '((0 . "CIRCLE") (8 . "URB-TEST-TOP"))))
  (nc "toperol rotado genera 240 circulos" (and ss (= (sslength ss) 240)))
  (setq en (urb:ramp-quad-poly '(20 0 0) 0.0 1.0 0.0 0.0 3.0 8.0 "URB-RAMPA"))
  (setq frames (list (urb:ramp-end-frame en '(21.5 0 0)) (urb:ramp-end-frame en '(21.5 8 0))))
  (setq ref (urb:build-contour-ramp en frames "PASO-PEATONAL" "1" "1" "Adoquin")
        attrs (urb:block-attribute-values ref))
  (nc "paso 3x8 menos dos remates 0.2: 22.8m2" (equal (atof (cdr (assoc "AREA_M2" attrs))) 22.8 1e-6))
  (nc "tipo paso conservado" (= (cdr (assoc "TIPO" attrs)) "PASO-PEATONAL"))
  (nc "contorno original conservado" (entget en))
  (setq ref (urb:build-contour-ramp en frames "RAMPA-VEHICULAR" "1" "1" "Concreto")
        attrs (urb:block-attribute-values ref))
  (nc "vehicular area total 24m2" (equal (atof (cdr (assoc "AREA_M2" attrs))) 24.0 1e-6))
)))
(if (vl-catch-all-error-p caught) (nl (strcat "ERROR " (vl-catch-all-error-message caught))))
(nl "DONE")
(princ)
