(vl-load-com)
(setq rt:dir "C:/Users/juanbusper/Documents/URBANISMO/work/verify573_20260920/")
(defun rt:log (s / f) (setq f (open (strcat rt:dir "regression574.txt") "a")) (write-line s f) (close f))
(defun rt:assert (ok message)
 (rt:log (strcat (if ok "PASS " "FAIL ") message))
 (if (not ok) (vl-exit-with-error message)))
(defun rt:run (/ road data b axis records stations start span t0 result mov pts newaxis endmid ends a p local ztn zd cf cut fill area sam near raw w snapshots fake i compact surface depth)
 (if (/= (strcase (vl-string-translate "\\" "/" (strcat (getvar "DWGPREFIX") (getvar "DWGNAME")))) (strcase (strcat rt:dir "fixture.dwg"))) (vl-exit-with-error "Wrong fixture"))
 (rt:log (strcat "VERSION " *urb-version*))
 (rt:assert (= *urb-version* "5.7.4") "native engine loaded")
 (rt:assert (equal (urb:road-earthwork-width 100.0 20.0 8.0 1.0 1.0) 7.0 1e-9) "calzada + 1m/side")
 (rt:assert (equal (urb:road-earthwork-width 0.0 0.0 8.0 0.5 1.5) 10.0 1e-9) "nominal fallback / asymmetric overwidth")
 (setq *urb-overexc-depth* 0.5 *urb-road-crossfall* 0.02)
 (foreach handle '("13BBED" "125AAE")
  (setq road (handent handle) data (urb:get-xdata-strings road "URB_VIA")
        snapshots data axis (urb:road-axis-recover road data (nth 22 data))
        b (urb:explode-road-block-boundary road) records (urb:road-design-grade-records road data)
        start (atof (nth 21 data)) span (atof (nth 18 data))
        stations (mapcar '(lambda (r) (list (if (urb:string-equal-p (nth 12 data) "Final") (- (+ start span) (car r)) (+ start (car r))) (cadr r))) records))
  (setq *urb-road-picked-cotas* nil *urb-road-picked-stations* stations)
  ;; Avoid an unrelated interactive text-layer recalibration: use the exact
  ;; persisted grade as independent input. Real Civil surface, not a mock.
  (setq data (urb:replace-nth 8 "" data))
  (urb:set-xdata-strings b "URB_VIA" data)
  (setq t0 (getvar "MILLISECS") result (urb:compute-road-earthworks b data axis) mov (urb:road-movement-data b))
  (rt:log (strcat (nth 1 data) " RESULT " (vl-princ-to-string result) " MOV " (vl-princ-to-string mov) " ms=" (itoa (- (getvar "MILLISECS") t0))))
  (rt:assert (and result mov (= (nth 4 mov) "0")) "complete real surface computation")
  (rt:assert (< (abs (- (atof (nth 5 mov)) (+ (/ (atof (nth 17 data)) span) 2.0))) 0.006) "persisted width includes overwidth")
  ;; Polygon quadrature, same calzada/old axis/grade. Diagnostic comparison
  ;; only: not a TIN composite volume nor the requested overwidth footprint.
  (setq pts (urb:anden-earthwork-raw-points b)
        surface (urb:surface-object-by-name "SUP_TN") depth (urb:road-profile-depth (nth 4 data)))
  (foreach step '(0.5 0.25)
   (setq sam (urb:earthwork-scanline-samples pts step) cut 0.0 fill 0.0 area 0.0 i 0)
   (foreach sample sam
    (setq p (car sample) w (cadr sample) near (vlax-curve-getClosestPointTo axis p)
          raw (vlax-curve-getDistAtPoint axis near)
          zd (- (urb:cota-at-axis-distance raw stations) (* (distance (list (car p) (cadr p)) (list (car near) (cadr near))) *urb-road-crossfall*))
          ztn (urb:surface-elevation surface (car p) (cadr p)))
    (if (and ztn zd)
     (progn (setq cf (urb:cut-fill-at (- ztn (- zd depth))))
      (setq cut (+ cut (* w (car cf))) fill (+ fill (* w (cadr cf))) area (+ area w)))
     (setq i (1+ i))))
   (rt:log (strcat (nth 1 data) " POLYGON step=" (rtos step 2 3) " area=" (rtos area 2 6) " cut=" (rtos cut 2 6) " fill=" (rtos fill 2 6) " missing=" (itoa i))))
  (if (= handle "13BBED")
   (progn
    (setq newaxis (urb:road-axis-from-boundary b))
    (rt:assert newaxis "VIA17 revised automatic axis exists")
    (rt:log (strcat "VIA17 revised axis start=" (vl-princ-to-string (vlax-curve-getStartPoint newaxis)) " end=" (vl-princ-to-string (vlax-curve-getEndPoint newaxis))))
    (urb:invalidate-road-movement b T "PENDIENTE: EJE CAMBIADO")
    (rt:assert (null (urb:road-design-grade-records b (urb:get-xdata-strings b "URB_VIA"))) "axis change removes old grade")
    (rt:assert (null (urb:road-movement-data b)) "axis change removes old volumes")
    (rt:assert (equal snapshots (urb:get-xdata-strings road "URB_VIA")) "original road data unchanged")))
  (entdel b))
 ;; Real no-coverage case outside SUP_TN; no mocked surface function.
 (setq fake (entmakex '((0 . "LWPOLYLINE") (100 . "AcDbEntity") (100 . "AcDbPolyline") (90 . 2) (70 . 0) (10 0.0 0.0) (10 20.0 0.0))))
 (setq b (urb:explode-road-block-boundary (handent "13BBED")) data (urb:get-xdata-strings b "URB_VIA")
       data (urb:replace-nth 8 "" data) data (urb:replace-nth 18 "20.0" data) data (urb:replace-nth 21 "0.0" data)
       *urb-road-picked-stations* '((0.0 2500.0) (20.0 2501.0)) *urb-road-picked-cotas* nil)
 (urb:set-xdata-strings b "URB_VIA" data)
 (setq result (urb:compute-road-earthworks b data fake))
 (rt:assert (null result) "missing terrain rejected by production compute")
 (rt:assert (null (urb:road-movement-data b)) "missing terrain clears previous computed quantities")
 (rt:assert (= (nth 19 (urb:get-xdata-strings b "URB_VIA")) "PENDIENTE: COBERTURA TN INCOMPLETA") "missing terrain explicit pending status")
 (entdel b) (entdel fake)
 ;; Existing lossy grade persistence audit: narrow crest not on retained grid.
 (setq sam nil i 0)
 (repeat 41 (setq sam (cons (list (* i 2.5) 100.0 (if (= i 3) 101.0 100.0)) sam) i (1+ i)))
 (setq compact (urb:compact-road-grade-samples (reverse sam)))
 (rt:log (strcat "PENDING_COMPACT crest_at_7.5=" (rtos (urb:cota-at-axis-distance 7.5 compact) 2 6) " expected=101"))
 (rt:log "FINISHED"))
(if (/= *urb-version* "5.7.4") (load (strcat rt:dir "motor574.lsp")))
(setq rt:r (vl-catch-all-apply 'rt:run nil))
(if (vl-catch-all-error-p rt:r) (rt:log (strcat "FAILED " (vl-catch-all-error-message rt:r))))
(princ)
