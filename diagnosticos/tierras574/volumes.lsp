(vl-load-com)
(setq vt:dir "C:/Users/juanbusper/Documents/URBANISMO/work/verify573_20260920/")
(defun vt:log (s / f) (setq f (open (strcat vt:dir "volumes.txt") "a")) (write-line s f) (close f))
(defun vt:run (/ surface road data axis span start width depth records stations sam totals t0 dense pts k p q j samples sumw)
 (if (/= (strcase (vl-string-translate "\\" "/" (strcat (getvar "DWGPREFIX") (getvar "DWGNAME")))) (strcase (strcat vt:dir "fixture.dwg"))) (vl-exit-with-error "Wrong fixture"))
 (setq surface (urb:surface-object-by-name "SUP_TN"))
 (vt:log (strcat "VERSION " *urb-version* " SURFACE " (vl-princ-to-string surface)))
 (setq *urb-overexc-depth* 0.5 *urb-road-crossfall* 0.02)
 (foreach handle '("13BBED" "125AAE")
  (setq road (handent handle) data (urb:get-xdata-strings road "URB_VIA")
    axis (urb:road-axis-recover road data (nth 22 data))
    span (atof (nth 18 data)) start (atof (nth 21 data))
    width (/ (atof (nth 17 data)) span) depth (urb:road-profile-depth (nth 4 data))
    records (urb:road-design-grade-records road data))
  (setq stations (mapcar '(lambda (r) (list (if (urb:string-equal-p (nth 12 data) "Final") (- (+ start span) (car r)) (+ start (car r))) (cadr r))) records))
  (vt:log (strcat "ROAD " (nth 1 data) " area=" (nth 17 data) " depth=" (rtos depth 2 6) " width=" (rtos width 2 6)))
  (if surface (foreach extra '(0.0 2.0)
    (foreach step '(2.5 1.25 0.625)
     (setq t0 (getvar "MILLISECS"))
     (setq sam (urb:road-section-samples surface axis start span step (nth 12 data) (+ width extra) stations T (urb:station-number (nth 10 data))))
     (setq totals (urb:road-integrate-earthworks sam (+ width extra) depth))
     (vt:log (strcat "extra=" (rtos extra 2 2) " step=" (rtos step 2 3) " cut/fill/skipped=" (vl-princ-to-string totals) " sections=" (itoa (length sam)) " ms=" (itoa (- (getvar "MILLISECS") t0)))))))
  )
 ;; Production dispatcher >200 vertices: densified thin rectangle.
 (setq pts '((0.0 0.0) (10.0 0.0) (10.0 0.2) (0.0 0.2) (0.0 0.0)) dense nil)
 (while (cdr pts)
  (setq p (car pts) q (cadr pts) j 0)
  (repeat 60 (setq dense (cons (list (+ (car p) (* (/ j 60.0) (- (car q) (car p)))) (+ (cadr p) (* (/ j 60.0) (- (cadr q) (cadr p))))) dense) j (1+ j)))
  (setq pts (cdr pts)))
 (setq samples (urb:earthwork-area-samples (reverse dense)) sumw 0.0)
 (foreach sample samples (setq sumw (+ sumw (cadr sample))))
 (vt:log (strcat "PRODUCTION_THIN area=" (rtos sumw 2 8) " expected=2 vertices=" (itoa (length dense))))
 (foreach step '(0.5 0.25 0.125 0.0625)
  (setq samples (urb:earthwork-scanline-samples '((0.0 0.0) (10.0 0.0) (0.0 1.2)) step) sumw 0.0)
  (foreach sample samples (setq sumw (+ sumw (* (cadar sample) (cadr sample)))))
  (vt:log (strcat "TRI step=" (rtos step 2 4) " integral=" (rtos sumw 2 8) " expected=2.4")))
 (vt:log "FINISHED"))
(setq vt:r (vl-catch-all-apply 'vt:run nil))
(if (vl-catch-all-error-p vt:r) (vt:log (strcat "FAILED " (vl-catch-all-error-message vt:r))))
(princ)
