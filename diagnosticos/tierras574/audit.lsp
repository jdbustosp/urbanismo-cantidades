(vl-load-com)
(setq au:dir "C:/Users/juanbusper/Documents/URBANISMO/work/verify573_20260920/")
(defun au:log (s / f) (setq f (open (strcat au:dir "audit.txt") "a")) (write-line s f) (close f))
(defun au:dump (e file / f k len p)
 (setq f (open (strcat au:dir file) "w") k 0 len (vlax-curve-getDistAtParam e (vlax-curve-getEndParam e)))
 (repeat 301 (setq p (vlax-curve-getPointAtDist e (* len (/ k 300.0))) k (1+ k))
 (write-line (strcat (rtos (car p) 2 6) "," (rtos (cadr p) 2 6)) f)) (close f))
(defun au:sum (samples fn / sum)
 (setq sum 0.0)
 (foreach s samples (setq sum (+ sum (* (cadr s) (apply fn (list (caar s) (cadar s))))))) sum)
(defun au:run (/ ss i en data b ax newaxis r len pts sam q area)
 (if (/= (strcase (vl-string-translate "\\" "/" (strcat (getvar "DWGPREFIX") (getvar "DWGNAME")))) (strcase (strcat au:dir "fixture.dwg"))) (vl-exit-with-error "Wrong fixture"))
 (au:log (strcat "VERSION " *urb-version*))
 (au:log (strcat "COLLINEAR middle=" (rtos (urb:design-z-from-picks-plane '((100.0 (0.0 0.0)) (110.0 (5.0 0.0)) (100.0 (10.0 0.0))) 5.0 0.0) 2 6) " expected=110"))
 (setq pts '((0.0 0.0) (10.0 0.0) (10.0 0.2) (0.0 0.2)))
 (setq sam (urb:earthwork-scanline-samples pts 0.5))
 (au:log (strcat "THIN_SCAN area=" (rtos (au:sum sam '(lambda (x y) 1.0)) 2 6) " expected=2"))
 (setq pts '((0.0 0.0) (10.0 0.0) (0.0 1.2)))
 (setq sam (urb:earthwork-scanline-samples pts 0.5))
 (au:log (strcat "TRI_SCAN integral_y=" (rtos (au:sum sam '(lambda (x y) y)) 2 6) " expected=2.4"))
 (au:log (strcat "CUT_FILL delta=-1,h=0.5 -> " (vl-princ-to-string (urb:cut-fill-at -1.0))))
 (setq *urb-overexc-depth* 0.0 *urb-road-crossfall* 0.0)
 (setq sam (list (list 0.0 1.0 0.0 '((-5.0 1.0) (0.0 1.0) (5.0 1.0))) (list 10.0 nil 0.0 nil) (list 20.0 1.0 0.0 '((-5.0 1.0) (0.0 1.0) (5.0 1.0)))))
 (au:log (strcat "MISSING_SECTION " (vl-princ-to-string (urb:road-integrate-earthworks sam 10.0 0.0))))
 ;; W(x)=2+0.2*x, TN=x on x=0..10, design=0. Exact integral=500/3.
 (setq sam (list (list 0.0 0.0 0.0 '((-1.5 0.0) (0.0 0.0) (1.5 0.0))) (list 10.0 10.0 0.0 '((-1.5 10.0) (0.0 10.0) (1.5 10.0)))))
 (au:log (strcat "VARIABLE_WIDTH " (vl-princ-to-string (urb:road-integrate-earthworks sam 3.0 0.0)) " expected_cut=166.666667"))
 (setq ss (ssget "_X" '((0 . "INSERT") (-3 ("URB_VIA")))) i 0)
 (repeat (if ss (sslength ss) 0)
  (setq en (ssname ss i) i (1+ i) data (urb:get-xdata-strings en "URB_VIA"))
  (setq ax (urb:road-axis-recover en data (nth 22 data)) b (urb:explode-road-block-boundary en))
  (au:log (strcat "ROAD " (cdr (assoc 5 (entget en))) " name=" (nth 1 data) " data=" (vl-princ-to-string data)))
  (if b (progn
    (au:dump b (strcat "road-" (nth 1 data) "-boundary.csv"))
    (if ax (au:dump ax (strcat "road-" (nth 1 data) "-oldaxis.csv")))
    (setq newaxis (vl-catch-all-apply 'urb:road-axis-from-boundary (list b)))
    (if (and newaxis (not (vl-catch-all-error-p newaxis)))
     (au:dump newaxis (strcat "road-" (nth 1 data) "-newaxis.csv")))
    (au:log (strcat "NEWAXIS " (vl-princ-to-string newaxis)))
  )))
 (au:log "FINISHED"))
(load (strcat au:dir "motor.lsp"))
(setq au:r (vl-catch-all-apply 'au:run nil))
(if (vl-catch-all-error-p au:r) (au:log (strcat "FAILED " (vl-catch-all-error-message au:r))))
(princ)
