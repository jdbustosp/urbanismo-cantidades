(vl-load-com)
(setq ar:dir "C:/Users/juanbusper/Documents/URBANISMO/work/verify573_20260920/")
(defun ar:log (s / f) (setq f (open (strcat ar:dir "areas574.txt") "a")) (write-line s f) (close f))
(defun ar:run (/ surface axis p x y z e picks result coarse fine delta cf cut fill k j px py depth t0)
 (if (/= (strcase (vl-string-translate "\\" "/" (strcat (getvar "DWGPREFIX") (getvar "DWGNAME")))) (strcase (strcat ar:dir "fixture.dwg"))) (vl-exit-with-error "Wrong fixture"))
 (setq surface (urb:surface-object-by-name "SUP_TN") axis (handent "13BACC")
       p (vlax-curve-getPointAtDist axis 100.0) x (car p) y (cadr p)
       z (+ 0.4 (urb:surface-elevation surface x y)) *urb-overexc-depth* 0.5)
 (setq e (entmakex (list '(0 . "LWPOLYLINE") '(100 . "AcDbEntity") '(100 . "AcDbPolyline") '(90 . 4) '(70 . 1)
   (cons 10 (list (- x 1.0) (- y 0.5))) (cons 10 (list (+ x 1.0) (- y 0.5)))
   (cons 10 (list (+ x 1.0) (+ y 0.5))) (cons 10 (list (- x 1.0) (+ y 0.5))))))
 (setq picks (list (list z (list x y))))
 (ar:log "Controlled 2m2 rectangle, actual SUP_TN, fixed finish=TNcentre+0.40m. This tests shared volume integrator, not each UI/offset builder.")
 (foreach item '(("ANDEN" 0.6) ("SENDERO-test" 0.35) ("ZONA_VERDE" 0.2))
  (setq depth (cadr item) t0 (getvar "MILLISECS") result (urb:earthworks-from-picks e picks depth)
        cut 0.0 fill 0.0 k 0)
  ;; Independent regular 0.025m quadrature, exact rectangular cell areas.
  (repeat 80
   (setq j 0 px (+ (- x 1.0) (* (+ k 0.5) 0.025)))
   (repeat 40
    (setq py (+ (- y 0.5) (* (+ j 0.5) 0.025))
          delta (- (urb:surface-elevation surface px py) (- z depth)))
    (setq cut (+ cut (* 0.000625 (max 0.5 delta)))
          fill (+ fill (* 0.000625 (max 0.0 (- 0.5 delta)))) j (1+ j)))
   (setq k (1+ k)))
  (ar:log (strcat (car item) " engine=" (vl-princ-to-string result) " fine=" (vl-princ-to-string (list cut fill)) " ms=" (itoa (- (getvar "MILLISECS") t0)))))
 (entdel e)
 (ar:log "FINISHED"))
(setq ar:r (vl-catch-all-apply 'ar:run nil))
(if (vl-catch-all-error-p ar:r) (ar:log (strcat "FAILED " (vl-catch-all-error-message ar:r))))
(princ)
