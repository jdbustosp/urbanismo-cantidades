(vl-load-com)
(defun sw:log (s / f) (setq f (open "C:/Users/juanbusper/Documents/URBANISMO/work/verify573_20260920/sidewalk574.txt" "a")) (write-line s f) (close f))
(defun sw:check (ok msg) (sw:log (strcat (if ok "PASS " "FAIL ") msg)) (if (not ok) (vl-exit-with-error msg)))
(defun sw:loose (h / *urb-generation-parent* *urb-generation-start*) (length (urb:generated-objects h)))
(defun sw:val (key at) (atof (urb:attribute-alist-value at key "0")))
(defun sw:run (/ target e b h result t0 bms pms rms def child at guide top n nested sumarea ss)
 (if (/= (strcase (vl-string-translate "\\" "/" (strcat (getvar "DWGPREFIX") (getvar "DWGNAME")))) "C:/USERS/JUANBUSPER/DOCUMENTS/URBANISMO/WORK/VERIFY573_20260920/FIXTURE.DWG") (vl-exit-with-error "Wrong fixture"))
 (sw:log (strcat "VERSION " *urb-version*))
 (foreach e (urb:all-anden-blocks) (if (wcmatch (cdr (assoc 2 (entget e))) "URB_ANDEN_13D362_*") (setq target e)))
 (sw:check target "actual target exists")
 (setq e (urb:explode-anden-block-boundary target) h (cdr (assoc 5 (entget e))))
 (sw:log (strcat "FINISH_AREA=" (rtos (vla-get-Area (vlax-ename->vla-object e)) 2 6)))
 (urb:set-anden-data e "Loseta" "4" "4B" "Si" "Si" "20 x 20 cm" "No" "SUP_TN" "Via creada")
 (setq *urb-current-tactile-side-point* '(83038.9 95306.5 0.0) *urb-current-tactile-side-choice* nil t0 (getvar "MILLISECS"))
 (setq result (urb:build-anden-finish e "Loseta" "Si" "Si" "20 x 20 cm") bms (- (getvar "MILLISECS") t0))
 (sw:log (strcat "BUILD_MS=" (itoa bms)))
 (sw:check result "complete finish builder accepted guide and toperol")
 (setq t0 (getvar "MILLISECS") b (urb:package-anden e) pms (- (getvar "MILLISECS") t0))
 (sw:check b "block packaged")
 (sw:check (= (vla-get-ObjectName b) "AcDbBlockReference") "one block reference")
 (sw:check (= (sw:loose h) 0) "zero loose generated pieces (full modelspace scan)")
 (setq at (urb:block-attribute-values b) def (vla-Item (vla-get-Blocks (urb:doc)) (vla-get-Name b)) guide 0 top 0 nested 0 n 0)
 (vlax-for child def
  (setq n (1+ n))
  (if (= (vla-get-ObjectName child) "AcDbBlockReference") (setq nested (1+ nested)))
  (if (wcmatch (vla-get-Layer child) "*GUIA*") (setq guide (1+ guide)))
  (if (wcmatch (vla-get-Layer child) "*TOPEROL*") (setq top (1+ top))))
 (sw:check (and (> guide 0) (> top 0)) "both tactile layers inside block")
 (setq sumarea (+ (sw:val "LOSETA_LISA_M2" at) (sw:val "ADOQUIN_20X10_M2" at) (sw:val "LOSETA_GUIA_M2" at) (sw:val "LOSETA_TOPEROL_M2" at)))
 (sw:log (strcat "PARTITION=" (rtos sumarea 2 6) " NET=" (rtos (sw:val "AREA_SIN_SOBREANCHO_M2" at) 2 6)))
 (sw:check (< (abs (- sumarea (sw:val "AREA_SIN_SOBREANCHO_M2" at))) 0.01) "finish quantity partition within 0.01m2")
 (setq t0 (getvar "MILLISECS")) (vla-Regen (urb:doc) 1) (setq rms (- (getvar "MILLISECS") t0))
 (sw:log (strcat "TIMES build=" (itoa bms) " pack=" (itoa pms) " regen=" (itoa rms) " total=" (itoa (+ bms pms rms))))
 (sw:log (strcat "COUNTS=" (vl-princ-to-string (list n guide top nested)) " ATTRIBUTES=" (vl-princ-to-string at)))
 (sw:log "FINISHED (no terrain calculation, no DWG save, no full-render validation)"))
(setq sw:r (vl-catch-all-apply 'sw:run nil))
(if (vl-catch-all-error-p sw:r) (sw:log (strcat "FAILED " (vl-catch-all-error-message sw:r))))
(princ)
