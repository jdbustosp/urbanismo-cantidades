(vl-load-com)
(setq ft:dir "C:/Users/juanbusper/Documents/URBANISMO/work/verify573_20260920/")
(defun ft:log (s / f) (setq f (open (strcat ft:dir "final574.txt") "a")) (write-line s f) (close f))
(defun ft:assert (ok msg) (ft:log (strcat (if ok "PASS " "FAIL ") msg)) (if (not ok) (vl-exit-with-error msg)))
(defun ft:integral (pts / sam ar mx my p w t0)
 (setq t0 (getvar "MILLISECS") sam (urb:earthwork-scanline-samples pts 0.5) ar 0.0 mx 0.0 my 0.0)
 (foreach s sam (setq p (car s) w (cadr s) ar (+ ar w) mx (+ mx (* w (car p))) my (+ my (* w (cadr p)))))
 (ft:log (strcat "quadrature=" (vl-princ-to-string (list ar mx my)) " samples=" (itoa (length sam)) " ms=" (itoa (- (getvar "MILLISECS") t0))))
 (list ar mx my))
(defun ft:run (/ a b e data road axis records packed rebuilt start span surf samples t0 newaxis dense pts p q j sam ar full i)
 (if (/= (strcase (vl-string-translate "\\" "/" (strcat (getvar "DWGPREFIX") (getvar "DWGNAME")))) (strcase (strcat ft:dir "fixture.dwg"))) (vl-exit-with-error "Wrong fixture"))
 (ft:log (strcat "VERSION " *urb-version*))
 (ft:assert (equal 110.0 (urb:design-z-from-picks-plane '((100.0 (0.0 0.0)) (110.0 (5.0 0.0)) (100.0 (10.0 0.0))) 5.0 0.0) 1e-8) "collinear middle preserved")
 (ft:assert (equal 105.0 (urb:design-z-from-picks-plane '((100.0 (10.0 0.0)) (100.0 (0.0 0.0)) (110.0 (5.0 0.0))) 2.5 0.0) 1e-8) "collinear unordered interpolation")
 (setq a (ft:integral '((0.0 0.0) (10.0 0.0) (0.0 1.2))))
 (ft:assert (and (equal (car a) 6.0 1e-8) (equal (cadr a) 20.0 1e-8) (equal (caddr a) 2.4 1e-8)) "triangle exact area and linear integrals")
 (setq a (ft:integral '((0.0 0.0) (10.0 0.0) (10.0 0.2) (0.0 0.2))))
 (ft:assert (equal (car a) 2.0 1e-8) "thin rectangle no lost samples")
 (setq a (ft:integral '((0.0 0.0) (3.0 0.0) (3.0 1.0) (1.0 1.0) (1.0 3.0) (0.0 3.0))))
 (ft:assert (and (equal (car a) 5.0 1e-8) (equal (cadr a) 5.5 1e-8) (equal (caddr a) 5.5 1e-8)) "concave L exact area and moments")
 (setq a (ft:integral (reverse '((83000.0 95000.0) (83010.0 95000.0) (83010.0 95000.2) (83000.0 95000.2)))))
 (ft:assert (equal (car a) 2.0 1e-7) "large WCS and reverse orientation")
 (setq pts '((0.0 0.0) (10.0 0.0) (10.0 0.2) (0.0 0.2) (0.0 0.0)) dense nil)
 (while (cdr pts)
  (setq p (car pts) q (cadr pts) j 0)
  (repeat 60 (setq dense (cons (list (+ (car p) (* (/ j 60.0) (- (car q) (car p)))) (+ (cadr p) (* (/ j 60.0) (- (cadr q) (cadr p))))) dense) j (1+ j)))
  (setq pts (cdr pts)))
 (setq sam (urb:earthwork-area-samples dense) ar 0.0)
 (foreach s sam (setq ar (+ ar (cadr s))))
 (ft:assert (equal ar 2.0 1e-8) "production dispatcher 240 vertices")
 ;; Actual road curvature and high vertex count.
 (setq road (handent "13BBED") data (urb:get-xdata-strings road "URB_VIA")
       e (urb:explode-road-block-boundary road) pts (urb:anden-earthwork-raw-points e))
 (setq a (ft:integral pts))
 (ft:assert (< (abs (- (car a) (vla-get-Area (vlax-ename->vla-object e)))) 0.005) "actual curved road footprint area")
 (setq axis (urb:road-axis-recover road data (nth 22 data)) start (atof (nth 21 data)) span (atof (nth 18 data))
       records '((0.0 2500.0) (7.3 2501.0)) i 1)
 (repeat 80 (setq records (append records (list (list (+ 7.3 (* i 2.0)) 2500.0))) i (1+ i)))
 (setq *urb-road-picked-stations* records *urb-road-picked-cotas* nil)
 (urb:store-selected-road-grade e 0.0 170.0 "Inicio")
 (ft:assert (equal 2501.0 (urb:cota-at-axis-distance 7.3 (urb:road-design-grade-records e (urb:get-xdata-strings e "URB_VIA"))) 1e-8) "full grade stored before TN calculation")
 (ft:assert (<= (strlen (nth 32 (urb:get-xdata-strings e "URB_VIA"))) 255) "82-point grade keeps XDATA compatible")
 (setq packed (urb:as-ename (urb:package-road e)))
 (ft:assert packed "road packaged")
 (ft:assert (equal records (urb:road-design-grade-records packed (urb:get-xdata-strings packed "URB_VIA")) 1e-8) "full grade survives block packaging")
 (setq rebuilt (urb:explode-road-block-boundary packed))
 (ft:assert (equal records (urb:road-design-grade-records rebuilt (urb:get-xdata-strings rebuilt "URB_VIA")) 1e-8) "full grade survives edit extraction")
 (ft:assert (equal records (nth 1 (urb:anden-road-grade-for packed)) 1e-8) "sidewalk consumer gets complete grade")
 (urb:invalidate-road-movement rebuilt T "PENDIENTE")
 (ft:assert (null (urb:road-design-grade-records rebuilt (urb:get-xdata-strings rebuilt "URB_VIA"))) "axis replacement invalidates full grade too")
 (setq surf (urb:surface-object-by-name "SUP_TN")
       samples (urb:road-section-samples surf axis start 20.0 2.5 "Inicio" 6.0 records T 0.0))
 (ft:assert (vl-some '(lambda (s) (equal (car s) 7.3 1e-8)) samples) "grade breakpoint sampled off regular grid")
 (urb:delete-anden-block packed) (entdel rebuilt)
 (ft:log "FINISHED"))
(load (strcat ft:dir "motor574-final.lsp"))
(setq ft:r (vl-catch-all-apply 'ft:run nil))
(if (vl-catch-all-error-p ft:r) (ft:log (strcat "FAILED " (vl-catch-all-error-message ft:r))))
(princ)
