(vl-load-com)
(setq v575:dir "C:/Users/juanbusper/Documents/URBANISMO/work/verify573_20260920/")
(defun v575:log (s / f)
  (setq f (open (strcat v575:dir "verify575.txt") "a"))
  (write-line s f) (close f))
(defun v575:check (ok s)
  (v575:log (strcat (if ok "PASS " "FAIL ") s))
  (if (not ok) (vl-exit-with-error s)))
(defun v575:aval (tag vals) (atof (urb:attribute-alist-value vals tag "0")))
(defun v575:weighted-x (samples / total s)
  (setq total 0.0)
  (foreach s samples (setq total (+ total (* (cadr s) (caar s)))))
  total)
(defun v575:synthetic (/ boundary axis footprint points samples area moment)
  ;; W(x)=2+0.2x; los costados miden sqrt(101). El sobreancho es
  ;; perpendicular a cada costado: area exacta=30+sqrt(101), y el
  ;; primer momento en x=500/3+5*sqrt(101). El modelo viejo por ancho
  ;; promedio daba 200 y no representaba el ensanche local.
  (setq boundary
    (entmakex '((0 . "LWPOLYLINE") (100 . "AcDbEntity")
      (100 . "AcDbPolyline") (90 . 4) (70 . 1)
      (10 0.0 -1.0) (10 10.0 -2.0) (10 10.0 2.0) (10 0.0 1.0))))
  (setq axis
    (entmakex '((0 . "LINE") (100 . "AcDbEntity") (100 . "AcDbLine")
      (10 0.0 0.0 0.0) (11 10.0 0.0 0.0))))
  (setq footprint (urb:road-earthwork-footprint boundary axis 0.5 0.5 "Inicio"))
  (v575:log (strcat "SYNTH_FOOTPRINT "
    (vl-princ-to-string *urb-last-road-footprint-diagnostic*)))
  (v575:check footprint "variable-width footprint exists")
  (setq area (vla-get-Area (vlax-ename->vla-object footprint))
        points (urb:anden-earthwork-raw-points footprint)
        samples (urb:earthwork-scanline-samples points 0.125)
        moment (v575:weighted-x samples))
  (v575:log (strcat "SYNTH area=" (rtos area 2 8)
    " moment_x=" (rtos moment 2 8) " old_average=200.00000000"))
  (v575:check (< (abs (- area (+ 30.0 (sqrt 101.0)))) 1e-5)
    "variable-width exact perpendicular footprint area")
  (v575:check (< (abs (- moment (+ (/ 500.0 3.0) (* 5.0 (sqrt 101.0))))) 0.01)
    "variable-width integral follows local width, not average width")
  (entdel footprint) (entdel boundary) (entdel axis))
(defun v575:road (handle / road data original axis b records start span stations
  result mov footprint info vals packed expected-area independent raw-grade plan025 plan0125)
  (setq road (handent handle) original (urb:get-xdata-strings road "URB_VIA")
        data original axis (urb:road-axis-recover road data (nth 22 data))
        b (urb:explode-road-block-boundary road)
        records (urb:road-design-grade-records road data)
        start (atof (nth 21 data)) span (atof (nth 18 data))
        stations (mapcar '(lambda (r)
          (list (if (urb:string-equal-p (nth 12 data) "Final")
            (- (+ start span) (car r)) (+ start (car r))) (cadr r))) records))
  (v575:check (and b axis (>= (length stations) 2))
    (strcat (nth 1 data) " real boundary/axis/grade available"))
  (setq data (urb:replace-nth 8 "" data)
        *urb-road-picked-cotas* nil *urb-road-picked-stations* stations)
  (urb:set-xdata-strings b "URB_VIA" data)
  (setq result (urb:compute-road-earthworks b data axis)
        mov (urb:road-movement-data b)
        info (vlax-ldata-get b "URB_VIA_HUELLA"))
  (v575:check (and result mov (wcmatch (nth 2 mov) "HUELLA_REAL_CONVERGENCIA_*")
    info) (strcat (nth 1 data) " production uses converged real footprint"))
  (setq footprint (urb:road-earthwork-footprint b axis
      (atof (nth 14 data)) (atof (nth 15 data)) (nth 12 data))
        expected-area (vla-get-Area (vlax-ename->vla-object footprint))
        raw-grade (mapcar '(lambda (r) (list (car r) (cadr r))) stations)
        plan025 (urb:road-plan-integral (urb:anden-earthwork-raw-points footprint)
          (urb:surface-object-by-name "SUP_TN") axis raw-grade start span
          (nth 12 data) (urb:road-profile-depth (nth 4 data)) 0.25
          (max 1.0 (atof (nth 11 data))))
        plan0125 (urb:road-plan-integral (urb:anden-earthwork-raw-points footprint)
          (urb:surface-object-by-name "SUP_TN") axis raw-grade start span
          (nth 12 data) (urb:road-profile-depth (nth 4 data)) 0.125
          (max 1.0 (atof (nth 11 data)))))
  (v575:log (strcat (nth 1 data) " result=" (vl-princ-to-string result)
    " footprint=" (rtos expected-area 2 6)
    " step025=" (vl-princ-to-string (list (car plan025) (cadr plan025)))
    " step0125=" (vl-princ-to-string (list (car plan0125) (cadr plan0125)))))
  (v575:check (< (abs (- (car info) expected-area)) 1e-5)
    (strcat (nth 1 data) " stored footprint area equals geometry"))
  (v575:check (and (= (nth 2 plan0125) 0)
    (< (abs (- expected-area (nth 3 plan0125))) (max 0.001 (* expected-area 0.0001))))
    (strcat (nth 1 data) " complete TN coverage over footprint"))
  (v575:check (and
    (<= (abs (- (car plan025) (car plan0125))) (max 0.02 (* 0.005 (abs (car plan0125)))))
    (<= (abs (- (cadr plan025) (cadr plan0125))) (max 0.02 (* 0.005 (abs (cadr plan0125))))))
    (strcat (nth 1 data) " 0.25/0.125m volume convergence within 0.5%"))
  (entdel footprint)
  (setq packed (urb:package-road b) vals (urb:block-attribute-values packed))
  (v575:check (< (abs (- (v575:aval "VIA_AREA_SOBREANCHO_M2" vals) expected-area)) 0.011)
    (strcat (nth 1 data) " property total area equals earthwork footprint"))
  (v575:check (< (abs (- (v575:aval "VIA_SOBREANCHO_M2" vals)
      (- expected-area (atof (nth 17 data))))) 0.011)
    (strcat (nth 1 data) " property exclusive overwidth equals geometry"))
  (v575:check (vlax-ldata-get (vlax-vla-object->ename packed) "URB_VIA_HUELLA")
    (strcat (nth 1 data) " footprint metadata survives packaging"))
  (v575:check (equal original (urb:get-xdata-strings road "URB_VIA"))
    (strcat (nth 1 data) " original road unchanged"))
  (urb:safe-delete packed))
(defun v575:run ()
  (v575:log (strcat "VERSION " *urb-version*))
  (v575:check (= *urb-version* "5.7.5") "engine version")
  (setq *urb-overexc-depth* 0.5 *urb-road-crossfall* 0.02)
  (v575:synthetic)
  (v575:road "13BBED")
  (v575:road "125AAE")
  (v575:log "FINISHED"))
(setq v575:r (vl-catch-all-apply 'v575:run nil))
(if (vl-catch-all-error-p v575:r)
  (v575:log (strcat "FAILED " (vl-catch-all-error-message v575:r))))
(princ)
