(defun cc:anden (/ en t0 build block)
 (setq en (cc:curve 1800.0) t0 (getvar "MILLISECS"))
 (urb:set-anden-data en "Loseta" "5" "5A" "Si" "Si" "40 x 40 cm" "No" "Seleccionar en dibujo" "Via creada")
 (urb:poly-costados-build en "Bordillo" "Sardinel" "Interno" "5" "5A" "Anden")
 (urb:anden-clip-contour en)
 (setq build (urb:build-anden-finish en "Loseta" "Si" "Si" "40 x 40 cm"))
 (cc:log (list 'ANDEN_CURVO 'BUILD build))
 (if build (setq block (urb:package-anden en)))
 (cc:log (list 'ANDEN_CURVO 'MS (- (getvar "MILLISECS") t0) 'BLOCK (if block T nil) 'ATTRS (if block (urb:block-attribute-values block)))))
