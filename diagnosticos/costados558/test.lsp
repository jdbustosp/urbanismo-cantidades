(vl-load-com)
(if (/= (strcase (strcat (getvar "DWGPREFIX") (getvar "DWGNAME"))) "C:\\USERS\\JUANBUSPER\\DOCUMENTS\\CHATGPT\\COMPLEMENTO AUTOCAD\\WORK\\COSTADOS558\\FIXTURE.DWG") (exit))
(setq cc:dir "C:/Users/juanbusper/Documents/ChatGPT/COMPLEMENTO AUTOCAD/work/costados558/" *urb-suppress-auto-migration* T)
(defun cc:log (x / f) (setq f (open (strcat cc:dir "result.txt") "a")) (write-line (vl-princ-to-string x) f) (close f))
(defun cc:curve (y)
 (entmakex (list '(0 . "LWPOLYLINE") '(100 . "AcDbEntity") '(100 . "AcDbPolyline") '(90 . 6) '(70 . 1)
 (cons 10 (list 1000.0 y)) '(42 . 0.12) (cons 10 (list 1030.0 y)) '(42 . -0.10)
 (cons 10 (list 1060.0 y)) '(42 . 0.0) (cons 10 (list 1060.0 (+ y 6))) '(42 . 0.06)
 (cons 10 (list 1030.0 (+ y 9))) '(42 . -0.10) (cons 10 (list 1000.0 (+ y 2))) '(42 . 0.0))))
(defun cc:case (tag y mode / en obj before e hatch reg net data t0 prefcount)
 (setq en (cc:curve y) obj (vlax-ename->vla-object en) before (entlast) cc:queue (list en) t0 (getvar "MILLISECS"))
 (cc:log (list tag 'VALID (urb:anden-shape-ok-p (urb:lwpoly-points-with-arcs en))))
 (urb:poly-element-draw (assoc "SEND-ECO" *urb-send-tipos*) "5" "5A" "Bordillo" "Sardinel" mode "URB_SENDERO")
 (setq e (entnext before) prefcount 0)
 (while e
  (cond ((and (= (cdr (assoc 0 (entget e))) "HATCH") (= (cdr (assoc 8 (entget e))) "URB-SENDERO-ECOLOGICO")) (setq hatch (vlax-ename->vla-object e)))
   ((urb:get-xdata-strings e "URB_PREFAB_BLOCK") (setq prefcount (1+ prefcount))))
  (setq e (entnext e)))
 (setq reg (urb:anden-region-from-object obj) reg (urb:apply-anden-cutouts reg) net (vla-get-Area reg) data (urb:get-xdata-strings en "URB_SENDERO"))
 (cc:log (list tag 'MS (- (getvar "MILLISECS") t0) 'PREFABS prefcount 'GROSS (vla-get-Area obj) 'NET net
  'HATCH (if hatch (vla-get-Area hatch)) 'OVERLAP (if hatch (- (vla-get-Area hatch) net))
  'QUANTITY (- (vla-get-Area obj) (atof (urb:safe-string (nth 6 data) "0")))))
 (urb:safe-delete reg))
(defun cc:anden (/ en t0 build block)
 (setq en (cc:curve 1200.0) t0 (getvar "MILLISECS"))
 (urb:set-anden-data en "Loseta" "5" "5A" "Si" "Si" "40 x 40 cm" "No" "Seleccionar en dibujo" "Via creada")
 (urb:poly-costados-build en "Bordillo" "Sardinel" "Interno" "5" "5A" "Anden")
 (urb:anden-clip-contour en)
 (setq build (urb:build-anden-finish en "Loseta" "Si" "Si" "40 x 40 cm"))
 (cc:log (list 'ANDEN_CURVO 'BUILD build))
 (if build (setq block (urb:package-anden en)))
 (cc:log (list 'ANDEN_CURVO 'MS (- (getvar "MILLISECS") t0) 'BLOCK (if block T nil) 'ATTRS (if block (urb:block-attribute-values block)))))
(defun cc:run ()
 (load (strcat cc:dir "baseline.lsp"))
 (defun urb:draw-closed-polyline (/ en) (setq en (car cc:queue) cc:queue (cdr cc:queue)) (if (and en (urb:anden-shape-ok-p (urb:lwpoly-points-with-arcs en))) en))
 (defun urb:pick-design-cotas () nil)
 (cc:case 'BASE_INTERNO 1000.0 "Interno")
 (cc:case 'BASE_EXTERNO 1100.0 "Externo")
 (cc:anden)
 (command "_.QSAVE")
 (cc:log 'DONE))
(setq cc:r (vl-catch-all-apply 'cc:run nil))
(if (vl-catch-all-error-p cc:r) (cc:log (list 'ERROR (vl-catch-all-error-message cc:r))))
(princ)
