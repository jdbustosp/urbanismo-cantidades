(defun cn:run ()
 (cc:log 'CANDIDATE_BEGIN)
 (load "C:/Users/juanbusper/Documents/ChatGPT/COMPLEMENTO AUTOCAD/work/costados558/candidate.lsp")
 (defun urb:draw-closed-polyline (/ en) (setq en (car cc:queue) cc:queue (cdr cc:queue)) (if (and en (urb:anden-shape-ok-p (urb:lwpoly-points-with-arcs en))) en))
 (defun urb:pick-design-cotas () nil)
 (cc:case 'CAND_INTERNO 1500.0 "Interno")
 (cc:case 'CAND_EXTERNO 1600.0 "Externo")
 (load "C:/Users/juanbusper/Documents/ChatGPT/COMPLEMENTO AUTOCAD/work/costados558/anden-candidate.lsp")
 (cc:anden)
 (command "_.QSAVE")
 (cc:log 'CANDIDATE_DONE))
(setq cn:r (vl-catch-all-apply 'cn:run nil))
(if (vl-catch-all-error-p cn:r) (cc:log (list 'ERROR (vl-catch-all-error-message cn:r))))
(princ)
