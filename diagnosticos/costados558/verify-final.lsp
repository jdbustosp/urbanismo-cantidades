(defun cv:check (label ok) (if (not ok) (setq cv:fail (1+ cv:fail))) (cc:log (list (if ok 'OK 'FAIL) label)))
(defun cv:poly (points / en) (setq en (urb:open-poly-from-points points 0.0)) (vla-put-Closed (vlax-ename->vla-object en) :vlax-true) en)
(defun cv:end-cap-only (ref outside / items o ends box width ok)
 ;; La cara final es perpendicular a la tangente; un cierre oblicuo del
 ;; sendero puede dejar una cuna en el remate. Verificar que TODA la caja
 ;; residual este a <=1.5 anchos de UN extremo, nunca en el cuerpo lateral.
 (setq width (atof (nth 3 (urb:get-xdata-strings ref "URB_PREFAB_BLOCK")))
       box (urb:object-box-points outside)
       items (urb:variant-object-list (vla-Explode (urb:as-vla-object ref))))
 (foreach o items
  (if (= (urb:generated-role o) "EXTERIOR")
   (setq ends (list (vlax-curve-getStartPoint o) (vlax-curve-getEndPoint o)))))
 (setq ok (vl-some '(lambda (end) (not (vl-some '(lambda (p) (> (distance p end) (* 1.5 width))) box))) ends))
 (foreach o items (urb:safe-delete o))
 ok)
(defun cv:case (tag y shape mode left / en obj en2 vb loop area before e hatch refs reg cut intersection inarea footprint data dt t0 outside side-ok)
 (setq en
  (cond
   ((= shape "U") (cv:poly (mapcar '(lambda (p) (list (+ 1000 (car p)) (+ y (cadr p)))) '((0 0) (30 0) (30 30) (24 30) (24 6) (6 6) (6 30) (0 30)))))
   ((= shape "WIDE") (cv:poly (mapcar '(lambda (p) (list (+ 1000 (car p)) (+ y (cadr p)))) '((0 0) (10 0) (20 -8) (30 0) (40 0) (40 2) (30 2) (20 10) (10 2) (0 2)))))
   (T (cc:curve y))))
 (if (= shape "REVERSE")
  (progn
   (setq vb (urb:lwpoly-vertex-bulges en) loop (urb:loop-reverse (mapcar '(lambda (p b) (cons p b)) (car vb) (cadr vb))))
   (setq en2 (urb:poly-chain-polyline (mapcar '(lambda (v) (list (caar v) (cadar v) (cdr v))) loop)))
   (vla-put-Closed (vlax-ename->vla-object en2) :vlax-true) (entdel en) (setq en en2)))
 (setq obj (vlax-ename->vla-object en) area (vla-get-Area obj) before (entlast) cc:queue (list en) t0 (getvar "MILLISECS"))
 (urb:poly-element-draw (assoc "SEND-ECO" *urb-send-tipos*) "5" "5A" "Bordillo" left mode "URB_SENDERO")
 (setq e (entnext before))
 (while e
  (cond
   ((and (= (cdr (assoc 0 (entget e))) "HATCH") (= (cdr (assoc 8 (entget e))) "URB-SENDERO-ECOLOGICO")) (setq hatch (vlax-ename->vla-object e)))
   ((urb:get-xdata-strings e "URB_PREFAB_BLOCK") (setq refs (cons e refs))))
  (setq e (entnext e)))
 (cv:check (list tag 'PREFABS) (= (length refs) (if (= left "Ninguno") 1 2)))
 (setq reg (urb:anden-region-from-object obj) inarea 0.0 footprint 0.0 side-ok T)
 (foreach ref refs
  (setq cut (urb:block-footprint-region ref) intersection (vla-Copy reg))
  (setq footprint (+ footprint (vla-get-Area cut)))
  (if (= mode "Interno")
   (progn (setq outside (vla-Copy cut)) (vla-Boolean outside 2 (vla-Copy reg))
    (if (and (> (vla-get-Area outside) 1e-5) (not (cv:end-cap-only ref outside))) (setq side-ok nil))
    (urb:safe-delete outside)))
  (vla-Boolean intersection 1 cut)
  (setq inarea (+ inarea (vla-get-Area intersection)))
  (urb:safe-delete cut) (urb:safe-delete intersection))
 (cv:check (list tag 'PREFAB_SIDE) (if (= mode "Interno") side-ok (< inarea 1e-5)))
 (setq reg (urb:apply-anden-cutouts reg) data (urb:get-xdata-strings en "URB_SENDERO"))
 (cv:check (list tag 'NO_HATCH_OVERLAP) (and hatch (equal (vla-get-Area hatch) (vla-get-Area reg) 1e-5)))
 (cv:check (list tag 'QUANTITY) (equal (- area (atof (nth 6 data))) (vla-get-Area reg) 1e-5))
 (cv:check (list tag 'CONTOUR_UNCHANGED) (equal area (vla-get-Area obj) 1e-8))
 (cc:log (list tag 'MS (- (getvar "MILLISECS") t0) 'GROSS area 'NET (vla-get-Area reg) 'PREFAB_AREA footprint 'INSIDE inarea))
 (urb:safe-delete reg))
(defun cv:run ()
 (setq cv:fail 0)
 (cv:case 'CURVO_INTERNO 3000.0 "CURVE" "Interno" "Sardinel")
 (cv:case 'CURVO_EXTERNO 3100.0 "CURVE" "Externo" "Sardinel")
 (cv:case 'INVERSO_INTERNO 3200.0 "REVERSE" "Interno" "Sardinel")
 (cv:case 'INVERSO_EXTERNO 3300.0 "REVERSE" "Externo" "Sardinel")
 (cv:case 'UN_COSTADO 3400.0 "CURVE" "Interno" "Ninguno")
 (cv:case 'U_INTERNO 3500.0 "U" "Interno" "Sardinel")
 (cv:case 'U_EXTERNO 3600.0 "U" "Externo" "Sardinel")
 (cv:case 'VARIABLE_INTERNO 3700.0 "WIDE" "Interno" "Sardinel")
 (command "_.QSAVE")
 (cc:log (list 'VERIFY_DONE 'FAILURES cv:fail)))
(setq cv:r (vl-catch-all-apply 'cv:run nil))
(if (vl-catch-all-error-p cv:r) (cc:log (list 'ERROR (vl-catch-all-error-message cv:r))))
(princ)
