(vl-load-com)
(setq t16:out "C:/Users/juanbusper/Documents/URBANISMO/work/bloques5716/native.txt" t16:pass 0 t16:fail 0)
(defun t16:log (s / f) (setq f (open t16:out "a")) (write-line s f) (close f))
(defun t16:check (ok s)
  (if ok (setq t16:pass (1+ t16:pass)) (setq t16:fail (1+ t16:fail)))
  (t16:log (strcat (if ok "PASS " "FAIL ") s)))
;; Real COM packaging/attributes. Only user input is replaced; error injected at picker.
(defun urb:confirm-meter-units () T)
(defun urb:dialog-green (a b c) '("4" "4B" 0.2))
(defun t16:rect ()
  (entmakex '((0 . "LWPOLYLINE") (100 . "AcDbEntity") (100 . "AcDbPolyline")
    (90 . 4) (70 . 1) (10 0.0 0.0) (10 10.0 0.0) (10 10.0 4.0) (10 0.0 4.0))))
(defun urb:draw-green-boundary () (setq t16:boundary (t16:rect)))
(defun urb:draw-closed-polyline ()
  (if t16:draw (progn (setq t16:draw nil t16:boundary (t16:rect)) t16:boundary)))
(defun urb:poly-costados-interactive (en etapa sub tipo) nil)
(defun urb:area-earthwork-picks (en editing)
  (t16:check (null editing) "creation picker mode")
  (t16:check (null (entget t16:boundary)) "original already packaged BEFORE picker")
  (if (= t16:mode "error") (/ 1 0) nil))
(defun t16:run (/ kind ss en atts before)
  (if (/= (strcase (vl-string-translate "\\" "/" (strcat (getvar "DWGPREFIX") (getvar "DWGNAME"))))
    "C:/USERS/JUANBUSPER/DOCUMENTS/URBANISMO/WORK/BLOQUES5716/FIXTURE.DWG") (exit))
  (t16:check (= *urb-version* "5.7.16") "version")
  (foreach kind '("ZONA_VERDE" "SENDERO")
    (foreach t16:mode '("nil" "error")
      (setq before (vla-get-Count (urb:space)))
      (if (= kind "ZONA_VERDE") (urb:create-green-zone-command)
        (progn (setq t16:draw T)
          (urb:poly-element-draw (car *urb-send-tipos*) "4" "4B" "Ninguno" "Ninguno" "Externo" "URB_SENDERO")))
      (setq ss (ssget "_X" (list '(0 . "INSERT") (list -3 (list (if (= kind "ZONA_VERDE") "URB_GREEN_BLOCK" "URB_SENDERO"))))))
      (t16:check ss (strcat kind " INSERT with metadata survives " t16:mode))
      (setq en (ssname ss (1- (sslength ss))) atts (urb:block-attribute-values (urb:as-vla-object en)))
      (t16:check (equal (atof (cdr (assoc "AREA_M2" atts))) 40.0 0.001) "area attribute 40 m2")
      (t16:check (= (1+ before) (vla-get-Count (urb:space))) "one new INSERT, no loose hatch or temporary boundary")
      (t16:check (null (urb:get-xdata-strings en (if (= kind "ZONA_VERDE") "URB_GREEN_MOV" "URB_SEND_MOV"))) "MT remains pending")))
  (t16:log (strcat "SUMMARY pass=" (itoa t16:pass) " fail=" (itoa t16:fail)))
  (if (= t16:fail 0) (t16:log "FINISHED")))
(t16:log "STARTED")
(setq t16:r (vl-catch-all-apply 't16:run nil))
(if (vl-catch-all-error-p t16:r) (t16:log (strcat "ERROR " (vl-catch-all-error-message t16:r))))
(princ)
