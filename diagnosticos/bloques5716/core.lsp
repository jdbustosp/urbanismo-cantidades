(setq t16:out "C:/Users/juanbusper/Documents/URBANISMO/work/bloques5716/core.txt" t16:pass 0 t16:fail 0)
(defun t16:log (s / f) (setq f (open t16:out "a")) (write-line s f) (close f))
(defun t16:check (ok s)
  (if ok (setq t16:pass (1+ t16:pass)) (setq t16:fail (1+ t16:fail)))
  (t16:log (strcat (if ok "PASS " "FAIL ") s)))
;; Adapters ONLY for fault injection: this does not validate COM or a TIN.
(defun urb:area-earthwork-clear (en app) (setq t16:cleared (list en app)))
(defun t16:result ()
  (cond ((= t16:mode "error") (/ 1 0))
        ((= t16:mode "cancel") (exit))
        ((= t16:mode "ok") '(12.0 34.0)) (T nil)))
(defun urb:green-earthworks-run (en thickness editing)
  (t16:check (null editing) "green creation uses Sin, not Conservar") (t16:result))
(defun urb:sendero-earthworks-run (en editing)
  (t16:check (null editing) "sendero creation uses Sin, not Conservar") (t16:result))
(t16:check (= *urb-version* "5.7.16") "version")
(foreach kind '("ZONA_VERDE" "SENDERO")
  (foreach t16:mode '("nil" "error" "cancel" "ok")
    (setq t16:cleared nil t16:r (vl-catch-all-apply 'urb:area-created-earthworks (list 'test kind 0.2)))
    (t16:check (not (vl-catch-all-error-p t16:r)) (strcat kind " survives " t16:mode))
    (t16:check (if (= t16:mode "ok") (and (equal t16:r '(12.0 34.0)) (null t16:cleared))
      (and (null t16:r) (equal t16:cleared (list 'test (if (= kind "ZONA_VERDE") "URB_GREEN_MOV" "URB_SEND_MOV")))))
      (strcat kind " pending/success state " t16:mode))))
(t16:check (equal (urb:cota-at-axis-distance 10.0 '((0.0 100.0) (20.0 104.0))) 102.0 1e-8) "profile regression")
(t16:log (strcat "SUMMARY pass=" (itoa t16:pass) " fail=" (itoa t16:fail)))
(if (= t16:fail 0) (t16:log "FINISHED"))
(princ)
