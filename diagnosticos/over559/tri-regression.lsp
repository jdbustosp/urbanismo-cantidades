(load (strcat ov:dir "candidate.lsp"))
(load (strcat ov:dir "old-triangulate.lsp"))
(defun ov:tri-regression (/ k n j pts scale center before after bad t0)
 (setq ov:seed 73.0 k 0 bad 0 t0 (getvar "MILLISECS"))
 (repeat 240
  (setq n (+ 4 (fix (* 26 (ov:random)))) j 0 pts nil
        scale (nth (rem k 4) '(1.0 0.0001 0.001 100.0))
        center (if (= 0 (rem k 2)) '(82900.0 95400.0) '(0.0 0.0)))
  (repeat n (setq pts (cons (polar center (/ (* 2.0 pi j) n) (* scale (+ 10 (* 10 (ov:random))))) pts) j (1+ j)))
  (if (= 0 (rem k 3)) (setq pts (reverse pts)))
  (setq before (ov:old-triangulate pts) after (urb:triangulate-polygon pts))
  (if (not (equal before after 0.0)) (progn (setq bad (1+ bad)) (ov:log (list 'TRI_DIFF k))))
  (setq k (1+ k)))
 (ov:check 'TRI_EXACT_EQUIVALENCE_240 (= bad 0))
 (ov:log (list 'TRI_REGRESSION 'CASES 240 'DIFF bad 'MS (- (getvar "MILLISECS") t0))))
(ov:tri-regression)
(setq ov:old-samples ov:samples ov:t (getvar "MILLISECS"))
(ov:log 'FAST_MESH_BEGIN)
(setq ov:samples (vl-catch-all-apply 'urb:earthwork-area-samples (list ov:pts)))
(ov:log (list 'FAST_MESH 'MS (- (getvar "MILLISECS") ov:t) 'N (if (vl-catch-all-error-p ov:samples) (vl-catch-all-error-message ov:samples) (length ov:samples))))
(if ov:old-samples
 (ov:check 'REAL_MESH_EXACT_EQUIVALENCE (equal ov:old-samples ov:samples 0.0))
 (ov:log 'BASELINE_REAL_MESH_INTERRUPTED_NO_FULL_EQUIVALENCE_CLAIM))
(if (and ov:samples (not (vl-catch-all-error-p ov:samples)))
 (progn
  (setq ov:sum (apply '+ (mapcar 'cadr ov:samples)) ov:area (urb:anden-earthwork-area ov:newblock))
  (ov:log (list 'FAST_MESH_AREA ov:sum 'EXACT ov:area 'DELTA (- ov:sum ov:area)))
  (ov:check 'EARTH_MESH_AREA (<= (abs (- ov:sum ov:area)) (max 0.001 (* ov:area 0.0001))))))
(ov:log 'TRI_DONE)
(princ)
