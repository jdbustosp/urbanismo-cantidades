(defun ov:arc-check (/ b en obj pts p near maxd area poly)
 (foreach b '(0.000000001 -0.000000001 0.00001 -0.00001 0.1 -0.1 1.0 -1.0 2.0 -2.0)
  (setq en (entmakex (list '(0 . "LWPOLYLINE") '(100 . "AcDbEntity") '(100 . "AcDbPolyline") '(90 . 4) '(70 . 1)
    '(10 82900.0 95400.0) (cons 42 b) '(10 82910.0 95400.0) '(42 . 0.0) '(10 82910.0 95420.0) '(42 . 0.0) '(10 82900.0 95420.0) '(42 . 0.0))))
  (setq pts (urb:anden-earthwork-raw-points en) maxd 0.0)
  (foreach p pts (setq near (vlax-curve-getClosestPointTo en p) maxd (max maxd (distance near p))))
  (ov:check (list 'ARC_NATIVE_DISTANCE b) (< maxd 0.000001))
  (setq poly (urb:open-poly-from-points pts 0.0))
  (vla-put-Closed (vlax-ename->vla-object poly) :vlax-true)
  (setq area (vla-get-Area (vlax-ename->vla-object en)))
  (ov:check (list 'ARC_AREA b) (< (abs (- area (vla-get-Area (vlax-ename->vla-object poly)))) 0.002))
  (entdel en) (entdel poly)))
(ov:arc-check)
(ov:log 'ARC_CHECK_DONE)
(princ)
