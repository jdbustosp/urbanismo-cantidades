(defun ov:build-real (/ en data t0 t1 ok block attrs)
 (setq en (vlax-vla-object->ename (vla-Copy (vlax-ename->vla-object ov:lastbase))))
 (urb:set-anden-data en "Loseta" "4" "4B" "Si" "Si" "40 x 40 cm" "No" "Seleccionar en dibujo" "Via creada")
 (setq t0 (getvar "MILLISECS") ok (urb:build-anden-finish en "Loseta" "Si" "Si" "40 x 40 cm") t1 (getvar "MILLISECS"))
 (ov:log (list 'REAL_BUILD 'MS (- t1 t0) 'OK ok))
 (if ok (setq block (urb:package-anden en)))
 (ov:log (list 'REAL_PACKAGE 'MS (- (getvar "MILLISECS") t1) 'TOTAL_MS (- (getvar "MILLISECS") t0) 'BLOCK (if block (vla-get-Handle block))))
 (ov:check 'REAL_SINGLE_BLOCK (and block (= (vla-get-ObjectName block) "AcDbBlockReference")))
 (if block
  (progn
   (setq attrs (urb:block-attribute-values block))
   (ov:log (list 'REAL_ATTRS attrs))
   (setq ov:newblock block)))
 block)
(ov:log 'BUILD_BEGIN)
(setq ov:buildresult (vl-catch-all-apply 'ov:build-real nil))
(ov:log (list 'BUILD_DONE (if (vl-catch-all-error-p ov:buildresult) (vl-catch-all-error-message ov:buildresult) 'OK)))
(command "_.QSAVE")
(princ)
