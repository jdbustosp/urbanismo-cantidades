(load (strcat ov:dir "candidate.lsp"))
(ov:log 'STABLE_MESH_BEGIN)
(setq ov:fail 0 ov:newblock (vlax-ename->vla-object (handent "7513")))
(setq ov:t (getvar "MILLISECS") ov:pts (urb:anden-earthwork-points ov:newblock))
(ov:log (list 'STABLE_POINTS 'N (length ov:pts) 'MS (- (getvar "MILLISECS") ov:t)))
(setq ov:pl (urb:open-poly-from-points ov:pts 0.0))
(vla-put-Closed (vlax-ename->vla-object ov:pl) :vlax-true)
(ov:log (list 'SAMPLED_AREA (vla-get-Area (vlax-ename->vla-object ov:pl)) 'EXACT (urb:anden-earthwork-area ov:newblock)))
(setq ov:t (getvar "MILLISECS") ov:samples (vl-catch-all-apply 'urb:earthwork-area-samples (list ov:pts)))
(ov:log (list 'STABLE_MESH 'MS (- (getvar "MILLISECS") ov:t) 'N (if (vl-catch-all-error-p ov:samples) (vl-catch-all-error-message ov:samples) (length ov:samples))))
(if (and ov:samples (not (vl-catch-all-error-p ov:samples)))
 (progn
  (setq ov:sum (apply '+ (mapcar 'cadr ov:samples)) ov:area (urb:anden-earthwork-area ov:newblock))
  (ov:log (list 'STABLE_MESH_AREA ov:sum 'EXACT ov:area 'DELTA (- ov:sum ov:area)))
  (ov:check 'STABLE_EARTH_MESH_AREA (<= (abs (- ov:sum ov:area)) (max 0.001 (* ov:area 0.0001))))))
(ov:log 'STABLE_DONE)
(princ)
