(load (strcat ov:dir "candidate.lsp"))
(setq ov:fail 0)
(defun ov:check (label ok) (if (not ok) (setq ov:fail (1+ ov:fail))) (ov:log (list (if ok 'OK 'FAIL) label)))
(defun ov:poly (pts / en) (setq en (urb:open-poly-from-points pts 0.0)) (vla-put-Closed (vlax-ename->vla-object en) :vlax-true) en)
(defun ov:case (label en expected / data t0 result gap area reg cut err remaining)
 (setq data (entget en) gap (getvar "OFFSETGAPTYPE") t0 (getvar "MILLISECS") result (urb:anden-overwidth-contour en 1.0))
 (ov:log (list label 'MS (- (getvar "MILLISECS") t0)))
 (ov:check (list label 'EXISTS) (and result (entget result)))
 (ov:check (list label 'SOURCE_UNCHANGED) (equal data (entget en)))
 (ov:check (list label 'GAP_RESTORED) (= gap (getvar "OFFSETGAPTYPE")))
 (if result
  (progn
   (setq area (vla-get-Area (vlax-ename->vla-object result)))
   (ov:check (list label 'BOUNDED_1M) (urb:anden-overwidth-bounded-p en result 1.0))
   (ov:check (list label 'NO_CROSS) (not (urb:polygon-self-intersects-p (urb:lwpoly-points-with-arcs result))))
   (if expected (ov:check (list label 'EXPECTED_AREA) (equal area expected 1e-5)))
   (ov:log (list label 'AREA (rtos area 2 9)))
   (setq reg (vl-catch-all-apply 'urb:anden-region-from-object (list (vlax-ename->vla-object en)))
         cut (vl-catch-all-apply 'urb:anden-region-from-object (list (vlax-ename->vla-object result))))
   (if (or (vl-catch-all-error-p reg) (vl-catch-all-error-p cut))
    (ov:log (list 'REGION_UNAVAILABLE label (if (vl-catch-all-error-p reg) (vl-catch-all-error-message reg)) (if (vl-catch-all-error-p cut) (vl-catch-all-error-message cut))))
    (progn
     (setq err (vl-catch-all-apply 'vla-Boolean (list reg 2 cut))
           remaining (vl-catch-all-apply 'vla-get-Area (list reg)))
     (ov:log (list label 'REMAINING (if (vl-catch-all-error-p remaining) (vl-catch-all-error-message remaining) remaining)))
     (ov:check (list label 'SOURCE_CONTAINED) (and (not (vl-catch-all-error-p err)) (or (vlax-erased-p reg) (and (numberp remaining) (< remaining 1e-5)))))))
   (urb:safe-delete reg) (urb:safe-delete cut)))
 result)
(ov:log 'VALIDATE_BEGIN)
(setq ov:base ov:lastbase)
(ov:dump "source" ov:base)
(ov:dump "old-over" ov:lastover)
(setq ov:correct (ov:case 'REAL_E239A ov:base nil))
(if ov:correct (ov:dump "correct-over" ov:correct))
(ov:case 'STRAIGHT (ov:poly '((0 0) (20 0) (20 4) (0 4))) 120.0)
(ov:case 'VARIABLE (ov:poly '((0 50) (20 50) (40 50) (40 54) (20 64) (0 54))) nil)
(ov:case 'REVERSED (ov:poly (reverse '((100 50) (120 50) (140 50) (140 54) (120 64) (100 54)))) nil)
(ov:check 'REJECT_OLD_SPIKE (not (urb:anden-overwidth-bounded-p ov:base ov:lastover 1.0)))
(ov:log (list 'VALIDATE_DONE 'FAIL ov:fail))
(princ)
