(load (strcat ov:dir "old-cross.lsp"))
(defun ov:random () (setq ov:seed (rem (+ (* ov:seed 25173.0) 13849.0) 65536.0)) (/ ov:seed 65536.0))
(defun ov:regression (/ k n pts j before after bad t0)
 (setq ov:seed 73.0 k 0 bad 0 t0 (getvar "MILLISECS"))
 (foreach pts '(nil ((0 0)) ((0 0) (1 1)) ((0 0) (1 1) (2 2)) ((0 0) (5 5) (0 5) (5 0)) ((0 0) (0 0) (4 0) (4 4) (0 4)))
  (if (not (eq (ov:old-cross pts) (urb:polygon-self-intersects-p pts))) (setq bad (1+ bad))))
 (repeat 500
  (setq n (+ 4 (fix (* 30 (ov:random)))) j 0 pts nil)
  (repeat n
   (setq pts (cons (if (< k 250)
    (list (+ 82000 (* 100 (ov:random))) (+ 95000 (* 100 (ov:random))))
    (polar '(82000.0 95000.0) (/ (* 2.0 pi j) n) (+ 10 (* 10 (ov:random))))) pts) j (1+ j)))
  (setq before (ov:old-cross pts) after (urb:polygon-self-intersects-p pts))
  (if (not (eq before after)) (setq bad (1+ bad)))
  (setq k (1+ k)))
 (ov:check 'CROSS_EQUIVALENCE_506 (= bad 0))
 (ov:log (list 'REGRESSION 'CASES 506 'DIFFERENCES bad 'MS (- (getvar "MILLISECS") t0))))
(ov:regression)
(setq ov:gap (getvar "OFFSETGAPTYPE"))
(setvar "OFFSETGAPTYPE" 2)
(ov:check 'INVALID_INPUT_RETURNS_NIL (null (urb:anden-overwidth-contour nil 1.0)))
(ov:check 'GAP_RESTORED_AFTER_ERROR (= 2 (getvar "OFFSETGAPTYPE")))
(setvar "OFFSETGAPTYPE" ov:gap)
(ov:log 'REGRESSION_DONE)
(princ)
