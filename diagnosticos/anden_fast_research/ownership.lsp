(if (/= (strcase (strcat (getvar "DWGPREFIX") (getvar "DWGNAME")))
 "C:\\USERS\\JUANBUSPER\\DOCUMENTS\\URBANISMO\\WORK\\ANDEN_FAST_RESEARCH\\FIXTURE.DWG") (exit))
(command "_.NETLOAD" "C:/Users/juanbusper/Documents/URBANISMO/work/anden_fast_research/FastPack.dll")
(defun fd:data (obj)
 (vl-remove-if '(lambda (p) (member (car p) '(-1 330 360 102)))
   (entget (vlax-vla-object->ename obj) '("URB_ANDEN_GEN"))))
(defun fd:case (label radius / en h t0 built objs snapshots bms pms rms sms blk item pair valid owner at n)
 (setq en (fr:curve radius) h (cdr (assoc 5 (entget en))))
 (urb:set-anden-data en "Loseta" "1" "1" "Si" "Si" "20 x 20 cm" "No" "Seleccionar en dibujo" "Via creada")
 (setq *urb-current-tactile-side-choice* nil *urb-current-tactile-side-point* '(82800.0 102401.0))
 (fr:log (list label 'START))
 (setq t0 (getvar "MILLISECS") built (urb:build-anden-finish en "Loseta" "Si" "Si" "20 x 20 cm") bms (- (getvar "MILLISECS") t0))
 (if (not built) (vl-exit-with-error "D BUILD failed"))
 (setq objs (urb:generated-objects h) snapshots (mapcar '(lambda (o) (cons o (fd:data o))) objs))
 (setq t0 (getvar "MILLISECS") blk (urb:package-anden en) pms (- (getvar "MILLISECS") t0))
 (if (not blk) (vl-exit-with-error "D PACK failed"))
 (setq owner (vla-Item (vla-get-Blocks (urb:doc)) (vla-get-Name blk)) valid T n 0)
 (foreach pair snapshots
   (if (or (/= (vla-get-OwnerID (car pair)) (vla-get-ObjectID owner))
      (not (equal (cdr pair) (fd:data (car pair)) 1e-9)))
     (progn
       (if valid (fr:log (list 'D_FIRST_DIFF
          'OWNER_MATCH (= (vla-get-OwnerID (car pair)) (vla-get-ObjectID owner))
          'BEFORE (cdr pair) 'AFTER (fd:data (car pair)))))
       (setq valid nil))))
 (vlax-for item owner (if (= (vla-get-ObjectName item) "AcDbBlockReference") (setq n (1+ n))))
 (setq t0 (getvar "MILLISECS")) (vla-Regen (urb:doc) 1) (setq rms (- (getvar "MILLISECS") t0))
 (setq t0 (getvar "MILLISECS")) (command "_.QSAVE") (setq sms (- (getvar "MILLISECS") t0))
 (fr:log (list label 'BUILD_MS bms 'PACK_MS pms 'REGEN_MS rms 'SAVE_MS sms 'TOTAL_MS (+ bms pms rms sms)
   'LIVE_GEOMETRY_XDATA_UNCHANGED valid 'NESTED n 'LOOSE (fr:loose h) 'OBJECTS (length objs)))
 (setq at (urb:block-attribute-values blk)) (fr:log (list label 'QTY at))
 (urb:safe-delete blk) at)
(defun fd:run (/ q0 q1 pair)
 (fr:log 'D_BEGIN)
 (load "C:/Users/juanbusper/Documents/URBANISMO/work/anden552/baseline.lsp")
 (setq q0 (fr:case "FLAT551_188" 450.0))
 (load "C:/Users/juanbusper/Documents/URBANISMO/work/anden_fast_research/flat-d.lsp")
 (setq q1 (fd:case "D_OWNER_188" 450.0))
 (foreach pair q0
   (if (wcmatch (car pair) "*M2,*ML,*UND")
     (fr:log (list 'D_QTY (car pair) (equal (cdr pair) (cdr (assoc (car pair) q1)))))))
 (fd:case "D_OWNER_800" (/ 800.0 0.418))
 (fr:log 'D_DONE))
(setq fd:r (vl-catch-all-apply 'fd:run nil))
(if (vl-catch-all-error-p fd:r) (fr:log (list 'D_ERROR (vl-catch-all-error-message fd:r))))
(princ)
