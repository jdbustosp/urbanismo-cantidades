;; PROTOTIPO LOCAL. NO cargado por el instalador ni por el repo.
;; Geometria de trazos con espesor fisico 1 mm, NO identica a lineweight.
(defun fr:loop (pts bulges / out p b)
  (setq out '((92 . 2) (72 . 1) (73 . 1) (93 . 4)))
  (while pts
    (setq out (append out (list (cons 10 (car pts)) (cons 42 (car bulges))))
          pts (cdr pts) bulges (cdr bulges)))
  (append out '((97 . 0))))
(defun fr:emit-hatch (loops layer parent color expected / data en obj got)
  (setq data (append
    (list '(0 . "HATCH") '(100 . "AcDbEntity") (cons 8 layer) (cons 62 color)
      '(100 . "AcDbHatch") '(10 0.0 0.0 0.0) '(210 0.0 0.0 1.0)
      '(2 . "SOLID") '(70 . 1) '(71 . 0) (cons 91 (length loops)))
    (apply 'append (reverse loops))
    (list '(75 . 0) '(76 . 1) '(98 . 0)
      (urb:generated-xdata-fragment parent "FEATURE_SYMBOL"))))
  (if (not (entmake data)) (vl-exit-with-error "PROTOTYPE HATCH FAILED"))
  (setq en (entlast) obj (vlax-ename->vla-object en))
  (vla-Evaluate obj)
  (setq got (vla-get-Area obj))
  (if (> (abs (- got expected)) (max 1e-6 (* expected 1e-6)))
    (progn (fr:log (list 'HATCH_AREA_FAIL got expected)) (setq fr:fails (1+ fr:fails))))
  (setq fr:hatches (1+ fr:hatches) fr:loops (+ fr:loops (length loops)))
  en)
(defun urb:flush-tactile-batch (layer parent-handle / item pts inn p1 p2 p3 p4 dx dy len nx ny width r expected loops joints joint-area count)
  (setq width 0.001 expected 0.0 joint-area 0.0 count 0)
  (foreach item (reverse *urb-tactile-entities*)
    (cond
      ((= (cdr (assoc 0 item)) "LWPOLYLINE")
        (setq pts (mapcar 'cdr (vl-remove-if-not '(lambda (p) (= (car p) 10)) item))
              p1 (nth 0 pts) p2 (nth 1 pts) p3 (nth 2 pts) p4 (nth 3 pts)
              r (/ (distance p2 p3) 2.0) len (distance p1 p2)
              nx (/ (- (car p3) (car p2)) (* 2.0 r))
              ny (/ (- (cadr p3) (cadr p2)) (* 2.0 r)))
        (setq inn (list
          (list (+ (car p1) (* nx width)) (+ (cadr p1) (* ny width)))
          (list (+ (car p2) (* nx width)) (+ (cadr p2) (* ny width)))
          (list (- (car p3) (* nx width)) (- (cadr p3) (* ny width)))
          (list (- (car p4) (* nx width)) (- (cadr p4) (* ny width)))))
        (setq loops (cons (fr:loop inn '(0.0 1.0 0.0 1.0))
                         (cons (fr:loop pts '(0.0 1.0 0.0 1.0)) loops))
              expected (+ expected (* 2.0 len width) (* pi (- (* r r) (* (- r width) (- r width)))))
              count (+ count 2))
        (if (>= count fr:limit)
          (progn (fr:emit-hatch loops layer parent-handle 7 expected)
            (setq loops nil count 0 expected 0.0))))
      ((= (cdr (assoc 0 item)) "LINE")
        (setq p1 (cdr (assoc 10 item)) p2 (cdr (assoc 11 item)) len (distance p1 p2)
          nx (/ (- (cadr p1) (cadr p2)) len) ny (/ (- (car p2) (car p1)) len))
        (setq pts (list
          (list (+ (car p1) (* nx width 0.5)) (+ (cadr p1) (* ny width 0.5)))
          (list (+ (car p2) (* nx width 0.5)) (+ (cadr p2) (* ny width 0.5)))
          (list (- (car p2) (* nx width 0.5)) (- (cadr p2) (* ny width 0.5)))
          (list (- (car p1) (* nx width 0.5)) (- (cadr p1) (* ny width 0.5)))))
        (setq joints (cons (fr:loop pts '(0.0 0.0 0.0 0.0)) joints)
          joint-area (+ joint-area (* len width))))))
  (if loops (fr:emit-hatch loops layer parent-handle 7 expected))
  (if joints (fr:emit-hatch joints layer parent-handle 8 joint-area))
  (setq *urb-tactile-entities* nil)
  (entlast))
