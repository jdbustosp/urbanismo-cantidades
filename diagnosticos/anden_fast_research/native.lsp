(vl-load-com)
(if (/= (strcase (strcat (getvar "DWGPREFIX") (getvar "DWGNAME")))
 "C:\\USERS\\JUANBUSPER\\DOCUMENTS\\URBANISMO\\WORK\\ANDEN_FAST_RESEARCH\\FIXTURE.DWG") (exit))
(setq *urb-suppress-auto-migration* T fr:fails 0 fr:hatches 0 fr:loops 0)
(defun fr:log (x / f)
 (setq f (open "C:/Users/juanbusper/Documents/URBANISMO/work/anden_fast_research/result.txt" "a"))
 (write-line (vl-princ-to-string x) f) (close f))
(defun fr:curve (r / dx dy th b d p0 p1 p2 q0 q1 q2)
  (setq dx 82800.0 dy 102400.0 th 0.209 d 1.75
        b (/ (sin (/ th 4.0)) (cos (/ th 4.0)))
        p0 (list dx (+ dy d))
        p1 (list (+ dx (* (- r d) (sin th))) (+ dy r (- (* (- r d) (cos th)))))
        p2 (list (+ dx (* 2 r (sin th))) (+ dy (* 2 r (- 1 (cos th))) d))
        q0 (list dx (- dy d))
        q1 (list (+ dx (* (+ r d) (sin th))) (+ dy r (- (* (+ r d) (cos th)))))
        q2 (list (+ dx (* 2 r (sin th))) (- (+ dy (* 2 r (- 1 (cos th)))) d)))
  (entmakex (list '(0 . "LWPOLYLINE") '(100 . "AcDbEntity") '(8 . "0")
    '(100 . "AcDbPolyline") '(90 . 6) '(70 . 1)
    (cons 10 p0) (cons 42 b) (cons 10 p1) (cons 42 (- b)) (cons 10 p2) '(42 . 0.0)
    (cons 10 q2) (cons 42 b) (cons 10 q1) (cons 42 (- b)) (cons 10 q0) '(42 . 0.0))))

(defun fr:case (label radius / en h t0 build bms pms rms sms blk objs at n child def)
 (setq en (fr:curve radius) h (cdr (assoc 5 (entget en))))
 (urb:set-anden-data en "Loseta" "1" "1" "Si" "Si" "20 x 20 cm" "No" "Seleccionar en dibujo" "Via creada")
 (setq *urb-current-tactile-side-choice* nil *urb-current-tactile-side-point* '(82800.0 102401.0))
 (setq fr:hatches 0 fr:loops 0 t0 (getvar "MILLISECS"))
 (fr:log (list label 'START))
 (setq build (urb:build-anden-finish en "Loseta" "Si" "Si" "20 x 20 cm")
       bms (- (getvar "MILLISECS") t0))
 (if (not build) (vl-exit-with-error "BUILD returned nil"))
 (setq objs (urb:generated-objects h))
 (setq t0 (getvar "MILLISECS") blk (urb:package-anden en) pms (- (getvar "MILLISECS") t0))
 (if (not blk) (vl-exit-with-error "PACKAGE returned nil"))
 (setq def (vla-Item (vla-get-Blocks (urb:doc)) (vla-get-Name blk)) n 0)
 (vlax-for child def (if (= (vla-get-ObjectName child) "AcDbBlockReference") (setq n (1+ n))))
 (setq t0 (getvar "MILLISECS")) (vla-Regen (urb:doc) 1) (setq rms (- (getvar "MILLISECS") t0))
 (setq t0 (getvar "MILLISECS")) (command "_.QSAVE") (setq sms (- (getvar "MILLISECS") t0))
 (fr:log (list label 'BUILD_MS bms 'PACK_MS pms 'REGEN_MS rms 'SAVE_MS sms
   'TOTAL_MS (+ bms pms rms sms) 'OBJECTS (length objs) 'NESTED_INSERTS n
   'HATCHES fr:hatches 'LOOPS fr:loops))
 (setq at (urb:block-attribute-values blk))
 (fr:log (list label 'QTY at))
 (fr:log (list label 'LOOSE (fr:loose h)))
 (urb:safe-delete blk)
 at)
(defun fr:loose (h / *urb-generation-parent* *urb-generation-start*) (length (urb:generated-objects h)))
(defun fr:clone-check (/ a obj ss name child)
 (setq a (entmakex '((0 . "LINE") (8 . "0") (10 0.0 0.0 0.0) (11 1.0 0.0 0.0)))
  obj (vlax-ename->vla-object a) ss (ssadd a) name "FR_CLONE_TEST")
 (fr:log (list 'C_ORIGINAL_HANDLE (cdr (assoc 5 (entget a)))))
 (setvar "ATTREQ" 0)
 (vl-cmdf "_.-BLOCK" name "0,0,0" ss "")
 (fr:log (list 'C_ORIGINAL_STILL_LIVE (not (null (entget a)))))
 (vlax-for child (vla-Item (vla-get-Blocks (urb:doc)) name)
   (fr:log (list 'C_CLONED_HANDLE (vla-get-Handle child)))))
(defun fr:run (/ q0 q1 pair)
 (load "C:/Users/juanbusper/Documents/URBANISMO/work/anden_fast_research/baseline.lsp")
 (fr:clone-check)
 (setq q0 (fr:case "BASE552_188" 450.0))
 (load "C:/Users/juanbusper/Documents/URBANISMO/work/anden_fast_research/prototype.lsp")
 (setq fr:limit 256)
 (setq q1 (fr:case "A_BATCH256_188" 450.0))
 (foreach pair q0
   (if (wcmatch (car pair) "*M2,*ML,*UND")
     (if (not (equal (cdr pair) (cdr (assoc (car pair) q1)))) (setq fr:fails (1+ fr:fails)))))
 (setq fr:limit 256)
 (fr:case "A_BATCH256_800" (/ 800.0 0.418))
 (fr:log (list 'DONE 'FAILURES fr:fails)))
(setq fr:r (vl-catch-all-apply 'fr:run nil))
(if (vl-catch-all-error-p fr:r) (fr:log (list 'ERROR (vl-catch-all-error-message fr:r))))
(princ)
