(if (/= (strcase (strcat (getvar "DWGPREFIX") (getvar "DWGNAME")))
 "C:\\USERS\\JUANBUSPER\\DOCUMENTS\\URBANISMO\\WORK\\ANDEN_BATCHNET\\FIXTURE.DWG") (exit))
(command "_.NETLOAD" "C:/Users/juanbusper/Documents/URBANISMO/work/anden_batchnet/CheckBatch.dll")
(defun ba:hatches (def / values item data)
 (vlax-for item def
  (if (= (vla-get-ObjectName item) "AcDbHatch")
   (progn
    (setq data (vl-remove-if '(lambda (p) (member (car p) '(-1 5 330 360 102 -3))) (entget (vlax-vla-object->ename item))))
    (setq values (cons data values)))))
 (mapcar '(lambda (i) (nth i values)) (vl-sort-i values 'nx:less)))
(defun ba:hole (baseline / en reg cut marker h objs geom block def)
 (if baseline
  (load "C:/Users/juanbusper/Documents/URBANISMO/work/anden_batchnet/baseline.lsp")
  (progn (load "C:/Users/juanbusper/Documents/URBANISMO/work/anden_batchnet/candidate.lsp")
         (load "C:/Users/juanbusper/Documents/URBANISMO/work/anden_batchnet/batch.lsp")))
 (setq en (entmakex '((0 . "LWPOLYLINE") (100 . "AcDbEntity") (8 . "0")
  (100 . "AcDbPolyline") (90 . 4) (70 . 1) (10 20.0 20.0) (10 23.0 20.0) (10 23.0 20.4) (10 20.0 20.4))))
 (setq h (cdr (assoc 5 (entget en))) reg (urb:add-region-from-object (vlax-ename->vla-object en))
  cut (urb:polygon-region '((21.0 19.9) (21.7 19.9) (21.7 20.6) (21.0 20.6)) 0.0))
 (vla-Boolean reg 2 cut)
 (setq *urb-generation-parent* h *urb-generation-start* (entlast))
 (urb:fill-tactile-symbols reg "GUIA" 0.0 "URB-ANDEN-LOSETA-GUIA-20X20" 0.0 h 0.20)
 (if baseline
   (progn (setq objs (urb:generated-objects h) geom (nx:geometry objs)) (foreach marker objs (urb:safe-delete marker)))
   (progn
    (setq def (vla-Add (vla-get-Blocks (urb:doc)) (vlax-3d-point '(0 0 0)) "BN_HOLE"))
    (bn:finish "BN_HOLE" h)
    (setq geom (nx:geometry (urb:block-object-list def)))
    (bn:check 'HOLE_ORDER (= 0 (BNCHECKORDER "BN_HOLE")))))
 (urb:safe-delete reg) (entdel en) geom)
(defun ba:visual (definition filename / ref selection)
 (setq ref (vla-InsertBlock (urb:space) (vlax-3d-point '(0 0 0)) (vla-get-Name definition) 1.0 1.0 1.0 0.0))
 (vla-ZoomWindow (vlax-get-acad-object) (vlax-3d-point '(82848.0 102400.5 0.0)) (vlax-3d-point '(82853.0 102405.0 0.0)))
 (vla-Regen (urb:doc) 1)
 (setq selection (vla-Add (vla-get-SelectionSets (urb:doc)) "BN_VISUAL"))
 (vla-AddItems selection (urb:object-array-variant (list ref)))
 (vla-Export (urb:doc) filename "WMF" selection)
 (vla-Delete selection) (urb:safe-delete ref))
(defun ba:run (/ defs item a b t0 msold msnew lst oldorder neworder hole1 hole2 cnt result)
 (bn:log 'ACCEPT_BEGIN)
 (vlax-for item (vla-get-Blocks (urb:doc))
  (if (wcmatch (vla-get-Name item) "URB_ANDEN_*") (setq defs (append defs (list item)))))
 (setq a (car defs) b (cadr defs))
 (bn:check 'ALL_MATERIAL_HATCH_DXF_IDENTICAL (equal (ba:hatches a) (ba:hatches b) 1e-9))
 (bn:check 'ORDER_188 (= 0 (BNCHECKORDER (vla-get-Name b))))
 (bn:check 'ORDER_800 (= 0 (BNCHECKORDER (vla-get-Name (nth 3 defs)))))
 (setq result (vl-catch-all-apply 'ba:visual (list a "C:/Users/juanbusper/Documents/URBANISMO/work/anden_batchnet/before")))
 (bn:log (list 'VISUAL_BASE (if (vl-catch-all-error-p result) (vl-catch-all-error-message result) 'EXPORTED)))
 (setq result (vl-catch-all-apply 'ba:visual (list b "C:/Users/juanbusper/Documents/URBANISMO/work/anden_batchnet/after")))
 (bn:log (list 'VISUAL_BATCH (if (vl-catch-all-error-p result) (vl-catch-all-error-message result) 'EXPORTED)))
 (setq t0 (getvar "MILLISECS") lst (urb:block-object-list b))
 (urb:set-block-draw-order b lst)
 (setq msold (- (getvar "MILLISECS") t0) t0 (getvar "MILLISECS"))
 (BNSORT (vla-get-Name b)) (setq msnew (- (getvar "MILLISECS") t0))
 (bn:log (list 'SORT_INCLUDE_ENUM_188 'LISP_MS msold 'NET_MS msnew))
 (setq hole1 (ba:hole T) hole2 (ba:hole nil))
 (bn:check 'HOLE_EXACT_GUIDE (and (> (length hole1) 0) (equal hole1 hole2 1e-9)))
 (setq cnt (vla-get-Count (vla-Item (vla-get-Blocks (urb:doc)) "BN_HOLE")))
 (setq result (vl-catch-all-apply 'BNAPPEND (list "BN_HOLE" "TEST" "URB-ANDEN-LOSETA-GUIA-20X20" '(2 7 0.0 0.0 1.0 1.0 99 7))))
 (bn:check 'TRANSACTION_REJECT_BAD_BATCH (vl-catch-all-error-p result))
 (bn:check 'TRANSACTION_NO_PARTIAL_ENTITIES (= cnt (vla-get-Count (vla-Item (vla-get-Blocks (urb:doc)) "BN_HOLE"))))
 (command "_.QSAVE")
 (bn:log (list 'ACCEPT_DONE 'FAILURES bn:fail)))
(setq ba:r (vl-catch-all-apply 'ba:run nil))
(if (vl-catch-all-error-p ba:r) (bn:log (list 'ACCEPT_ERROR (vl-catch-all-error-message ba:r))))
(princ)
