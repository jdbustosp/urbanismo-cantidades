(vl-load-com)
(setq t15:dir "C:/Users/juanbusper/Documents/URBANISMO/work/tierras5715/" t15:ok 0 t15:fail 0)
(defun t15:log (s / f) (setq f (open (strcat t15:dir "result.txt") "a")) (write-line s f) (close f))
(defun t15:check (ok msg)
  (if ok (setq t15:ok (1+ t15:ok)) (setq t15:fail (1+ t15:fail)))
  (t15:log (strcat (if ok "PASS " "FAIL ") msg)))
(defun t15:rect (x y dx dy / en)
  (setq en (urb:poly-chain-polyline (list (list x y 0.0) (list (+ x dx) y 0.0)
    (list (+ x dx) (+ y dy) 0.0) (list x (+ y dy) 0.0))))
  (vla-put-Closed (urb:as-vla-object en) :vlax-true) en)
(defun t15:run (/ data ref picks a b c pts blockdef copy ab surface m1 m2 flat temp
                    entry send s1 s2 over before xy)
  (if (/= (strcase (vl-string-translate "\\" "/" (strcat (getvar "DWGPREFIX") (getvar "DWGNAME"))))
          (strcase (strcat t15:dir "fixture.dwg"))) (vl-exit-with-error "Wrong fixture"))
  (t15:check (= *urb-version* "5.7.15") "version")
  (urb:prepare-anden-layers)
  ;; Isolated synthetic road, actual CAD entities and stored profile, no mock.
  (setq t15:axis (urb:poly-chain-polyline '((90000.0 90000.0 0.0) (90040.0 90000.0 0.0)))
        t15:road (t15:rect 90000.0 89998.0 40.0 4.0)
        data '("VIA" "TEST5715"))
  (foreach pair (list (cons 5 (cdr (assoc 5 (entget t15:axis)))) (cons 12 "Inicio")
                     (cons 18 "40") (cons 21 "0") (cons 22 "TEST5715"))
    (setq data (urb:list-set-extended data (car pair) (cdr pair))))
  (urb:set-xdata-strings t15:road "URB_VIA" data)
  (vlax-ldata-put t15:road "URB_VIA_RASANTE_FULL" '((0.0 2700.0) (20.0 2704.0) (40.0 2700.0)))
  (setq t15:near (t15:rect 90005.0 90003.0 30.0 3.0)
        pts (urb:anden-earthwork-raw-points t15:near)
        picks (urb:area-grade-auto pts) ref (caddr (car picks)))
  (t15:check (and ref (= (car ref) t15:axis)) "automatic detects real linked road")
  (setq *urb-picks-edge-offset* nil
        a (urb:design-z-from-picks picks 90000.0 90004.0)
        b (urb:design-z-from-picks picks 90020.0 90004.0)
        c (urb:design-z-from-picks picks 90040.0 90004.0))
  (t15:check (and a b c (equal (- b a) 4.0 1e-8) (equal a c 1e-8))
    "intermediate road elevation retained, not a flat clicked point")
  (t15:check (= (length (urb:area-grade-from-pick (list t15:road '(90010.0 90000.0)))) 1)
    "single reference selection returns complete road profile")
  ;; Lightweight synthetic sidewalk block with the real earthwork role.
  (setq blockdef (vla-Add (vla-get-Blocks (urb:doc)) (vlax-3d-point '(0.0 0.0 0.0)) "URB_ANDEN_TEST5715")
        copy (urb:variant-object-list (vla-CopyObjects (urb:doc)
          (urb:object-array-variant (list (urb:as-vla-object t15:near))) blockdef)))
  (urb:tag-generated-role (car copy) "TEST5715" "EARTHWORK_BOUNDARY")
  (setq ab (vla-InsertBlock (urb:space) (vlax-3d-point '(0.0 0.0 0.0)) "URB_ANDEN_TEST5715" 1.0 1.0 1.0 0.0))
  (urb:set-xdata-strings (urb:as-ename ab) "URB_ANDEN_BLOCK" '("ANDEN"))
  (setq *urb-anden-pts-cache* nil
        picks (urb:area-grade-auto '((90005.0 90011.0) (90035.0 90011.0) (90035.0 90013.0) (90005.0 90013.0))))
  (t15:check (and picks (eq (car (caddr (car picks))) 'ANDEN)) "automatic falls back to adjacent sidewalk when road too far")
  (setq a (urb:design-z-from-picks picks 90005.0 90011.0)
        b (urb:design-z-from-picks picks 90020.0 90011.0))
  (t15:check (and a b (> (- b a) 2.9)) "sidewalk reference follows variable design elevations")
  (t15:check (urb:area-grade-from-pick (list (urb:as-ename ab) '(90020.0 90005.0))) "single sidewalk reference")
  (t15:check (null (urb:area-grade-auto '((100000.0 100000.0) (100010.0 100000.0) (100010.0 100010.0)))) "no remote automatic reference invented")
  (urb:anden-ref-curves-clear)
  ;; Native Civil TIN at z=2600, synthetic laboratory terrain. High design grade keeps all samples in fill, so
  ;; changing depth by .3 must reduce fill by exactly area*.3, independently
  ;; of the terrain's shape and of the configured overexcavation.
  (setq surface (mp:current-terrain-surface))
  (t15:check surface "real terrain surface available")
  (setq t15:real (t15:rect 83000.0 95250.0 10.0 4.0)
        flat '((2800.0 (83000.0 95250.0)))
        m1 (urb:earthworks-from-picks t15:real flat 0.2)
        m2 (urb:earthworks-from-picks t15:real flat 0.5))
  (t15:check (and m1 m2 (equal (- (cadr m1) (cadr m2)) 12.0 1e-5)) "40m2 green: depth delta .30 changes fill by 12m3 on real TN")
  (t15:check (and m1 (equal (car m1) (* 40.0 *urb-overexc-depth*) 1e-5)
    (equal (cadr m1) (* 40.0 (+ 199.8 *urb-overexc-depth*)) 1e-5)) "analytic cut/fill against native flat TIN agrees")
  (setq t15:green (urb:package-green-zone t15:real nil "1" "1" 0.2))
  (urb:set-xdata-strings (urb:as-ename t15:green) "URB_GREEN_MOV" '("123" "456" "0.2"))
  (urb:update-green-zone-data (urb:as-ename t15:green) "1" "1" 0.5)
  (t15:check (null (urb:get-xdata-strings (urb:as-ename t15:green) "URB_GREEN_MOV")) "thickness edit invalidates old earthwork")
  (setq entry (assoc "SEND-ECO" *urb-send-tipos*)
        send (t15:rect 83000.0 95250.0 10.0 4.0)
        s1 (urb:sendero-mt-calcular send send flat 0.2 entry nil)
        s2 (urb:sendero-mt-calcular send send flat 0.5 entry nil))
  (t15:check (and s1 s2 (equal (- (cadr s1) (cadr s2)) 18.0 1e-5)) "sendero 60m2 with lateral overwidth: depth delta gives 18m3")
  (setq t15:send (urb:package-sendero send nil entry "1" "1" '("SEND-ECO" "1" "1") s2))
  (t15:check (and t15:send (urb:send-selected (ssadd (urb:as-ename t15:send)))) "sendero block remains recognized by EDITAR")
  (setq before (urb:send-temp-contour (urb:as-ename t15:send)) xy (car (urb:lwpoly-points before)))
  (entdel before)
  (vla-Move t15:send (vlax-3d-point '(0.0 0.0 0.0)) (vlax-3d-point '(1.0 2.0 0.0)))
  (setq temp (urb:send-temp-contour (urb:as-ename t15:send)))
  (t15:check (equal (car (urb:lwpoly-points temp)) (mapcar '+ xy '(1.0 2.0 0.0)) 1e-6) "edited moved sendero contour uses actual WCS placement")
  (entdel temp)
  ;; Interactive calls continue in SCR, no DCL and no screen control.
  (t15:log "SETUP_FINISHED"))
(setq t15:result (vl-catch-all-apply 't15:run nil))
(if (vl-catch-all-error-p t15:result) (t15:log (strcat "ERROR " (vl-catch-all-error-message t15:result))))
(defun t15:after-auto ()
  (t15:check (and t15:picks (= (car (caddr (car t15:picks))) t15:axis)) "creation Automatico prompt consumes one answer"))
(defun t15:after-sin () (t15:check (null t15:picks) "creation Sin returns without cotas"))
(defun t15:after-edit (/ data)
  (setq data (urb:get-xdata-strings (urb:as-ename t15:green) "URB_GREEN_MOV"))
  (t15:check (and data (equal (atof (nth 2 data)) 0.5 1e-8)) "EDITAR green Tierras writes new movement at edited thickness")
  (t15:check (urb:get-xdata-strings (urb:as-ename t15:send) "URB_SEND_MOV") "EDITAR sendero computes movement")
  (t15:log (strcat "SUMMARY pass=" (itoa t15:ok) " fail=" (itoa t15:fail)))
  (if (and (= t15:fail 0) (not (vl-catch-all-error-p t15:result))) (t15:log "FINISHED")))
(princ)
