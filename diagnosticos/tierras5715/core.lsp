(setq t15:core-out "C:/Users/juanbusper/Documents/URBANISMO/work/tierras5715/core.txt" t15:core-ok 0 t15:core-fail 0)
(defun t15:core-check (ok label / f)
  (if ok (setq t15:core-ok (1+ t15:core-ok)) (setq t15:core-fail (1+ t15:core-fail)))
  (setq f (open t15:core-out "a")) (write-line (strcat (if ok "PASS " "FAIL ") label) f) (close f))
(defun t15:core-run (/ samples area)
  (t15:core-check (= *urb-version* "5.7.15") "version")
  (t15:core-check (equal (urb:design-z-from-picks-plane '((100.0 (0.0 0.0))) 8.0 9.0) 100.0 1e-8) "one manual elevation remains flat")
  (t15:core-check (equal (urb:design-z-from-picks-plane '((100.0 (0.0 0.0)) (104.0 (20.0 0.0)) (100.0 (40.0 0.0))) 20.0 0.0) 104.0 1e-8) "intermediate collinear elevation retained")
  (t15:core-check (equal (urb:cota-at-axis-distance 10.0 '((0.0 100.0) (20.0 104.0) (40.0 100.0))) 102.0 1e-8) "complete profile interpolation")
  (setq samples (urb:earthwork-area-samples '((0.0 0.0) (10.0 0.0) (10.0 4.0) (0.0 4.0))) area (apply '+ (mapcar 'cadr samples)))
  (t15:core-check (equal area 40.0 1e-8) "weighted sample area exact")
  (setq *urb-overexc-depth* 0.0)
  (t15:core-check (equal (urb:cut-fill-at 2.0) '(2.0 0.0) 1e-8) "cut sign")
  (t15:core-check (equal (urb:cut-fill-at -2.0) '(0.0 2.0) 1e-8) "fill sign"))
(setq t15:core-result (vl-catch-all-apply 't15:core-run nil))
(t15:core-check (not (vl-catch-all-error-p t15:core-result)) "core functions execute without exception")
(defun t15:core-finish (/ f)
  (t15:core-check (null t15:core-picks) "Conservar returns without requesting elevations")
  (setq f (open t15:core-out "a"))
  (write-line (strcat "SUMMARY pass=" (itoa t15:core-ok) " fail=" (itoa t15:core-fail)) f)
  (if (= t15:core-fail 0) (write-line "FINISHED" f)) (close f))
(princ)
