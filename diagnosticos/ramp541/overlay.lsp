;; Ejecutar despues de native.lsp en el mismo laboratorio, nunca en maestro.
(defun rv:overlay (/ en source r at rows)
  (rv:clear)
  (setq en (urb:ramp-quad-poly '(0.0 0.0 0.0) 0.0 1.0 0.0 0.0 12.0 5.0 "URB-ANDEN"))
  (urb:set-anden-data en "Loseta" "1" "4E" "Si" "Si" "20 x 20 cm" "No" "SUP_TN" "Via creada")
  (urb:build-anden-finish en "Loseta" "Si" "Si" "20 x 20 cm")
  (setq r (urb:package-anden en))
  (rv:check "OVERLAY_REAL_ANDEN_BLOCK" (= (type r) 'VLA-OBJECT) r)
  (setq source (urb:ramp-quad-poly '(0.0 0.0 0.0) 0.0 1.0 0.0 0.0 10.0 4.0 "URB-RAMPA")
    *urb-rampav-frente* '(5.0 0.0 0.0))
  (rv:check "OVERLAY_DETECTED" (urb:anden-under-p source) source)
  (setq r (urb:build-vehicular-access source (list (list '(0.0 0.0 0.0) 0.0 1.0 10.0)) "1" "4E")
    at (urb:block-attribute-values r))
  (rv:check "OVERLAY_NO_DUPLICATE_BASE"
    (and (= (rv:num "SBG_M3" at) 0.0) (= (rv:num "ADOQUIN_M2" at) 0.0)
         (= (rv:num "LOSETA_LISA_M2" at) 0.0)) at)
  (rv:check "OVERLAY_TACTILE_COUNTED" (= (rv:num "LOSETA_TOPEROL_UND" at) 65.0) at)
  (rv:log (list 'OVERLAY_BUDGET (urb:ppto-rows-rampas)))
  (urb:safe-delete (urb:as-vla-object source))
  (command "_.QSAVE"))
(setq rv:r (vl-catch-all-apply 'rv:overlay nil))
(if (vl-catch-all-error-p rv:r) (rv:log (list 'OVERLAY_ERROR (vl-catch-all-error-message rv:r))))
(rv:log 'OVERLAY_DONE)
(princ)
