(vl-load-com)
(setq *urb-suppress-auto-migration* T)
(setq rv:lab "C:/Users/juanbusper/Documents/URBANISMO/work/ramp541/")
(if (not (and (= (strcase (vl-string-translate "\\" "/" (getvar "DWGPREFIX"))) (strcase rv:lab))
              (= (strcase (getvar "DWGNAME")) "FIXTURE.DWG")))
  (progn (prompt "\nPRUEBA CANCELADA: solo se permite ramp541/fixture.dwg.") (exit)))
(defun rv:log (x / f)
  (setq f (open (strcat rv:lab "result.txt") "a"))
  (write-line (vl-princ-to-string x) f) (close f))
(defun rv:check (name ok detail)
  (rv:log (list rv:phase (if ok 'OK 'FAIL) name detail)))
(defun rv:clear (/ o xs)
  (vlax-for o (urb:space) (setq xs (cons o xs)))
  (foreach o xs (urb:safe-delete o)))
(defun rv:v (p base ang sg)
  (* sg (+ (* (- (car p) (car base)) (- (sin ang)))
           (* (- (cadr p) (cadr base)) (cos ang)))))
(defun rv:num (key attrs) (atof (urb:safe-string (cdr (assoc key attrs)) "0")))
(defun rv:overlap (o p / a b res ar)
  (setq a (if (= (vla-get-ObjectName o) "AcDbRegion") (vla-Copy o) (urb:add-region-from-object o))
    b (urb:block-footprint-region p) ar 0.0)
  (if (and a b)
    (progn
      (setq res (vl-catch-all-apply 'vla-Boolean (list a 1 b)))
      (if (vl-catch-all-error-p res) (setq ar 1e9)
        (progn (setq res (vl-catch-all-apply 'vla-get-Area (list a)))
          (if (numberp res) (setq ar res))))))
  (urb:safe-delete a) (urb:safe-delete b) ar)
(defun rv:veh (ang sg / base frame source r at ss i be pa reg pts minv
                      types def o xs polys laterals vv area toparea n t0 rows overlap j)
  (rv:clear)
  (setq base '(1000.0 2000.0 0.0) frame (list base ang sg 10.0)
    source (urb:ramp-quad-poly base ang sg 0.0 0.0 10.0 4.0 "URB-RAMPA")
    *urb-rampav-frente* (urb:ramp-local-point base ang sg 5.0 0.0)
    t0 (getvar "MILLISECS"))
  (setq r (urb:build-vehicular-access source (list frame) "1" "4E"))
  (rv:check "BLOCK" (= (type r) 'VLA-OBJECT) (- (getvar "MILLISECS") t0))
  (setq at (urb:block-attribute-values r))
  (rv:check "A86_10_A85_5.8"
    (and (equal (rv:num "SARDINEL_A86_ML" at) 10.0 1e-6)
         (equal (rv:num "SARDINEL_A85_ML" at) 5.8 1e-6)) at)
  (setq ss (ssget "_X" '((0 . "INSERT") (-3 ("URB_PREFAB_BLOCK")))))
  (setq i 0 minv 1000.0 types nil)
  (if ss (repeat (sslength ss)
    (setq be (ssname ss i) pa (urb:block-attribute-values (urb:as-vla-object be))
      types (cons (list (cdr (assoc "TIPO" pa)) (cdr (assoc "LONGITUD_M" pa))
        (cdr (assoc "DESTINO_PPTO" pa))) types)
      reg (urb:block-footprint-region be))
    (if reg (progn
      (setq pts (urb:region-outline-points reg))
      (foreach p pts (setq minv (min minv (rv:v p base ang sg))))
      (urb:safe-delete reg))
      (rv:check "FOOTPRINT" nil (cdr (assoc 5 (entget be)))))
    (setq i (1+ i))))
  (rv:check "PREFABS_4" (= i 4) types)
  (rv:check "NO_ROAD_INVASION" (and (< minv 1.0) (>= minv -1e-6)) (list ang sg minv))
  (setq def (vla-Item (vla-get-Blocks (urb:doc)) (vla-get-Name r)) laterals 0 toparea 0.0 overlap 0.0)
  (vlax-for o def
    (if (and (member (vla-get-ObjectName o) '("AcDbPolyline" "AcDbRegion"))
             (= (vla-get-Layer o) "URB-ANDEN-LOSETA-TOPEROL-20X20"))
      (progn
        (setq area (vla-get-Area o) toparea (+ toparea area))
        (if (and (> area 0.70) (<= area 0.760001)) (setq laterals (1+ laterals)))
        (setq j 0)
        (repeat (sslength ss)
          (setq overlap (+ overlap (rv:overlap o (ssname ss j))) j (1+ j))))))
  (rv:check "TACTILE_NO_PREFAB_OVERLAP" (< overlap 1e-6) overlap)
  (rv:check "TWO_FULL_OUTER_TACTILES" (= laterals 2) laterals)
  (rv:check "TACTILE_AREA_QUANTITY"
    (equal toparea (* (rv:num "TOPEROL_ML" at) 0.2) 1e-6)
    (list toparea (rv:num "TOPEROL_ML" at) (rv:num "LOSETA_TOPEROL_UND" at)))
  (setq rows (urb:ppto-rows-prefabs))
  (rv:check "PREFAB_BUDGET_ROWS" (> (length rows) 0) rows)
  (rv:log (list 'RAMP_BUDGET (urb:ppto-rows-rampas)))
  (urb:safe-delete (urb:as-vla-object source)))
(defun rv:ped (/ r at def o n a)
  (rv:clear)
  (setq r (urb:build-ramp '(0.0 0.0 0.0) 0.74 -1.0 3.0 4.0 "1" "4E" 0.0 "RAMPA-PEATONAL")
    at (urb:block-attribute-values r)
    def (vla-Item (vla-get-Blocks (urb:doc)) (vla-get-Name r)) n 0 a 0.0)
  (vlax-for o def
    (if (and (= (vla-get-ObjectName o) "AcDbPolyline")
             (= (vla-get-Layer o) "URB-SARDINEL-A-86"))
      (setq n (1+ n) a (+ a (vla-get-Area o)))))
  (rv:check "PED_A86_3.6ML_0.72M2"
    (and (= n 1) (equal a 0.72 1e-6) (equal (rv:num "SARDINEL_A86_ML" at) 3.6 1e-6)) (list n a at))
  (rv:check "PED_A105_TWO" (equal (rv:num "A105_UND" at) 2.0 1e-6) at)
  (rv:log (list 'PED_BUDGET (urb:ppto-rows-rampas))))
(defun rv:run (name file / r)
  (setq rv:phase name)
  (setq r (vl-catch-all-apply 'load (list file)))
  (rv:check "LOAD" (not (vl-catch-all-error-p r)) r)
  (foreach args '((0.0 1.0) (0.74 -1.0) (3.14159265359 1.0))
    (setq r (vl-catch-all-apply 'rv:veh args))
    (if (vl-catch-all-error-p r) (rv:log (list name 'ERROR args (vl-catch-all-error-message r)))))
  (setq r (vl-catch-all-apply 'rv:ped nil))
  (if (vl-catch-all-error-p r) (rv:log (list name 'ERROR_PED (vl-catch-all-error-message r)))))
(rv:log (list 'START (getvar "ACADVER")))
(if (not rv:final-only) (rv:run "BASELINE_540" (strcat rv:lab "baseline.lsp")))
(rv:run "FINAL_541" (strcat rv:lab "candidate.lsp"))
(setq rv:r (urb:ramp-input-data "RAMPA-VEHICULAR" '(0 0 0) '(2 0 0) '(1 -4 0)))
(rv:check "FIXED_WIDTH_10" (and (= (nth 3 rv:r) 10.0) (= (caddr rv:r) -1.0)) rv:r)
(setq rv:r (urb:ramp-input-data "PASO-PEATONAL" '(0 0 0) '(2 0 0) '(1 -4 0)))
(rv:check "PASO_UNCHANGED" (= (nth 3 rv:r) 2.0) rv:r)
(command "_.QSAVE")
(rv:log 'DONE)
(princ)
