;; Pruebas puras + carga completa del motor INSTALADO (sin adaptador COM).
(setq fout (open (strcat (getenv "URB_TEST_LAB") "/focal_result.txt") "w") fp 0 ff 0)
(defun fc (name ok) (if ok (setq fp (1+ fp)) (setq ff (1+ ff)))
  (write-line (strcat (if ok "OK " "FALLO ") name) fout))
(setq ferr (vl-catch-all-apply '(lambda (/ loops chains len part)
  (load (strcat (getenv "APPDATA") "/Autodesk/ApplicationPlugins/UrbanismoCantidades.bundle/Contents/urbanismo_cantidades.lsp"))
  (fc "version instalada 4.80.0" (= *urb-version* "4.80.0"))
  (fc "ANDEN registrado" (= (type c:ANDEN) 'SUBR))
  (fc "recorte prefabricado registrado" (= (type urb:recut-prefab-for-container) 'SUBR))
  (setq loops '(((0 0) (6 0) (6 2) (0 2)) ((2 0.5) (4.2 0.5) (4.2 1.7) (2 1.7))))
  (fc "interior valido" (urb:point-in-region-polygons-p '(1 1) loops))
  (fc "hueco excluido" (not (urb:point-in-region-polygons-p '(3 1) loops)))
  (fc "exterior excluido" (not (urb:point-in-region-polygons-p '(8 1) loops)))
  (fc "bucle invertido conserva hueco" (not (urb:point-in-region-polygons-p '(3 1) (mapcar 'reverse loops))))
  (setq chains (urb:chain-split-por-poligonos '((0 2 0) (6 2 0)) '(((2 0.8) (4.2 0.8) (4.2 2) (2 2)))) len 0.0)
  (foreach part chains (setq len (+ len (urb:poly-chain-length part))))
  (fc "costado tangente se divide en dos" (= (length chains) 2))
  (fc "6m menos contenedor 2.2m = 3.8m" (equal len 3.8 1e-6))
  (fc "costado totalmente tapado devuelve vacio" (null (urb:chain-split-por-poligonos '((2 2 0) (4.2 2 0)) '(((2 0.8) (4.2 0.8) (4.2 2) (2 2))))))
)))
(if (vl-catch-all-error-p ferr) (progn (setq ff (1+ ff)) (write-line (vl-catch-all-error-message ferr) fout)))
(write-line (strcat "DONE " (itoa fp) " OK / " (itoa ff) " FALLOS") fout)
(close fout)
(princ)
