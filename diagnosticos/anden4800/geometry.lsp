;; Codex / BOG085CD119BDQN / 2026-09-08. Solo fixture, ActiveX real.
(setq test-out (strcat (getenv "URB_TEST_LAB") "/geometry_result.txt") test-fails 0)
(defun tlog (s / f) (setq f (open test-out "a")) (write-line s f) (close f))
(defun check (name ok) (if (not ok) (setq test-fails (1+ test-fails)))
  (tlog (strcat (if ok "OK " "FALLO ") name)))
(defun poly (pts z / d p)
  (setq d (list '(0 . "LWPOLYLINE") '(100 . "AcDbEntity")
    '(100 . "AcDbPolyline") (cons 90 (length pts)) '(70 . 1) (cons 38 z)))
  (foreach p pts (setq d (append d (list (cons 10 p))))) (entmakex d))
(defun rot (p) (urb:local-to-world (car p) (cadr p) 0.7))
(setq err (vl-catch-all-apply '(lambda (/ outer hole reg cut before en n bad pt loops pc
  cont name pre parts attrs total reg2 bd result block)
  (load (strcat (getenv "URB_REPO") "/urbanismo_cantidades.lsp"))
  (check "carga completa 4.80.0 y comando ANDEN" (and (= *urb-version* "4.80.0") (member 'C:ANDEN (atoms-family 0))))
  ;; Region rotada y concava con hueco interior. El test de pertenencia
  ;; esperado usa los poligonos de entrada, NO el algoritmo probado.
  (setq outer (mapcar 'rot '((0 0) (6 0) (6 2) (0 2)))
        hole (mapcar 'rot '((2 0.5) (4.2 0.5) (4.2 1.7) (2 1.7))))
  (setq reg (urb:add-region-from-object (urb:as-vla-object (poly outer 0.0)))
        cut (urb:add-region-from-object (urb:as-vla-object (poly hole 0.0))))
  (vla-Boolean reg 2 cut)
  (setq loops (urb:region-polygons reg))
  (check "region reconstruye exterior y hueco" (= (length loops) 2))
  (urb:ensure-layer "URB-TEST-TACTIL" 8 T)
  (setq before (entlast))
  (urb:fill-tactile-symbols reg "TOPEROL" 0.7 "URB-TEST-TACTIL" 0.0 "TEST4800" 0.4)
  (setq en (entnext before) n 0 bad 0)
  (while en
    (if (= (cdr (assoc 0 (entget en))) "CIRCLE")
      (progn (setq pt (cdr (assoc 10 (entget en))) n (1+ n))
        (if (or (not (urb:point-in-poly-2d pt outer)) (urb:point-in-poly-2d pt hole))
          (setq bad (1+ bad)))))
    (setq en (entnext en)))
  (tlog (strcat "SIMBOLOS " (itoa n) " FUERA " (itoa bad)))
  (check "toperoles sin centros fuera ni en hueco" (and (> n 100) (= bad 0)))
  (urb:safe-delete reg)
  ;; Anden primero, contenedor despues, cotas distintas y eje rotado.
  (setq bd (poly (mapcar 'rot '((20 0) (26 0) (26 2) (20 2))) 0.0))
  (urb:set-anden-data bd "Loseta" "1" "1" "Si" "Si" "40 x 40 cm" "No" "SUP_TN" "Via creada")
  (urb:set-anden-pattern-mode bd "AUTOMATICO")
  (setq *urb-current-tactile-side-point* (rot '(23 2)))
  (urb:build-anden-finish bd "Loseta" "Si" "Si" "40 x 40 cm")
  (setq block (urb:package-anden bd))
  (check "anden inicial empaquetado con guia y toperol" block)
  (setq pre (urb:poly-chain-polyline (mapcar '(lambda(p / q) (setq q (rot p)) (list (car q) (cadr q) 0.0)) '((20 2) (26 2)))))
  (setq pre (urb:build-prefab-from-reference pre (rot '(23 2.2)) "Bordillo" 0.2 "1" "1" "Exterior" "Anden"))
  (check "prefabricado inicial 6m creado" pre)
  (setq name (urb:mob-ensure-block (assoc "CONT-C" *urb-mob-tipos*) -1.0)
        pc (rot '(22 2))
        cont (vla-InsertBlock (urb:space) (vlax-3d-point (list (car pc) (cadr pc) 100.0)) name 1.0 1.0 1.0 0.7))
  (urb:set-xdata-strings (urb:as-ename cont) "URB_MOBILIARIO" '("CONT-C" "IZQUIERDA" "0.7"))
  (setq reg2 (urb:add-region-from-object (urb:as-vla-object (poly (mapcar 'rot '((20 0) (26 0) (26 2) (20 2))) 0.0))))
  (setq reg2 (urb:apply-anden-cutouts reg2))
  (tlog (strcat "AREA NETA " (rtos (vla-get-Area reg2) 2 4)))
  (check "recorte a distinta cota: 12 - 2.64 = 9.36m2" (equal (vla-get-Area reg2) 9.36 0.02))
  (urb:safe-delete reg2)
  (check "detecta interseccion con anden existente" (urb:container-overlaps-anden-p (urb:as-ename cont) (urb:as-ename block)))
  (setq result (urb:recut-andenes-for-container (urb:as-ename cont)))
  (tlog (strcat "RECUT " (vl-princ-to-string result)))
  (check "anden reconstruido sin fallos" (and (= (car result) 1) (= (caddr result) 0)))
  (setq parts (ssget "_X" '((0 . "INSERT") (-3 ("URB_PREFAB_BLOCK")))) n 0 total 0.0)
  (if parts (repeat (sslength parts)
    (setq attrs (urb:block-attribute-values (ssname parts n)) n (1+ n)
          total (+ total (atof (urb:safe-string (cdr (assoc "LONGITUD_M" attrs)) "0"))))))
  (tlog (strcat "PREFABS " (itoa n) " LONGITUD " (rtos total 2 4)))
  (check "prefabricado cortado en 2 piezas total 3.8m" (and (= n 2) (equal total 3.8 0.02)))
)))
(if (vl-catch-all-error-p err) (progn (setq test-fails (1+ test-fails)) (tlog (strcat "ERROR " (vl-catch-all-error-message err)))))
(tlog (strcat "DONE FALLOS=" (itoa test-fails)))
(princ)
