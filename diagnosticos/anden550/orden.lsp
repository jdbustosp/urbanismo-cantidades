(vl-load-com)
(setq *urb-suppress-auto-migration* T)
(setq ac:out "C:/Users/juanbusper/Documents/URBANISMO/work/claude_20260914_anden543/orden_result.txt")
(defun ac:log (v / f)
  (setq f (open ac:out "a")) (write-line (vl-princ-to-string (list (getvar "MILLISECS") v)) f) (close f))
(load "C:/Users/juanbusper/Streaming de Google Drive/Mi unidad/VARIOS/CLAUDE/proyectos/URBANISMO EXTERNO/urbanismo_cantidades.lsp")
(ac:log (list 'MOTOR (if (boundp '*urb-version*) *urb-version* "?")))
(setq *urb-suppress-auto-migration* T)
(defun ac:curva (dx dy r th / b d p0 p1 p2 q0 q1 q2)
  (setq d 1.75 b (/ (sin (/ th 4.0)) (cos (/ th 4.0)))
        p0 (list dx (+ dy d))
        p1 (list (+ dx (* (- r d) (sin th))) (+ dy r (- (* (- r d) (cos th)))))
        p2 (list (+ dx (* 2 r (sin th))) (+ dy (* 2 r (- 1 (cos th))) d))
        q0 (list dx (- dy d))
        q1 (list (+ dx (* (+ r d) (sin th))) (+ dy r (- (* (+ r d) (cos th)))))
        q2 (list (+ dx (* 2 r (sin th))) (- (+ dy (* 2 r (- 1 (cos th)))) d)))
  (entmakex (list '(0 . "LWPOLYLINE") '(100 . "AcDbEntity") '(8 . "0")
    '(100 . "AcDbPolyline") '(90 . 6) '(70 . 1)
    (cons 10 p0) (cons 42 b) (cons 10 p1) (cons 42 (- b)) (cons 10 p2) '(42 . 0.0)
    (cons 10 q2) (cons 42 b) (cons 10 q1) (cons 42 (- b)) (cons 10 q0) '(42 . 0.0))))
(defun ac:caso (etiq dx r / en h t0 bms pms blk lst t1 t2)
  (setq en (ac:curva dx 1000.0 r 0.209))
  (urb:set-anden-data en "Loseta" "1" "1" "Si" "Si" "20 x 20 cm" "No" "Seleccionar en dibujo" "Via creada")
  (setq *urb-current-tactile-side-choice* nil
        *urb-current-tactile-side-point* (list dx 1001.0)
        h (cdr (assoc 5 (entget en))) t0 (getvar "MILLISECS"))
  (vl-catch-all-apply 'urb:build-anden-finish (list en "Loseta" "Si" "Si" "20 x 20 cm"))
  (setq bms (- (getvar "MILLISECS") t0))
  (ac:log (list etiq 'BUILD_MS bms 'PIEZAS (length (urb:generated-objects h))))
  (setq t0 (getvar "MILLISECS"))
  (setq blk (vl-catch-all-apply 'urb:package-anden (list en)))
  (setq pms (- (getvar "MILLISECS") t0))
  (ac:log (list etiq 'PACK_MS pms 'ES_BLOQUE (and (not (vl-catch-all-error-p blk)) (= (type blk) 'VLA-OBJECT))
                'SUELTAS (length (urb:generated-objects h))))
  ;; medir APARTE las dos partes caras del empaquetado
  (if (and (not (vl-catch-all-error-p blk)) (= (type blk) 'VLA-OBJECT))
    (progn
      (setq t1 (getvar "MILLISECS"))
      (setq lst (urb:block-object-list
        (vla-Item (vla-get-Blocks (urb:doc)) (vla-get-Name blk))))
      (setq t1 (- (getvar "MILLISECS") t1))
      (setq t2 (getvar "MILLISECS"))
      (vl-catch-all-apply 'urb:set-block-draw-order
        (list (vla-Item (vla-get-Blocks (urb:doc)) (vla-get-Name blk)) lst))
      (setq t2 (- (getvar "MILLISECS") t2))
      (ac:log (list etiq 'LISTAR_OBJETOS_MS t1 'ORDEN_DIBUJO_MS t2 'OBJETOS (length lst))))))
(vl-catch-all-apply 'ac:caso (list "M188" 1000.0 450.0))
(vl-catch-all-apply 'ac:caso (list "M376" 4000.0 900.0))
(ac:log 'FIN)
(princ)
