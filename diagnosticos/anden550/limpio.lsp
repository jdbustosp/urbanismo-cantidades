(vl-load-com)
(setq *urb-suppress-auto-migration* T)
(setq ac:out "C:/Users/juanbusper/Documents/URBANISMO/work/claude_20260914_anden543/limpio_result.txt")
(defun ac:log (v / f)
  (setq f (open ac:out "a")) (write-line (vl-princ-to-string (list (getvar "MILLISECS") v)) f) (close f))
(ac:log 'L01_DIBUJO_LIMPIO)
(setq ac:t0 (getvar "MILLISECS"))
(load "C:/Users/juanbusper/Streaming de Google Drive/Mi unidad/VARIOS/CLAUDE/proyectos/URBANISMO EXTERNO/urbanismo_cantidades.lsp")
(ac:log (list 'L02_MOTOR (if (boundp '*urb-version*) *urb-version* "?")
              'MS (- (getvar "MILLISECS") ac:t0)))
(setq *urb-suppress-auto-migration* T)

;; contorno curvo sintetico de ~188 m de desarrollo y 3.5 m de ancho:
;; dos bordes paralelos unidos, con bulge real (no poligonal)
(defun ac:curva (/ r th d b p0 p1 p2 q0 q1 q2 dx dy)
  (setq r 450.0 th 0.209 d 1.75 dx 1000.0 dy 1000.0
        b (/ (sin (/ th 4.0)) (cos (/ th 4.0)))
        p0 (list dx (+ dy d))
        p1 (list (+ dx (* (- r d) (sin th))) (+ dy r (- (* (- r d) (cos th)))))
        p2 (list (+ dx (* 2 r (sin th))) (+ dy (* 2 r (- 1 (cos th))) d))
        q0 (list dx (- dy d))
        q1 (list (+ dx (* (+ r d) (sin th))) (+ dy r (- (* (+ r d) (cos th)))))
        q2 (list (+ dx (* 2 r (sin th))) (- (+ dy (* 2 r (- 1 (cos th)))) d)))
  (entmakex (list '(0 . "LWPOLYLINE") '(100 . "AcDbEntity") '(8 . "0")
    '(100 . "AcDbPolyline") '(90 . 6) '(70 . 1)
    (cons 10 p0) (cons 42 b) (cons 10 p1) (cons 42 (- b)) (cons 10 p2) '(42 . 0.0)
    (cons 10 q2) (cons 42 b) (cons 10 q1) (cons 42 (- b)) (cons 10 q0) '(42 . 0.0))))

(setq ac:en (ac:curva))
(ac:log (list 'L03_CONTORNO (if ac:en 'CREADO 'FALLO)
              'LONGITUD (if ac:en (vlax-curve-getDistAtParam
                (vlax-ename->vla-object ac:en)
                (vlax-curve-getEndParam (vlax-ename->vla-object ac:en))) 0)))
(setq ac:t0 (getvar "MILLISECS"))
(setq ac:r (vl-catch-all-apply 'urb:set-anden-data
  (list ac:en "Loseta" "1" "1" "Si" "Si" "20 x 20 cm" "No" "Seleccionar en dibujo" "Via creada")))
(ac:log (list 'L04_SET_DATA 'MS (- (getvar "MILLISECS") ac:t0)
  (if (vl-catch-all-error-p ac:r) (vl-catch-all-error-message ac:r) 'OK)))
(setq *urb-current-tactile-side-choice* nil
      *urb-current-tactile-side-point* (list 1000.0 1001.0))
(setq ac:h (cdr (assoc 5 (entget ac:en))))

;; cronometrar la franja tactil (guia + toperol) por separado
(setq ac:t-acc 0)
(setq ac:orig-acc urb:create-accessibility-features)
(defun urb:create-accessibility-features (ename guia toperol format / t0 r)
  (setq t0 (getvar "MILLISECS"))
  (setq r (apply ac:orig-acc (list ename guia toperol format)))
  (setq ac:t-acc (+ ac:t-acc (- (getvar "MILLISECS") t0)))
  r)
(ac:log 'L05_ANTES_BUILD)
(setq ac:t0 (getvar "MILLISECS"))
(setq ac:b (vl-catch-all-apply 'urb:build-anden-finish
  (list ac:en "Loseta" "Si" "Si" "20 x 20 cm")))
(setq ac:buildms (- (getvar "MILLISECS") ac:t0))
(ac:log (list 'L06_BUILD 'MS ac:buildms 'TACTIL_MS ac:t-acc
  'RESTO_MS (- ac:buildms ac:t-acc)
  (if (vl-catch-all-error-p ac:b) (vl-catch-all-error-message ac:b) ac:b)))
(ac:log (list 'L07_PIEZAS (length (urb:generated-objects ac:h))))
(setq ac:t0 (getvar "MILLISECS"))
(setq ac:blk (vl-catch-all-apply 'urb:package-anden (list ac:en)))
(ac:log (list 'L08_PACK 'MS (- (getvar "MILLISECS") ac:t0)
  'ES_BLOQUE (and (not (vl-catch-all-error-p ac:blk)) (= (type ac:blk) 'VLA-OBJECT))))
(ac:log (list 'L09_SUELTAS (length (urb:generated-objects ac:h))))
(if (and (not (vl-catch-all-error-p ac:blk)) (= (type ac:blk) 'VLA-OBJECT))
  (progn
    (setq ac:at (urb:block-attribute-values ac:blk))
    (ac:log (list 'L10_CANT 'AREA (mp:getval "AREA_M2" ac:at "0")
      'GUIA_ML (mp:getval "LOSETA_GUIA_ML" ac:at "0")
      'TOPEROL_ML (mp:getval "LOSETA_TOPEROL_ML" ac:at "0")))))
(ac:log 'DONE)
(princ)
