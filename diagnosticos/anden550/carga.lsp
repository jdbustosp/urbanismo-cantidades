(vl-load-com)
(setq *urb-suppress-auto-migration* T)
(setq ac:out "C:/Users/juanbusper/Documents/URBANISMO/work/claude_20260914_anden543/carga_result.txt")
(defun ac:log (v / f)
  (setq f (open ac:out "a")) (write-line (vl-princ-to-string (list (getvar "MILLISECS") v)) f) (close f))
(setq ac:t0 (getvar "MILLISECS"))
(load "C:/Users/juanbusper/Streaming de Google Drive/Mi unidad/VARIOS/CLAUDE/proyectos/URBANISMO EXTERNO/urbanismo_cantidades.lsp")
(ac:log (list 'CARGA_MS (- (getvar "MILLISECS") ac:t0)
              'VERSION (if (boundp '*urb-version*) *urb-version* "?")
              'SELLO (urb:safe-string (urb:config-read "URB_HATCH_REPAIR_VER") "(ninguno)")))
(command "_.QSAVE")
(ac:log 'GUARDADO)
(princ)
