(vl-load-com)
(setq *urb-suppress-auto-migration* T)
(setq ac:out "C:/Users/juanbusper/Documents/URBANISMO/work/claude_20260914_anden543/tactil_result.txt")
(defun ac:log (v / f)
  (setq f (open ac:out "a")) (write-line (vl-princ-to-string (list (getvar "MILLISECS") v)) f) (close f))
(setq ac:t0 (getvar "MILLISECS"))
(load "C:/Users/juanbusper/Streaming de Google Drive/Mi unidad/VARIOS/CLAUDE/proyectos/URBANISMO EXTERNO/urbanismo_cantidades.lsp")
(ac:log (list 'MOTOR (if (boundp '*urb-version*) *urb-version* "?") 'MS (- (getvar "MILLISECS") ac:t0)))
(setq *urb-suppress-auto-migration* T)

(defun ac:curva (dx dy r th / b d p0 p1 p2 q0 q1 q2)
  (setq d 1.75 b (/ (sin (/ th 4.0)) (cos (/ th 4.0)))
        p0 (list dx (+ dy d))
        p1 (list (+ dx (* (- r d) (sin th))) (+ dy r (- (* (- r d) (cos th)))))
        p2 (list (+ dx (* 2 r (sin th))) (+ dy (* 2 r (- 1 (cos th))) d))
        q0 (list dx (- dy d))
        q1 (list (+ dx (* (+ r d) (sin th))) (+ dy r (- (* (+ r d) (cos th)))))
        q2 (list (+ dx (* 2 r (sin th))) (- (+ dy (* 2 r (- 1 (cos th)))) d)))
  (entmakex (list '(0 . "LWPOLYLINE") '(100 . "AcDbEntity") '(8 . "0")
    '(100 . "AcDbPolyline") '(90 . 6) '(70 . 1)
    (cons 10 p0) (cons 42 b) (cons 10 p1) (cons 42 (- b)) (cons 10 p2) '(42 . 0.0)
    (cons 10 q2) (cons 42 b) (cons 10 q1) (cons 42 (- b)) (cons 10 q0) '(42 . 0.0))))

(defun ac:caso (etiq dx r th guia top / en h t0 bms pms blk at)
  (setq en (ac:curva dx 1000.0 r th))
  (urb:set-anden-data en "Loseta" "1" "1" guia top "20 x 20 cm" "No" "Seleccionar en dibujo" "Via creada")
  (setq *urb-current-tactile-side-choice* nil
        *urb-current-tactile-side-point* (list dx 1001.0)
        h (cdr (assoc 5 (entget en))) t0 (getvar "MILLISECS"))
  (setq bms (vl-catch-all-apply 'urb:build-anden-finish (list en "Loseta" guia top "20 x 20 cm")))
  (setq bms (- (getvar "MILLISECS") t0))
  (ac:log (list etiq 'GUIA guia 'TOPEROL top 'BUILD_MS bms
                'PIEZAS (length (urb:generated-objects h))))
  (setq t0 (getvar "MILLISECS"))
  (setq blk (vl-catch-all-apply 'urb:package-anden (list en)))
  (setq pms (- (getvar "MILLISECS") t0))
  (ac:log (list etiq 'PACK_MS pms
                'ES_BLOQUE (and (not (vl-catch-all-error-p blk)) (= (type blk) 'VLA-OBJECT))
                'SUELTAS (length (urb:generated-objects h))))
  (if (and (not (vl-catch-all-error-p blk)) (= (type blk) 'VLA-OBJECT))
    (progn (setq at (urb:block-attribute-values blk))
      (ac:log (list etiq 'AREA (mp:getval "AREA_M2" at "0")
                    'GUIA_ML (mp:getval "LOSETA_GUIA_ML" at "0")
                    'TOPEROL_ML (mp:getval "LOSETA_TOPEROL_ML" at "0")))))
  bms)

(setq ac:r (vl-catch-all-apply 'ac:caso (list "A_SIN_TACTIL" 1000.0 450.0 0.209 "No" "No")))
(if (vl-catch-all-error-p ac:r) (ac:log (list 'ERROR_A (vl-catch-all-error-message ac:r))))
(setq ac:r (vl-catch-all-apply 'ac:caso (list "B_CON_TACTIL" 3000.0 450.0 0.209 "Si" "Si")))
(if (vl-catch-all-error-p ac:r) (ac:log (list 'ERROR_B (vl-catch-all-error-message ac:r))))
;; caso largo: el doble de desarrollo, para ver como escala
(setq ac:r (vl-catch-all-apply 'ac:caso (list "C_LARGO_CON_TACTIL" 6000.0 900.0 0.209 "Si" "Si")))
(if (vl-catch-all-error-p ac:r) (ac:log (list 'ERROR_C (vl-catch-all-error-message ac:r))))
(ac:log 'PARCIAL)
(princ)

;; --- prueba del SELLO: la reparacion de hatches ya no debe repetirse ---
;; En este punto ya hay andenes empaquetados, o sea hatches URB-ANDEN-*
;; dentro de bloques: es el escenario que el barrido recorre.
(setq ac:t0 (getvar "MILLISECS"))
(setq ac:n1 (vl-catch-all-apply 'urb:repair-anden-hatches nil))
(ac:log (list 'SELLO_A_BARRIDO_COMPLETO 'MS (- (getvar "MILLISECS") ac:t0)
              'REPARADOS (if (vl-catch-all-error-p ac:n1) 'ERROR ac:n1)))
(urb:config-write "URB_HATCH_REPAIR_VER" *urb-version*)
(setq ac:t0 (getvar "MILLISECS"))
(setq ac:n2 (vl-catch-all-apply 'urb:repair-anden-hatches-si-hace-falta nil))
(ac:log (list 'SELLO_B_CON_SELLO 'MS (- (getvar "MILLISECS") ac:t0)
              'DEVOLVIO (if (vl-catch-all-error-p ac:n2) 'ERROR ac:n2)))
(urb:config-write "URB_HATCH_REPAIR_VER" "")
(setq ac:t0 (getvar "MILLISECS"))
(setq ac:n3 (vl-catch-all-apply 'urb:repair-anden-hatches-si-hace-falta nil))
(ac:log (list 'SELLO_C_SIN_SELLO 'MS (- (getvar "MILLISECS") ac:t0)
              'DEVOLVIO (if (vl-catch-all-error-p ac:n3) 'ERROR ac:n3)))
(ac:log 'FIN_TOTAL)
(princ)
