(vl-load-com)
(setq *urb-suppress-auto-migration* T)
(setq ac:out "C:/Users/juanbusper/Documents/URBANISMO/work/claude_20260914_anden543/capas_result.txt")
(defun ac:log (v / f)
  (setq f (open ac:out "a")) (write-line (vl-princ-to-string (list (getvar "MILLISECS") v)) f) (close f))
(load "C:/Users/juanbusper/Streaming de Google Drive/Mi unidad/VARIOS/CLAUDE/proyectos/URBANISMO EXTERNO/urbanismo_cantidades.lsp")
(ac:log (list 'MOTOR (if (boundp '*urb-version*) *urb-version* "?")))
(setq *urb-suppress-auto-migration* T)
(defun ac:curva (dx dy r th / b d p0 p1 p2 q0 q1 q2)
  (setq d 1.75 b (/ (sin (/ th 4.0)) (cos (/ th 4.0)))
        p0 (list dx (+ dy d))
        p1 (list (+ dx (* (- r d) (sin th))) (+ dy r (- (* (- r d) (cos th)))))
        p2 (list (+ dx (* 2 r (sin th))) (+ dy (* 2 r (- 1 (cos th))) d))
        q0 (list dx (- dy d))
        q1 (list (+ dx (* (+ r d) (sin th))) (+ dy r (- (* (+ r d) (cos th)))))
        q2 (list (+ dx (* 2 r (sin th))) (- (+ dy (* 2 r (- 1 (cos th)))) d)))
  (entmakex (list '(0 . "LWPOLYLINE") '(100 . "AcDbEntity") '(8 . "0")
    '(100 . "AcDbPolyline") '(90 . 6) '(70 . 1)
    (cons 10 p0) (cons 42 b) (cons 10 p1) (cons 42 (- b)) (cons 10 p2) '(42 . 0.0)
    (cons 10 q2) (cons 42 b) (cons 10 q1) (cons 42 (- b)) (cons 10 q0) '(42 . 0.0))))
;; censo de piezas por CAPA y por TIPO de entidad
(defun ac:censo (objs / tabla item clave n out)
  (setq tabla nil)
  (foreach item objs
    (setq clave (strcat (vla-get-Layer item) " | " (vla-get-ObjectName item)))
    (if (assoc clave tabla)
      (setq tabla (subst (cons clave (1+ (cdr (assoc clave tabla)))) (assoc clave tabla) tabla))
      (setq tabla (cons (cons clave 1) tabla))))
  (foreach item tabla (ac:log (list 'CENSO (car item) (cdr item))))
  (length tabla))
(setq ac:en (ac:curva 1000.0 1000.0 450.0 0.209))
(urb:set-anden-data ac:en "Loseta" "1" "1" "Si" "Si" "20 x 20 cm" "No" "Seleccionar en dibujo" "Via creada")
(setq *urb-current-tactile-side-choice* nil *urb-current-tactile-side-point* (list 1000.0 1001.0))
(setq ac:h (cdr (assoc 5 (entget ac:en))))
(vl-catch-all-apply 'urb:build-anden-finish (list ac:en "Loseta" "Si" "Si" "20 x 20 cm"))
(ac:log (list 'ESTADO_PATRON_TOPEROL *urb-toperol-pattern-state*
              'FALLOS_PIEZA *urb-toperol-fallos-pieza*))
(setq ac:objs (urb:generated-objects ac:h))
(ac:log (list 'TOTAL_PIEZAS (length ac:objs)))
(ac:censo ac:objs)
(ac:log 'FIN)
(princ)
