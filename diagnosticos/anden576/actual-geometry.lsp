(vl-load-com)

(setq a576:dir (getenv "URB_TEST_LAB"))
(setq a576:out (strcat a576:dir "/actual_geometry576.txt"))
(setq a576:paths (strcat a576:dir "/actual_paths576.txt"))

(defun a576:log (text / stream)
  (setq stream (open a576:out "a"))
  (write-line text stream)
  (close stream))

(defun a576:check (condition label)
  (a576:log (strcat (if condition "PASS " "FAIL ") label))
  (if (not condition) (vl-exit-with-error label)))

(defun a576:range (ename chain / point value low high)
  (foreach point (urb:lwpoly-points-with-arcs-fine ename)
    (setq value (urb:chain-min-distance chain point)
          low (if low (min low value) value)
          high (if high (max high value) value)))
  (list low high (- high low)))

(defun a576:dump (label points / stream text point)
  (setq stream (open a576:paths "a") text label)
  (foreach point points
    (setq text (strcat text ";" (rtos (car point) 2 6) "," (rtos (cadr point) 2 6))))
  (write-line text stream)
  (close stream))

(defun a576:run (/ original target boundary points reference driving copy base rings
                   chain curve-len midpoint mid-point mid-angle candidate perp-sign
                   off-sign test guide-offset guide-near guide-far top-far
                   guide-near-range guide-far-range top-range temp)
  (a576:log (strcat "VERSION " *urb-version*))
  (foreach original (urb:all-anden-blocks)
    (if (wcmatch (cdr (assoc 2 (entget original))) "URB_ANDEN_13D362_*")
      (setq target original)))
  (a576:check target "real 188 m source sidewalk exists")
  (setq boundary (urb:explode-anden-block-boundary target)
        points (urb:lwpoly-points-with-arcs-fine boundary)
        reference '(83038.9 95306.5 0.0)
        *urb-current-tactile-side-point* reference
        *urb-current-tactile-side-choice* nil
        driving (urb:anden-tactile-chain points))
  (if (and (urb:anden-near-root-container-p boundary)
           (not (vl-some '(lambda (item)
             (and (= (car item) 42) (not (equal (cdr item) 0.0 1e-12))))
             (entget boundary))))
    (setq driving (urb:anden-tactile-chain (urb:ring-remove-notches points))))
  (setq chain (urb:open-poly-from-points driving 0.0)
        curve-len (urb:curve-length chain)
        midpoint (* 0.5 curve-len)
        mid-point (urb:curve-pt chain midpoint)
        mid-angle (urb:curve-tangent chain midpoint)
        perp-sign 1.0
        candidate (polar mid-point (+ mid-angle (* 0.5 pi)) 0.3))
  (if (not (urb:point-in-poly-p candidate points)) (setq perp-sign -1.0))
  (setq off-sign 1.0 test (urb:offset-poly chain 0.3))
  (if test
    (progn
      (setq candidate (urb:curve-pt test (* 0.5 (urb:curve-length test))))
      (if (or (null candidate) (not (urb:point-in-poly-p candidate points)))
        (setq off-sign -1.0))
      (entdel test))
    (setq off-sign -1.0))
  (setq copy (vla-Copy (vlax-ename->vla-object boundary))
        base (urb:anden-region-from-object copy))
  (urb:safe-delete copy)
  (setq base (urb:apply-anden-cutouts base)
        rings (urb:region-polygons base)
        guide-offset (urb:guide-uniform-offset chain rings 2.5 0.2 perp-sign))
  (a576:log (strcat "SIDE_DISTANCE="
    (rtos (urb:chain-min-distance driving reference) 2 6)
    " GUIDE_OFFSET=" (rtos guide-offset 2 6)
    " OFF_SIGN=" (rtos off-sign 2 0) " PERP_SIGN=" (rtos perp-sign 2 0)))
  (setq guide-near (urb:offset-poly chain (* off-sign guide-offset))
        guide-far (urb:offset-poly chain (* off-sign (+ guide-offset 0.2)))
        top-far (urb:offset-poly chain (* off-sign 0.2)))
  (a576:check (and guide-near guide-far top-far) "all four tactile edges can be offset")
  (setq guide-near-range (a576:range guide-near driving)
        guide-far-range (a576:range guide-far driving)
        top-range (a576:range top-far driving))
  (a576:log (strcat "GUIDE_NEAR " (vl-princ-to-string guide-near-range)))
  (a576:log (strcat "GUIDE_FAR " (vl-princ-to-string guide-far-range)))
  (a576:log (strcat "TOP_FAR " (vl-princ-to-string top-range)))
  (a576:check (< (nth 2 guide-near-range) 0.03)
    "near guide edge is parallel to the selected road side")
  (a576:check (< (nth 2 guide-far-range) 0.03)
    "far guide edge is parallel to the selected road side")
  (a576:check (< (nth 2 top-range) 0.03)
    "toperol edge is parallel to the same selected side")
  (a576:check (< (abs (- (car guide-near-range) guide-offset)) 0.03)
    "guide starts at its single uniform offset")
  (a576:check (< (abs (- (car top-range) 0.2)) 0.03)
    "toperol remains adjacent to selected side")
  (a576:dump "SELECTED_SIDE" driving)
  (a576:dump "TOPEROL_FAR" (urb:lwpoly-points-with-arcs-fine top-far))
  (a576:dump "GUIDE_NEAR" (urb:lwpoly-points-with-arcs-fine guide-near))
  (a576:dump "GUIDE_FAR" (urb:lwpoly-points-with-arcs-fine guide-far))
  (a576:dump "BOUNDARY" points)
  (foreach temp (list guide-near guide-far top-far chain boundary)
    (if temp (entdel temp)))
  (urb:safe-delete base)
  (a576:log "FINISHED (geometry only; original DWG unchanged)"))

(if (findfile a576:out) (vl-file-delete a576:out))
(if (findfile a576:paths) (vl-file-delete a576:paths))
(setq a576:result (vl-catch-all-apply 'a576:run nil))
(if (vl-catch-all-error-p a576:result)
  (a576:log (strcat "FAILED " (vl-catch-all-error-message a576:result))))
(princ)
