(vl-load-com)
(setq v12:dir "C:/Users/juanbusper/Documents/URBANISMO/work/anden5712/"
      v12:pass 0 v12:fail 0)
(defun v12:log (s / f)
  (setq f (open (strcat v12:dir "result.txt") "a")) (write-line s f) (close f))
(defun v12:check (ok msg)
  (if ok (setq v12:pass (1+ v12:pass)) (setq v12:fail (1+ v12:fail)))
  (v12:log (strcat (if ok "PASS " "FAIL ") msg)))
(defun v12:poly (pts / en)
  (setq en (urb:poly-chain-polyline
    (mapcar '(lambda (p) (list (car p) (cadr p) 0.0)) pts)))
  (vla-put-Closed (urb:as-vla-object en) :vlax-true) en)
(defun v12:rings (parent feature / rings ob)
  (foreach ob (urb:generated-objects parent)
    (if (and (= (vla-get-ObjectName ob) "AcDbRegion")
             (wcmatch (vla-get-Layer ob) (strcat "*" feature "*")))
      (setq rings (append rings (urb:region-polygons ob))))) rings)
(defun v12:inside (pt rings)
  (vl-some '(lambda (r) (urb:point-in-poly-p pt r)) rings))
(defun v12:tactile (pts anchor label / en parent chain region poly len s p a sign
                         top gui hit-top hit-gui total out t0)
  (setq en (v12:poly pts) parent (cdr (assoc 5 (entget en)))
        *urb-current-tactile-side-anchor* anchor
        *urb-current-tactile-side-point* nil *urb-current-tactile-side-choice* nil
        chain (urb:anden-tactile-chain
          (if (wcmatch label "notch*") (urb:ring-remove-notches pts) pts))
        region (urb:polygon-region pts 0.0)
        t0 (getvar "MILLISECS")
        out (urb:create-accessibility-features-offset region pts chain "Si" "Si" "20 x 20 cm" parent)
        top (v12:rings parent "TOPEROL") gui (v12:rings parent "GUIA")
        poly (urb:open-poly-from-points chain 0.0) len (urb:curve-length poly)
        sign (if (< (urb:polygon-signed-area pts) 0.0) -1.0 1.0)
        s 1.0 total 0 hit-top 0 hit-gui 0)
  (while (< s (- len 1.0))
    (setq p (urb:curve-pt poly s) a (+ (urb:curve-tangent poly s) (* sign pi 0.5)))
    ;; Skip only the intentional notch; never waive an unexplained gap.
    (if (urb:point-in-poly-p (polar p a 0.1) pts)
      (progn (setq total (1+ total))
        (if (v12:inside (polar p a 0.1) top) (setq hit-top (1+ hit-top)))
        (if (v12:inside (polar p a 2.6) gui) (setq hit-gui (1+ hit-gui)))))
    (setq s (+ s 0.5)))
  (v12:log (strcat label " stations=" (itoa total) " top=" (itoa hit-top)
    " guide=" (itoa hit-gui) " ms=" (itoa (- (getvar "MILLISECS") t0))))
  (v12:check out (strcat label " builds"))
  (v12:check (and (> total 20) (= total hit-top)) (strcat label " toperol continuity every 0.5m"))
  (v12:check (= total hit-gui) (strcat label " guide continuity every 0.5m"))
  (foreach ob (urb:generated-objects parent) (urb:safe-delete ob))
  (urb:safe-delete region) (entdel en) (entdel poly))
(defun v12:run (/ notch inner outer pts k a en parent out packed t0)
  (if (/= (strcase (strcat (getvar "DWGPREFIX") (getvar "DWGNAME")))
          (strcase (strcat (vl-string-translate "/" "\\" v12:dir) "fixture.dwg")))
    (vl-exit-with-error "Not the exact local fixture"))
  (v12:check (= *urb-version* "5.7.12") "version")
  (urb:prepare-anden-layers)
  (if (not *v12-saved-only*) (progn
  (setq notch '((0.0 0.0) (14.0 0.0) (14.0 1.0) (16.0 1.0)
                (16.0 0.0) (30.0 0.0) (30.0 4.0) (0.0 4.0)))
  (v12:check (not (urb:point-in-poly-p '(15.0 0.3) notch))
    "baseline midpoint test would reverse the entire tactile stripe at notch")
  (v12:tactile notch '(10.0 0.0) "notch CCW")
  (v12:tactile (reverse notch) '(10.0 0.0) "notch CW")
  ;; Quarter circle with 1-degree steps. Inner and outer costados, both windings.
  (setq k 0)
  (repeat 91
    (setq a (* pi (/ k 180.0))
          inner (cons (list (+ 100.0 (* 30.0 (cos a))) (* 30.0 (sin a))) inner)
          outer (cons (list (+ 100.0 (* 34.0 (cos a))) (* 34.0 (sin a))) outer)
          k (1+ k)))
  (setq pts (append (reverse inner) outer))
  (v12:tactile pts '(121.213203 21.213203) "curve inner")
  (v12:tactile pts '(124.041631 24.041631) "curve outer")
  (v12:tactile (reverse pts) '(121.213203 21.213203) "curve reversed")
  ))
  ;; Exact four vertices saved in the last user's failure. Fixture predates
  ;; two surrounding cutouts, so this is not claimed as full reproduction.
  (setq en (v12:poly '((82984.8946 95231.5402) (82987.4024 95229.4015)
                      (83028.8159 95278.4749) (83026.2809 95280.5876)))
        parent (cdr (assoc 5 (entget en)))
        *urb-current-tactile-side-anchor* '(83005.6 95256.1)
        *urb-current-tactile-side-point* nil)
  (urb:set-anden-data en "Loseta" "1" "1" "Si" "Si" "20 x 20 cm" "No" "SUP_TN" "Cotas seleccionadas")
  (setq t0 (getvar "MILLISECS")
        out (urb:build-anden-finish en "Loseta" "Si" "Si" "20 x 20 cm"))
  (v12:check out "saved four-vertex case builds finish")
  (v12:check (> (urb:count-toperol-symbols (urb:generated-objects parent)) 0) "saved case has tactile texture")
  (if out (setq packed (urb:package-anden en)))
  (v12:check (and packed (= (vla-get-ObjectName packed) "AcDbBlockReference")) "saved case one block")
  (v12:check (= (length (urb:generated-objects parent)) 0) "saved case zero loose pieces")
  (v12:log (strcat "SAVED_BUILD_AND_PACKAGE_MS=" (itoa (- (getvar "MILLISECS") t0))))
  ;; The next SCR lines exercise real getkword, with exactly one answer each.
  (setq v12:prompt-en (v12:poly '((500.0 0.0) (530.0 0.0) (530.0 4.0) (500.0 4.0)))
        *urb-current-tactile-side-anchor* '(515.0 0.0)
        *urb-current-tactile-side-point* nil))
(setq v12:result (vl-catch-all-apply 'v12:run nil))
(if (vl-catch-all-error-p v12:result)
  (v12:log (strcat "ERROR " (vl-catch-all-error-message v12:result))))
(defun v12:after2 ()
  (v12:check (equal (urb:tactile-side-data v12:prompt-en) '(515.0 4.0) 1e-6)
    "one input 2 selects opposite and returns without reprompt"))
(defun v12:finish ()
  (v12:check (equal (urb:tactile-side-data v12:prompt-en) '(515.0 4.0) 1e-6)
    "one input 1 keeps highlighted side")
  (v12:log (strcat "SUMMARY pass=" (itoa v12:pass) " fail=" (itoa v12:fail)))
  (if (and (= v12:fail 0) (not (vl-catch-all-error-p v12:result))) (v12:log "FINISHED")))
(princ)
