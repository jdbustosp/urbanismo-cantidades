(setq f18:out "C:/Users/juanbusper/Documents/URBANISMO/work/flujo5718/core.txt"
      f18:pass 0 f18:fail 0)
(defun f18:log (s / f) (setq f (open f18:out "a")) (write-line s f) (close f))
(defun f18:check (ok s)
  (if ok (setq f18:pass (1+ f18:pass)) (setq f18:fail (1+ f18:fail)))
  (f18:log (strcat (if ok "PASS " "FAIL ") s)))
(f18:check (= *urb-version* "5.7.18") "version")
(setq f18:curve '((0.0 0.0) (20.0 0.0) (30.0 10.0) (40.0 0.0) (60.0 0.0)))
(f18:check (urb:anden-needs-segmented-p f18:curve) "curved chain would use automatic segmented mode")
(f18:check (not (urb:anden-use-segmented-p f18:curve 0.0)) "marked axis overrides segmented fan")
(f18:check (urb:anden-use-segmented-p f18:curve nil) "without marked axis automatic segmentation remains")
(f18:check (equal (urb:anden-axis-from-user-points '(0.0 0.0) '(10.0 0.0) nil) 0.0 1e-10)
  "two points store longitudinal angle directly")
(f18:check (equal (urb:anden-axis-from-user-points nil nil 0.0) (/ pi 2.0) 1e-10)
  "automatic curved fallback keeps historical perpendicular")
;; Isolate the orchestration: one invocation must request exactly one trace.
(setq f18:draws 0 f18:registers 0)
(defun urb:draw-open-polyline (label) (setq f18:draws (1+ f18:draws)) 'FAKE)
(defun urb:canuela-plu-register (en etapa sub ancho id)
  (setq f18:registers (1+ f18:registers)) 12.5)
(f18:check (equal (urb:canuela-plu-draw-one "4" "4B" 0.4 "C1") 12.5 1e-10)
  "one canuela returns its length")
(f18:check (and (= f18:draws 1) (= f18:registers 1)) "one command draws/registers one canuela only")
(f18:log (strcat "SUMMARY pass=" (itoa f18:pass) " fail=" (itoa f18:fail)))
(if (= f18:fail 0) (f18:log "FINISHED"))
(princ)
