(setq nfile "C:/Users/juanbusper/Documents/URBANISMO/work/codex4820/native.txt")
(defun nlog (s / f) (setq f (open nfile "a")) (write-line s f) (close f))
(defun ntry (label fn args / r)
  (setq r (vl-catch-all-apply fn args))
  (nlog (strcat label " " (if (vl-catch-all-error-p r) (vl-catch-all-error-message r) (vl-princ-to-string r)))) r)
(nlog "START")
(ntry "LOAD" 'load '("C:/Users/juanbusper/Documents/URBANISMO/work/codex4820/current.lsp"))
(setq urb:native-fill-original urb:fill-tactile-symbols)
(defun urb:fill-tactile-symbols (region feature axis layer phase parent module / result)
  (ntry (strcat feature " LOOPS") 'urb:region-polygons (list region))
  (setq result (ntry (strcat feature " SYMBOLS") 'urb:native-fill-original (list region feature axis layer phase parent module)))
  (if (vl-catch-all-error-p result) nil result))
(ntry "LAYERS" 'urb:prepare-anden-layers nil)
(ntry "LAYER" 'urb:ensure-layer '("URB-RAMPA" 4 T))
(setq test-en (ntry "POLY" 'urb:ramp-quad-poly '((0 0 0) 0.7 1.0 0.0 0.0 6.0 2.0 "URB-RAMPA")))
(ntry "DATA" 'urb:set-anden-data (list test-en "Loseta" "1" "1" "Si" "Si" "20 x 20 cm" "No" "SUP_TN" "Via creada"))
(setq *urb-current-tactile-side-point* (urb:local-to-world 3.0 2.0 0.7))
(ntry "PATTERN" 'urb:set-anden-pattern-mode (list test-en "AUTOMATICO"))
(ntry "FINISH" 'urb:build-anden-finish (list test-en "Loseta" "Si" "Si" "20 x 20 cm"))
(setq ts (ssget "_X" '((0 . "CIRCLE"))))
(nlog (strcat "CIRCLES_BEFORE " (itoa (if ts (sslength ts) 0))))
(setq bref (ntry "PACKAGE" 'urb:package-anden (list test-en)))
(defun count-block-circles (ref / block obj n)
  (setq n 0 block (vla-Item (vla-get-Blocks (urb:doc)) (vla-get-Name ref)))
  (vlax-for obj block (if (= (vla-get-ObjectName obj) "AcDbCircle") (setq n (1+ n)))) n)
(ntry "CIRCLES_BLOCK" 'count-block-circles (list bref))
(nlog "DONE")
(princ)
