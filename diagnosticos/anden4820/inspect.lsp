(setq rf (open "C:/Users/juanbusper/Documents/URBANISMO/work/codex4820/saved_dwg.txt" "w"))
(defun rl (s) (write-line s rf))
(setq ss (ssget "_X" '((0 . "INSERT") (2 . "URB_ANDEN_*"))))
(if ss
  (progn
    (rl (strcat "ANDENES " (itoa (sslength ss))))
    (setq i (max 0 (- (sslength ss) 5)))
    (while (< i (sslength ss))
      (setq en (ssname ss i) d (entget en) name (cdr (assoc 2 d)))
      (rl (strcat "ANDEN " (cdr (assoc 5 d)) " " name))
      (setq at (entnext en))
      (while (and at (= (cdr (assoc 0 (entget at))) "ATTRIB"))
        (setq ad (entget at))
        (if (wcmatch (cdr (assoc 2 ad)) "*TOPEROL*,*GUIA*,*FORMATO*")
          (rl (strcat (cdr (assoc 2 ad)) "=" (cdr (assoc 1 ad)))))
        (setq at (entnext at)))
      (setq be (tblobjname "BLOCK" name) ne (entnext be) c 0 topentities 0)
      (while (and ne (/= (cdr (assoc 0 (entget ne))) "ENDBLK"))
        (setq nd (entget ne))
        (if (wcmatch (cdr (assoc 8 nd)) "*TOPEROL*")
          (progn (setq topentities (1+ topentities))
            (if (= (cdr (assoc 0 nd)) "CIRCLE") (setq c (1+ c)))))
        (setq ne (entnext ne)))
      (rl (strcat "TOPEROL ENTIDADES=" (itoa topentities) " CIRCULOS=" (itoa c)))
      (setq i (1+ i)))))
(rl "DONE")
(close rf)
(princ)
