(defun urb:offset-strip-symbols (chain-poly len d1 d2 perp-sign feature module layer parent-handle loops / lab:t0 lab:result)
 (setq lab:t0 (getvar "MILLISECS"))
 (setq lab:result (lab:original-offset-strip-symbols chain-poly len d1 d2 perp-sign feature module layer parent-handle loops))
 (lab:record (strcat "offset-strip-symbols/" feature) (- (getvar "MILLISECS") lab:t0))
 lab:result)

(defun urb:fill-tactile-symbols (region feature angle-value layer phase-offset parent-handle module / lab:t0 lab:result)
 (setq lab:t0 (getvar "MILLISECS"))
 (setq lab:result (lab:original-fill-tactile-symbols region feature angle-value layer phase-offset parent-handle module))
 (lab:record (strcat "fill-tactile-symbols/" feature) (- (getvar "MILLISECS") lab:t0))
 lab:result)

(defun urb:add-toperol-hatch (boundary layer angle-value color / lab:t0 lab:result)
 (setq lab:t0 (getvar "MILLISECS"))
 (setq lab:result (lab:original-add-toperol-hatch boundary layer angle-value color))
 (lab:record "add-toperol-hatch" (- (getvar "MILLISECS") lab:t0))
 lab:result)

(defun urb:flush-tactile-batch (layer parent-handle / lab:t0 lab:result)
 (setq lab:t0 (getvar "MILLISECS"))
 (setq lab:result (lab:original-flush-tactile-batch layer parent-handle))
 (lab:record "flush-tactile-batch" (- (getvar "MILLISECS") lab:t0))
 lab:result)

(defun urb:create-accessibility-features (ename guia toperol format / lab:t0 lab:result)
 (setq lab:t0 (getvar "MILLISECS"))
 (setq lab:result (lab:original-create-accessibility-features ename guia toperol format))
 (lab:record "create-accessibility-features" (- (getvar "MILLISECS") lab:t0))
 lab:result)

(defun urb:evaluate-render-hatch (hatch / lab:t0 lab:result)
 (setq lab:t0 (getvar "MILLISECS"))
 (setq lab:result (lab:original-evaluate-render-hatch hatch))
 (lab:record "evaluate-render-hatch" (- (getvar "MILLISECS") lab:t0))
 lab:result)

(defun urb:anden-cutout-blocks ( / lab:t0 lab:result)
 (setq lab:t0 (getvar "MILLISECS"))
 (setq lab:result (lab:original-anden-cutout-blocks ))
 (lab:record "anden-cutout-blocks" (- (getvar "MILLISECS") lab:t0))
 lab:result)

(defun urb:objects-bbox-overlap-p (first second tolerance / lab:t0 lab:result)
 (setq lab:t0 (getvar "MILLISECS"))
 (setq lab:result (lab:original-objects-bbox-overlap-p first second tolerance))
 (lab:record "objects-bbox-overlap-p" (- (getvar "MILLISECS") lab:t0))
 lab:result)

(defun urb:block-footprint-region (block-ref / lab:t0 lab:result)
 (setq lab:t0 (getvar "MILLISECS"))
 (setq lab:result (lab:original-block-footprint-region block-ref))
 (lab:record "block-footprint-region" (- (getvar "MILLISECS") lab:t0))
 lab:result)
