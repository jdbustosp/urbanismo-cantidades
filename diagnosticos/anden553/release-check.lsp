(load "C:/Users/juanbusper/Documents/URBANISMO/work/anden_three_options/helpers.lsp")
(defun rc:hatches (def / item result data)
 (vlax-for item def
  (if (= (vla-get-ObjectName item) "AcDbHatch")
   (progn (setq data (vl-remove-if '(lambda (p) (member (car p) '(-1 5 330 360 102 -3))) (entget (vlax-vla-object->ename item))))
    (setq result (cons data result)))))
 (vl-sort result 'nx:less))
(defun rc:case (tag g top format side / en h block def result nested o)
 (setq en (nx:curve 80.0) h (cdr (assoc 5 (entget en))))
 (urb:set-anden-data en "Loseta" "1" "1" g top format "No" "Seleccionar en dibujo" "Via creada")
 (setq *urb-current-tactile-side-choice* nil *urb-current-tactile-side-point* side)
 (bn:check (list tag 'BUILD) (urb:build-anden-finish en "Loseta" g top format))
 (setq block (urb:package-anden en) def (vla-Item (vla-get-Blocks (urb:doc)) (vla-get-Name block)) nested 0)
 (vlax-for o def (if (= (vla-get-ObjectName o) "AcDbBlockReference") (setq nested (1+ nested))))
 (bn:check (list tag 'FLAT) (= nested 0))
 (bn:check (list tag 'NO_LOOSE) (= 0 (nx:loose h)))
 (bn:check (list tag 'ORDER) (= 0 (BNCHECKORDER (vla-get-Name block)))))
(defun rc:obstacle (/ ref)
 (entmake '((0 . "BLOCK") (2 . "URB_MOB_CONT_RELEASE") (70 . 0) (10 0.0 0.0 0.0)))
 (entmake '((0 . "LWPOLYLINE") (100 . "AcDbEntity") (8 . "0") (100 . "AcDbPolyline") (90 . 4) (70 . 1)
  (10 -0.6 -0.6) (10 0.6 -0.6) (10 0.6 0.6) (10 -0.6 0.6)))
 (entmake '((0 . "ENDBLK")))
 (vla-InsertBlock (urb:space) (vlax-3d-point '(82810.0 102400.0 0.0)) "URB_MOB_CONT_RELEASE" 1.0 1.0 1.0 0.0))
(defun rc:run (/ a b defs o bad original count result obstacle cut key loss)
 (bn:log 'RELEASE_CHECK_BEGIN)
 (command "_.NETLOAD" (strcat (getenv "TEMP") "/urbcant_anden553_build/UrbAndenFast2023_v553.dll"))
 (command "_.NETLOAD" "C:/Users/juanbusper/Documents/URBANISMO/work/anden_three_options/CheckBatch.dll")
 (load "C:/Users/juanbusper/Documents/URBANISMO/work/anden_batchnet/baseline.lsp")
 (setq a (bn:case "FINAL_BASE188" 450.0))
 (load "C:/Users/juanbusper/Documents/URBANISMO/work/anden_three_options/release-engine.lsp")
 (bn:check 'RELEASE_VERSION (= *urb-version* "5.5.3"))
 (bn:check 'FAST_PREFLIGHT (urb:ensure-anden-fast))
 (setq b (bn:case "FINAL553_188" 450.0)) (bn:compare 'FINAL553 a b)
 (vlax-for o (vla-get-Blocks (urb:doc)) (if (wcmatch (vla-get-Name o) "URB_ANDEN_*") (setq defs (append defs (list o)))))
 (bn:check 'ALL_HATCHES_EXACT_LAYERS_ANGLES_ORIGINS (equal (rc:hatches (car defs)) (rc:hatches (cadr defs)) 1e-9))
 (rc:case 'SIN_GUIA_NI_TOPEROL "No" "No" "20 x 20 cm" '(82800.0 102401.0))
 (rc:case 'SOLO_TOPEROL "No" "Si" "20 x 20 cm" '(82800.0 102401.0))
 (rc:case 'SOLO_GUIA_OTRO_LADO "Si" "No" "40 x 40 cm" '(82800.0 102399.0))
 (setq obstacle (rc:obstacle) cut (bn:case "FINAL553_CURVA_CONTENEDOR188" 450.0))
 (bn:check 'ROOT_NET_AREA (equal (- (atof (cdr (assoc "AREA_M2" (cadr b)))) (atof (cdr (assoc "AREA_M2" (cadr cut))))) 1.44 1e-6))
 (foreach key '("LOSETA_GUIA_M2" "LOSETA_TOPEROL_M2")
  (setq loss (- (atof (cdr (assoc key (cadr b)))) (atof (cdr (assoc key (cadr cut))))))
  (bn:check (list 'ROOT_NO_TRUNCATION key) (and (>= loss -1e-6) (<= loss 1.440001))))
 (bn:check 'ROOT_TOP_PATTERN (= *urb-toperol-pattern-state* "SI"))
 (bn:check 'ROOT_TOP_NO_FAILURES (= *urb-toperol-fallos-pieza* 0))
 (urb:safe-delete obstacle)
 ;; A malicious/unexpected nested transform must leave the block unchanged.
 (setq bad (vla-Add (vla-get-Blocks (urb:doc)) (vlax-3d-point '(0 0 0)) "URB_ANDEN_LAB_BAD"))
 (setq original (vla-InsertBlock bad (vlax-3d-point '(5 0 0)) (vla-get-Name (car defs)) 1.0 1.0 1.0 0.0) count (vla-get-Count bad))
 (setq result (vl-catch-all-apply 'URBANDENFLAT553 '("URB_ANDEN_LAB_BAD")))
 (bn:check 'REJECT_UNEXPECTED_NESTED (vl-catch-all-error-p result))
 (bn:check 'ROLLBACK_PRESERVES_BLOCK (= count (vla-get-Count bad)))
 (bn:check 'ROLLBACK_PRESERVES_REFERENCE (not (vlax-erased-p original)))
 (command "_.QSAVE")
 (bn:log (list 'RELEASE_CHECK_DONE 'FAILURES bn:fail)))
(setq rc:r (vl-catch-all-apply 'rc:run nil))
(if (vl-catch-all-error-p rc:r) (bn:log (list 'RELEASE_CHECK_ERROR (vl-catch-all-error-message rc:r))))
(princ)
