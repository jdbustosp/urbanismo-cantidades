;; Lab only: lifetime is exactly one measured construction. No footprint cache.
(defun lab:reset-cache () (setq lab:cutouts-ready nil lab:cutouts nil lab:boxes nil lab:cache-hits 0 lab:cache-misses 0))
(defun urb:anden-cutout-blocks (/ lab:t0 lab:r)
 (setq lab:t0 (getvar "MILLISECS"))
 (if (and lab:cache-enabled lab:cutouts-ready)
  (setq lab:r lab:cutouts)
  (progn (setq lab:r (lab:original-anden-cutout-blocks))
   (if lab:cache-enabled (setq lab:cutouts lab:r lab:cutouts-ready T))))
 (lab:record "anden-cutout-blocks" (- (getvar "MILLISECS") lab:t0)) lab:r)
(defun lab:get-box (obj can-cache / key found lo hi r)
 (setq key (vla-get-Handle obj) found (if can-cache (assoc key lab:boxes)))
 (if found (progn (setq lab:cache-hits (1+ lab:cache-hits)) (cdr found))
  (progn
   (setq lab:cache-misses (1+ lab:cache-misses)
     r (vl-catch-all-apply 'vla-GetBoundingBox (list obj 'lo 'hi)))
   (if (not (vl-catch-all-error-p r))
    (progn (setq r (list (vlax-safearray->list lo) (vlax-safearray->list hi)))
     (if can-cache (setq lab:boxes (cons (cons key r) lab:boxes))) r)
    nil))))
(defun urb:objects-bbox-overlap-p (first second tolerance / a b a1 a2 b1 b2 r t0)
 (setq t0 (getvar "MILLISECS"))
 (if (not lab:cache-enabled)
  (setq r (lab:original-objects-bbox-overlap-p first second tolerance))
  (progn
   ;; Always refresh first box: boolean operations can change that region.
   ;; Cache ONLY immutable INSERT obstacle boxes in this isolated build.
   (setq a (lab:get-box first nil)
     b (lab:get-box second (= (vla-get-ObjectName second) "AcDbBlockReference"))
     tolerance (if (numberp tolerance) tolerance 0.0))
   (if (and a b)
    (progn (setq a1 (car a) a2 (cadr a) b1 (car b) b2 (cadr b))
     (setq r (and (<= (- (car a1) tolerance) (+ (car b2) tolerance))
      (>= (+ (car a2) tolerance) (- (car b1) tolerance))
      (<= (- (cadr a1) tolerance) (+ (cadr b2) tolerance))
      (>= (+ (cadr a2) tolerance) (- (cadr b1) tolerance))))))))
 (lab:record "objects-bbox-overlap-p" (- (getvar "MILLISECS") t0)) r)
