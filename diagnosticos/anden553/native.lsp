(load "C:/Users/juanbusper/Documents/URBANISMO/work/anden_three_options/helpers.lsp")
(defun lab:record (key ms / p)
 (if (setq p (assoc key lab:stats))
  (setq lab:stats (subst (list key (1+ (cadr p)) (+ ms (caddr p))) p lab:stats))
  (setq lab:stats (cons (list key 1 ms) lab:stats))))
(defun lab:engine (candidate)
 (load (strcat "C:/Users/juanbusper/Documents/URBANISMO/work/anden_three_options/" (if candidate "profile-candidate.lsp" "profile-engine.lsp")))
 (load "C:/Users/juanbusper/Documents/URBANISMO/work/anden_three_options/wrappers.lsp")
 (load "C:/Users/juanbusper/Documents/URBANISMO/work/anden_three_options/cache.lsp")
 (if candidate (load "C:/Users/juanbusper/Documents/URBANISMO/work/anden_three_options/batch.lsp")))
(defun lab:case (name radius cache / result)
 (setq lab:stats nil lab:cache-enabled cache)
 (lab:reset-cache)
 (setq result (bn:case name radius))
 (setq lab:cache-enabled nil)
 (bn:log (list name 'PHASE_CALLS_MS lab:stats 'BOX_HITS lab:cache-hits 'BOX_MISSES lab:cache-misses
  'TOP_PATTERN *urb-toperol-pattern-state* 'TOP_FAILURES *urb-toperol-fallos-pieza*)) result)
(defun lab:defs (/ item result)
 (vlax-for item (vla-get-Blocks (urb:doc)))
 (vlax-for item (vla-get-Blocks (urb:doc))
  (if (wcmatch (vla-get-Name item) "URB_ANDEN_*") (setq result (cons item result))))
 (reverse result))
(defun lab:hatch-data (e)
 (vl-remove-if '(lambda (p) (member (car p) '(-1 5 330 360 102 -3))) (entget e)))
(defun lab:hatches (def / item result)
 (vlax-for item def (if (= (vla-get-ObjectName item) "AcDbHatch")
  (setq result (cons (lab:hatch-data (vlax-vla-object->ename item)) result))))
 (vl-sort result 'nx:less))
(defun lab:obstacles (/ k def)
 (entmake '((0 . "BLOCK") (2 . "URB_MOB_CONT_LABCACHE") (70 . 0) (10 0.0 0.0 0.0)))
 (entmake '((0 . "LWPOLYLINE") (100 . "AcDbEntity") (8 . "0") (100 . "AcDbPolyline") (90 . 4) (70 . 1)
  (10 -0.6 -0.6) (10 0.6 -0.6) (10 0.6 0.6) (10 -0.6 0.6)))
 (entmake '((0 . "ENDBLK")))
 (setq k 0)
 (repeat 100 (vla-InsertBlock (urb:space) (vlax-3d-point (list (+ 83000.0 (* k 4.0)) 103000.0 0.0)) "URB_MOB_CONT_LABCACHE" 1.0 1.0 1.0 0.0) (setq k (1+ k)))
 (vla-InsertBlock (urb:space) (vlax-3d-point '(82810.0 102400.0 0.0)) "URB_MOB_CONT_LABCACHE" 1.0 1.0 1.0 0.0))
(defun lab:sort-test (def / t0 old new lst)
 (setq t0 (getvar "MILLISECS") lst (urb:block-object-list def))
 (urb:set-block-draw-order def lst)
 (setq old (- (getvar "MILLISECS") t0))
 (bn:check 'LISP_ORDER_VALID (= 0 (BNCHECKORDER (vla-get-Name def))))
 (setq t0 (getvar "MILLISECS")) (BNSORT (vla-get-Name def))
 (setq new (- (getvar "MILLISECS") t0))
 (bn:check 'NET_ORDER_VALID (= 0 (BNCHECKORDER (vla-get-Name def))))
 (bn:log (list 'SORT_MS 'LISP old 'NET new)))
(defun lab:hatch-test (def / item regions handles originals fast t0 com-ms net-ms valid-ms a b e r mismatch)
 (vlax-for item def
  (if (and (= (vla-get-ObjectName item) "AcDbRegion") (< (length regions) 100))
   (setq regions (cons item regions))))
 (setq handles (mapcar 'vla-get-Handle regions) t0 (getvar "MILLISECS"))
 (foreach item regions
  (setq originals (append originals (list
   (urb:add-solid-hatch-detached-safe item "URB-ANDEN-BLOQUE-BLANCO-20X10" 7)
   (urb:add-user-hatch-detached-safe item "URB-ANDEN-BLOQUE-BLANCO-20X10" 0.1 0.317 nil 8 '(82800.0 102400.0))
   (urb:add-user-hatch-detached-safe item "URB-ANDEN-BLOQUE-BLANCO-20X10" 0.2 (+ 0.317 (/ pi 2.0)) nil 8 '(82800.0 102400.0))))))
 (setq com-ms (- (getvar "MILLISECS") t0) t0 (getvar "MILLISECS"))
 (setq fast (LABHATCHES handles) net-ms (- (getvar "MILLISECS") t0) t0 (getvar "MILLISECS"))
 ;; Retain production anti-circle checks: include their cost in the total.
 (foreach e fast (urb:evaluate-render-hatch (vlax-ename->vla-object e)))
 (setq valid-ms (- (getvar "MILLISECS") t0))
 (bn:check 'HATCH_COUNT (= (length originals) (length fast)))
 (setq mismatch 0)
 (mapcar '(lambda (a b)
  (if (not (equal (lab:hatch-data (vlax-vla-object->ename a)) (lab:hatch-data b) 1e-9)) (setq mismatch (1+ mismatch)))) originals fast)
 (bn:check 'HATCH_ALL_DXF_IDENTICAL (= mismatch 0))
 (bn:log (list 'HATCH_BATCH 'REGIONS (length regions) 'HATCHES (length fast) 'COM_MS com-ms 'NET_MS net-ms 'SAFETY_MS valid-ms 'MISMATCH mismatch))
 (if (> mismatch 0)
  (progn (bn:log (list 'HATCH_COM_EXAMPLE (lab:hatch-data (vlax-vla-object->ename (cadr originals)))))
         (bn:log (list 'HATCH_NET_EXAMPLE (lab:hatch-data (cadr fast))))))
 (foreach a originals (urb:safe-delete a)) (foreach b fast (entdel b)))
(defun lab:run (/ a b c d defs result)
 (foreach name '("BatchGuide" "CheckBatch" "HatchBatch")
  (command "_.NETLOAD" (strcat "C:/Users/juanbusper/Documents/URBANISMO/work/anden_three_options/" name ".dll")))
 (lab:engine nil) (setq a (lab:case "BASE_188" 450.0 nil))
 (lab:engine T) (setq b (lab:case "NET_188" 450.0 nil)) (bn:compare 'FLAT_188 a b)
 (setq defs (lab:defs))
 (bn:check 'FLAT_ALL_HATCHES_LAYERS (equal (lab:hatches (car defs)) (lab:hatches (cadr defs)) 1e-9))
 (lab:sort-test (cadr defs))
 (setq result (vl-catch-all-apply 'lab:hatch-test (list (car defs))))
 (if (vl-catch-all-error-p result) (progn (bn:check 'HATCH_BATCH_COMPLETED nil) (bn:log (list 'HATCH_ERROR (vl-catch-all-error-message result)))))
 (lab:obstacles)
 (lab:engine T) (setq c (lab:case "101_OBSTACLES_UNCACHED_188" 450.0 nil))
 (lab:engine T) (setq d (lab:case "101_OBSTACLES_CACHED_188" 450.0 T))
 (bn:compare 'CACHE_188 c d)
 (setq defs (lab:defs))
 (bn:check 'CACHE_ALL_HATCHES_LAYERS (equal (lab:hatches (nth 2 defs)) (lab:hatches (nth 3 defs)) 1e-9))
 (bn:check 'HOLE_REALLY_REDUCED_AREA (< (atof (cdr (assoc "AREA_M2" (cadr d)))) (atof (cdr (assoc "AREA_M2" (cadr b))))))
 (bn:log (list 'DONE 'FAILURES bn:fail)))
(setq lab:result (vl-catch-all-apply 'lab:run nil))
(if (vl-catch-all-error-p lab:result) (bn:log (list 'ERROR (vl-catch-all-error-message lab:result))))
(princ)
