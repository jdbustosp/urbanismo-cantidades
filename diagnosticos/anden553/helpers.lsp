(vl-load-com)
(if (/= (strcase (strcat (getvar "DWGPREFIX") (getvar "DWGNAME")))
 "C:\\USERS\\JUANBUSPER\\DOCUMENTS\\URBANISMO\\WORK\\ANDEN_THREE_OPTIONS\\FIXTURE.DWG") (exit))
(setq *urb-suppress-auto-migration* T bn:fail 0)
(defun bn:log (x / f) (setq f (open "C:/Users/juanbusper/Documents/URBANISMO/work/anden_three_options/result.txt" "a")) (write-line (vl-princ-to-string x) f) (close f))
(defun bn:check (label ok) (bn:log (list label (if ok 'OK 'FAIL))) (if (not ok) (setq bn:fail (1+ bn:fail))))
(defun nx:curve (r / dx dy th b d p0 p1 p2 q0 q1 q2)
  (setq dx 82800.0 dy 102400.0 th 0.209 d 1.75
        b (/ (sin (/ th 4.0)) (cos (/ th 4.0)))
        p0 (list dx (+ dy d))
        p1 (list (+ dx (* (- r d) (sin th))) (+ dy r (- (* (- r d) (cos th)))))
        p2 (list (+ dx (* 2 r (sin th))) (+ dy (* 2 r (- 1 (cos th))) d))
        q0 (list dx (- dy d))
        q1 (list (+ dx (* (+ r d) (sin th))) (+ dy r (- (* (+ r d) (cos th)))))
        q2 (list (+ dx (* 2 r (sin th))) (- (+ dy (* 2 r (- 1 (cos th)))) d)))
  (entmakex (list '(0 . "LWPOLYLINE") '(100 . "AcDbEntity") '(8 . "0")
    '(100 . "AcDbPolyline") '(90 . 6) '(70 . 1)
    (cons 10 p0) (cons 42 b) (cons 10 p1) (cons 42 (- b)) (cons 10 p2) '(42 . 0.0)
    (cons 10 q2) (cons 42 b) (cons 10 q1) (cons 42 (- b)) (cons 10 q0) '(42 . 0.0))))
(defun nx:less (a b)
  ;; Comparacion numerica, NO vl-princ-to-string: este ultimo redondea
  ;; coordenadas grandes y hace indistinguibles cuatro barras vecinas.
  (cond ((equal a b) nil)
        ((and (listp a) (listp b))
          (if (equal (car a) (car b)) (nx:less (cdr a) (cdr b)) (nx:less (car a) (car b))))
        (T (< a b))))
(defun nx:geometry (objects / result obj d def child numbered k)
  (foreach obj objects
    (setq d (entget (vlax-vla-object->ename obj)))
    (cond
      ((and (= (cdr (assoc 0 d)) "INSERT") (wcmatch (cdr (assoc 2 d)) "URB_GUIA_*"))
        (setq def (vla-Item (vla-get-Blocks (urb:doc)) (cdr (assoc 2 d))))
        (setq result (append (nx:geometry (urb:block-object-list def)) result)))
      ((and (wcmatch (cdr (assoc 8 d)) "*GUIA*")
            (member (cdr (assoc 0 d)) '("LINE" "LWPOLYLINE")))
        (setq result (cons (vl-remove-if-not
          '(lambda (p) (member (car p) '(0 8 62 90 70 10 11 42))) d) result)))))
  ;; No nth por cada indice: era O(n^2) dentro del VERIFICADOR de 800m.
  ;; Indice solo desempata duplicados exactos; se conserva el multiconjunto.
  (setq k 0)
  (foreach d result (setq numbered (cons (cons k d) numbered) k (1+ k)))
  (mapcar 'cdr (vl-sort numbered
    '(lambda (a b) (if (equal (cdr a) (cdr b)) (< (car a) (car b))
                     (nx:less (cdr a) (cdr b)))))))
(defun nx:loose (h / *urb-generation-parent* *urb-generation-start*)
  (length (urb:generated-objects h)))

(defun bn:case (label r / en h t0 build bms pms rms sms block def geom at nested item objs)
 (setq en (nx:curve r) h (cdr (assoc 5 (entget en))))
 (urb:set-anden-data en "Loseta" "1" "1" "Si" "Si" "20 x 20 cm" "No" "Seleccionar en dibujo" "Via creada")
 (setq *urb-current-tactile-side-choice* nil *urb-current-tactile-side-point* '(82800.0 102401.0))
 (bn:log (list label 'START))
 (setq t0 (getvar "MILLISECS") build (urb:build-anden-finish en "Loseta" "Si" "Si" "20 x 20 cm") bms (- (getvar "MILLISECS") t0))
 (bn:check (list label 'BUILD) build)
 (if (not build) (vl-exit-with-error "No BUILD"))
 (setq objs (urb:generated-objects h) t0 (getvar "MILLISECS") block (urb:package-anden en) pms (- (getvar "MILLISECS") t0))
 (if (not block) (vl-exit-with-error "No BLOCK"))
 (bn:check (list label 'ONE_BLOCK) (= (vla-get-ObjectName block) "AcDbBlockReference"))
 (bn:check (list label 'NO_LOOSE_FULL_SCAN) (= (nx:loose h) 0))
 (setq def (vla-Item (vla-get-Blocks (urb:doc)) (vla-get-Name block)) nested 0)
 (vlax-for item def (if (= (vla-get-ObjectName item) "AcDbBlockReference") (setq nested (1+ nested))))
 (setq geom (nx:geometry (urb:block-object-list def)) at (urb:block-attribute-values block))
 (setq t0 (getvar "MILLISECS")) (vla-Regen (urb:doc) 1) (setq rms (- (getvar "MILLISECS") t0))
 (setq t0 (getvar "MILLISECS")) (command "_.QSAVE") (setq sms (- (getvar "MILLISECS") t0))
 (bn:log (list label 'BUILD_MS bms 'PACK_MS pms 'REGEN_MS rms 'SAVE_MS sms 'TOTAL_MS (+ bms pms rms sms) 'NESTED nested 'GEOMETRIES (length geom) 'PACK_OBJECTS (length objs)))
 (bn:log (list label 'QTY at))
 (urb:safe-delete block)
 (list geom at nested))
(defun bn:compare (label a b / p)
 (bn:check (list label 'EXACT_GUIDE_DXF) (equal (car a) (car b) 1e-9))
 (bn:check (list label 'NO_NESTED) (= 0 (nth 2 b)))
 (foreach p (cadr a)
  (if (wcmatch (car p) "*M2,*ML,*UND,SOBREANCHO*")
   (bn:check (list label 'QTY (car p)) (equal (cdr p) (cdr (assoc (car p) (cadr b))))))))
