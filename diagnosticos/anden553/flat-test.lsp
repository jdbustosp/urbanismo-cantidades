(load "C:/Users/juanbusper/Documents/URBANISMO/work/anden_three_options/helpers.lsp")
(defun lab:record (key ms / p)
 (if (setq p (assoc key lab:stats)) (setq lab:stats (subst (list key (1+ (cadr p)) (+ ms (caddr p))) p lab:stats))
  (setq lab:stats (cons (list key 1 ms) lab:stats))))
(defun flat:load (fast)
 (load (strcat "C:/Users/juanbusper/Documents/URBANISMO/work/anden_three_options/" (if fast "flat-engine.lsp" "profile-engine.lsp")))
 (load "C:/Users/juanbusper/Documents/URBANISMO/work/anden_three_options/wrappers.lsp")
 (setq lab:stats nil))
(defun flat:run (/ a b c d item defs)
 (bn:log 'FLAT_RELEASE_BEGIN)
 (command "_.NETLOAD" "C:/Users/juanbusper/Streaming de Google Drive/Mi unidad/VARIOS/CLAUDE/proyectos/URBANISMO EXTERNO/bundle/net/UrbAndenFast2023_v553.dll")
 (command "_.NETLOAD" "C:/Users/juanbusper/Documents/URBANISMO/work/anden_three_options/CheckBatch.dll")
 (flat:load nil) (setq a (bn:case "RELEASE_BASE_188" 450.0)) (bn:log (list 'BASE_PHASES lab:stats))
 (flat:load T) (setq b (bn:case "RELEASE_FLAT_188" 450.0)) (bn:log (list 'FLAT_PHASES lab:stats))
 (bn:compare 'RELEASE188 a b)
 (flat:load nil) (setq c (bn:case "RELEASE_BASE_800" (/ 800.0 0.418)))
 (flat:load T) (setq d (bn:case "RELEASE_FLAT_800" (/ 800.0 0.418)))
 (bn:compare 'RELEASE800 c d)
 (vlax-for item (vla-get-Blocks (urb:doc))
  (if (wcmatch (vla-get-Name item) "URB_ANDEN_*") (setq defs (append defs (list item)))))
 (bn:check 'ORDER188 (= 0 (BNCHECKORDER (vla-get-Name (cadr defs)))))
 (bn:check 'ORDER800 (= 0 (BNCHECKORDER (vla-get-Name (nth 3 defs)))))
 (bn:log (list 'FLAT_RELEASE_DONE 'FAILURES bn:fail)))
(setq flat:r (vl-catch-all-apply 'flat:run nil))
(if (vl-catch-all-error-p flat:r) (bn:log (list 'FLAT_ERROR (vl-catch-all-error-message flat:r))))
(princ)
