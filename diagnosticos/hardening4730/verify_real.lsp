;; Ejecutar SOLO en validacion_real.dwg. Usa ActiveX nativo.
(if (/= (strcase (getvar "DWGNAME")) "VALIDACION_REAL.DWG")
  (progn (alert "Abra la fixture validacion_real.dwg antes de probar.") (exit)))
(setq vf (open (strcat (getenv "URB_TEST_LAB") "/real_result.txt") "w")
      passed 0 failed 0)
(defun vt:log (msg) (write-line msg vf) (princ))
(defun vt:check (name ok)
  (if ok (setq passed (1+ passed)) (setq failed (1+ failed)))
  (vt:log (strcat (if ok "OK " "FALLO ") name)))
(defun vt:fixture (/ en)
  (if (null (tblsearch "BLOCK" "URB_HARDEN_TEST"))
    (progn
      (entmake '((0 . "BLOCK") (2 . "URB_HARDEN_TEST") (70 . 2) (10 0 0 0)))
      (entmake '((0 . "ATTDEF") (10 0 0 0) (40 . 1.0) (1 . "A") (2 . "ID") (3 . "ID") (70 . 0)))
      (entmake '((0 . "ENDBLK")))))
  (vt:log (strcat "FIXTURE BLOCK " (vl-princ-to-string (tblsearch "BLOCK" "URB_HARDEN_TEST"))))
  (vt:log (strcat "FIXTURE INSERT " (vl-princ-to-string (entmake '((0 . "INSERT") (2 . "URB_HARDEN_TEST") (66 . 1) (10 0 0 0))))))
  (entmake '((0 . "ATTRIB") (10 0 0 0) (40 . 1.0) (1 . "A") (2 . "ID") (70 . 0)))
  (entmake '((0 . "SEQEND")))
  (setq en (entlast))
  (vt:log (strcat "FIXTURE EN " (vl-princ-to-string en)))
  (mp:store-cant-data en '(("ID" . "A") ("KEEP" . "123")))
  (urb:set-xdata-strings en "URB_TEST_OTHER" '("intacto"))
  en)
(setq caught (vl-catch-all-apply
  '(lambda (/ en result saved-store before attr-before audit old-rec new-rec generated dcl)
    (load (strcat (getenv "URB_TEST_LAB") "/baseline.lsp"))
    (setq en (vt:fixture))
    (mp:setatts en '(("ID" . "B")))
    (vt:check "BASELINE reproduce perdida de campo oculto"
      (null (assoc "KEEP" (mp:read-cant-data en))))
    (setq old-rec (urb:q-record "TEST" "" "X" "" "1" "1" "M3" -5 "1" "OK" "" ""))
    (vt:check "BASELINE reproduce cantidad negativa aprobada" (= (nth 9 old-rec) "OK"))
    (load (strcat (getenv "URB_TEST_LAB") "/current.lsp"))
    (vt:check "LOAD motor 4.73.0" (= *urb-version* "4.73.0"))
    (setq en (vt:fixture))
    (vt:check "Parche cambia un atributo" (= 1 (mp:setatts en '(("ID" . "B")))))
    (vt:check "Parche preserva campo oculto" (= "123" (cdr (assoc "KEEP" (mp:read-cant-data en)))))
    (vt:check "Parche actualiza visible" (= "B" (vla-get-TextString (vlax-ename->vla-object (entnext en)))))
    (vt:check "Preserva XDATA ajena" (equal '("intacto") (urb:get-xdata-strings en "URB_TEST_OTHER")))
    (setq before (entget en '("*")))
    (vt:check "Idempotente cuenta cero" (= 0 (mp:setatts en '(("ID" . "B")))))
    (vt:check "Idempotente no reescribe XDATA" (equal before (entget en '("*"))))
    (mp:setatts en '(("id" . "C") ("ID" . "D")))
    (vt:check "Claves normalizadas ultimo prevalece" (= "D" (cdr (assoc "ID" (mp:read-cant-data en)))))
    (mp:setatts en '(("ID" . "")))
    (vt:check "Permite vaciar explicitamente" (= "" (cdr (assoc "ID" (mp:read-cant-data en)))))
    (vt:check "Vaciado no pierde otros campos" (= "123" (cdr (assoc "KEEP" (mp:read-cant-data en)))))
    (setq before (entget en '("*")))
    (setq result (vl-catch-all-apply 'mp:setatts (list en '(("ID" "invalido")))))
    (vt:check "Rechaza lista mal formada" (vl-catch-all-error-p result))
    (vt:check "Datos invalidos no modifican entidad" (equal before (entget en '("*"))))
    (vt:check "Rechaza lista punteada" (not (mp:cant-patch-valid-p '(("A" . "B") . "C"))))
    (vt:check "Acepta parche vacio" (mp:cant-patch-valid-p nil))
    (setq saved-store mp:store-cant-data)
    (defun mp:store-cant-data (en vals) nil)
    (setq result (vl-catch-all-apply 'mp:setatts (list en '(("ID" . "FALLARA")))))
    (setq mp:store-cant-data saved-store)
    (vt:check "Fallo escritura aborta" (vl-catch-all-error-p result))
    (vt:check "Fallo escritura restaura atributo" (= "" (vla-get-TextString (vlax-ename->vla-object (entnext en)))))
    (vt:check "Fallo escritura conserva registro" (equal before (entget en '("*"))))
    (setq new-rec (urb:q-record "TEST" "" "X" "" "1" "1" "M3" -5 "1" "OK" "" ""))
    (vt:check "Cantidad negativa queda REVISAR" (= (nth 9 new-rec) "REVISAR"))
    (vt:check "Cantidad negativa no aprobada" (= 0 (urb:q-approved-record-count (list new-rec))))
    (vt:check "Diagnostico detecta cantidad negativa" (= 1 (length (urb:q-integrity-controls (list new-rec)))))
    (setq new-rec (urb:q-record "TEST" "" "X" "" "1" "1" "M3" 0 "1" "OK" "" ""))
    (vt:check "Cantidad cero valida conserva estado" (= (nth 9 new-rec) "OK"))
    (vt:check "Cama tuberia piso" (equal 0.1 (mp:pipe-bedding-thickness 0.2) 1e-9))
    (vt:check "Cama tuberia intermedio" (equal 0.125 (mp:pipe-bedding-thickness 0.5) 1e-9))
    (vt:check "Cama tuberia techo" (equal 0.15 (mp:pipe-bedding-thickness 1.0) 1e-9))
    (vt:check "Volumen constante" (equal 20.0 (mp:integrate-trench-volume '(2.0 2.0 2.0) 10.0 1.0) 1e-9))
    (vt:check "Volumen variable trapezoidal" (equal 25.0 (mp:integrate-trench-volume '(1.0 3.0 3.0) 10.0 1.0) 1e-9))
    (setq generated (urb:write-main-menu-dcl))
    (vt:check "Generacion DCL menus" (and generated (findfile generated)))
    (if generated (vl-file-copy generated (strcat (getenv "URB_TEST_LAB") "/menu.dcl")))
    (foreach item (urb:quality-selftests)
      (vt:check (strcat "Autoprueba integrada: " (car item)) (cadr item)))
    (setq saved-collect urb:q-collect-readonly saved-refresh urb:q-refresh-network-segments)
    (defun urb:q-refresh-network-segments () '(0 1))
    (setq vt-read-called nil)
    (defun urb:q-collect-readonly () (setq vt-read-called T) nil)
    (setq result (vl-catch-all-apply 'urb:q-collect-all nil))
    (vt:check "Exportacion aborta tras fallo de recalculo" (vl-catch-all-error-p result))
    (vt:check "No recoge datos obsoletos tras fallo" (not vt-read-called))
    (setq urb:q-collect-readonly saved-collect urb:q-refresh-network-segments saved-refresh)
    (setq before (entget en '("*")))
    (setq result (urb:q-collect-readonly))
    (vt:check "Colectores reales terminan" (= 2 (length result)))
    (vt:check "Consulta no modifica XDATA" (equal before (entget en '("*"))))
    (setq dcl (load_dialog generated))
    (vt:check "DCL real carga" (> dcl 0))
    (if (> dcl 0) (unload_dialog dcl))
    (vt:log "ActiveX nativo: sin adaptadores ni redefinicion de funciones VLA/DCL.")) nil))
(if (vl-catch-all-error-p caught)
  (progn (setq failed (1+ failed)) (vt:log (strcat "EXCEPCION " (vl-catch-all-error-message caught)))))
(vt:log (strcat "RESULTADO " (itoa passed) " OK / " (itoa failed) " FALLOS"))
(vt:log "DONE")
(close vf)
(princ)
