;; Pruebas de regresion en AutoCAD Core Console. El almacenamiento XDATA
;; y las entidades son reales. Adaptador ActiveX de prueba para la consola,
;; que no expone la aplicacion COM de AutoCAD completo.
(setq vf (open (strcat (getenv "URB_TEST_LAB") "/verify_result.txt") "w")
      passed 0 failed 0)
(defun vt:log (msg) (write-line msg vf) (princ))
(defun vt:check (name ok)
  (if ok (setq passed (1+ passed)) (setq failed (1+ failed)))
  (vt:log (strcat (if ok "OK " "FALLO ") name)))
(defun vt:bridge ()
  (defun vlax-ename->vla-object (en) en)
  (defun vla-get-HasAttributes (en) :vlax-true)
  (defun vlax-invoke (en method / attr result)
    (setq attr (entnext en))
    (while (and attr (= "ATTRIB" (cdr (assoc 0 (entget attr)))))
      (setq result (cons attr result) attr (entnext attr)))
    (reverse result))
  (defun vla-get-TagString (en) (cdr (assoc 2 (entget en))))
  (defun vla-get-TextString (en) (cdr (assoc 1 (entget en))))
  (defun vla-put-TextString (en value / data)
    (setq data (entget en))
    (entmod (subst (cons 1 value) (assoc 1 data) data)))
  (defun vla-Update (en) (entupd en)))
(defun vt:fixture (/ en)
  (if (null (tblsearch "BLOCK" "URB_HARDEN_TEST"))
    (progn
      (entmake '((0 . "BLOCK") (2 . "URB_HARDEN_TEST") (70 . 2) (10 0 0 0)))
      (entmake '((0 . "ATTDEF") (10 0 0 0) (40 . 1.0) (1 . "A") (2 . "ID") (3 . "ID") (70 . 0)))
      (entmake '((0 . "ENDBLK")))))
  (vt:log (strcat "FIXTURE BLOCK " (vl-princ-to-string (tblsearch "BLOCK" "URB_HARDEN_TEST"))))
  (vt:log (strcat "FIXTURE INSERT " (vl-princ-to-string (entmake '((0 . "INSERT") (2 . "URB_HARDEN_TEST") (66 . 1) (10 0 0 0))))))
  (entmake '((0 . "ATTRIB") (10 0 0 0) (40 . 1.0) (1 . "A") (2 . "ID") (70 . 0)))
  (entmake '((0 . "SEQEND")))
  (setq en (entlast))
  (vt:log (strcat "FIXTURE EN " (vl-princ-to-string en)))
  (mp:store-cant-data en '(("ID" . "A") ("KEEP" . "123")))
  (urb:set-xdata-strings en "URB_TEST_OTHER" '("intacto"))
  en)
(setq caught (vl-catch-all-apply
  '(lambda (/ en result saved-store before attr-before audit old-rec new-rec generated dcl)
    (load (strcat (getenv "URB_TEST_LAB") "/baseline.lsp"))
    (vt:bridge)
    (setq en (vt:fixture))
    (mp:setatts en '(("ID" . "B")))
    (vt:check "BASELINE reproduce perdida de campo oculto"
      (null (assoc "KEEP" (mp:read-cant-data en))))
    (setq old-rec (urb:q-record "TEST" "" "X" "" "1" "1" "M3" -5 "1" "OK" "" ""))
    (vt:check "BASELINE reproduce cantidad negativa aprobada" (= (nth 9 old-rec) "OK"))
    (load (strcat (getenv "URB_TEST_LAB") "/current.lsp"))
    (vt:bridge)
    (vt:check "LOAD motor 4.73.1" (= *urb-version* "4.73.1"))
    (setq en (vt:fixture))
    (vt:check "Parche cambia un atributo" (= 1 (mp:setatts en '(("ID" . "B")))))
    (vt:check "Parche preserva campo oculto" (= "123" (cdr (assoc "KEEP" (mp:read-cant-data en)))))
    (vt:check "Parche actualiza visible" (= "B" (vla-get-TextString (entnext en))))
    (vt:check "Preserva XDATA ajena" (equal '("intacto") (urb:get-xdata-strings en "URB_TEST_OTHER")))
    (setq before (entget en '("*")))
    (vt:check "Idempotente cuenta cero" (= 0 (mp:setatts en '(("ID" . "B")))))
    (vt:check "Idempotente no reescribe XDATA" (equal before (entget en '("*"))))
    (mp:setatts en '(("id" . "C") ("ID" . "D")))
    (vt:check "Claves normalizadas ultimo prevalece" (= "D" (cdr (assoc "ID" (mp:read-cant-data en)))))
    (mp:setatts en '(("ID" . "")))
    (vt:check "Permite vaciar explicitamente" (= "" (cdr (assoc "ID" (mp:read-cant-data en)))))
    (vt:check "Vaciado no pierde otros campos" (= "123" (cdr (assoc "KEEP" (mp:read-cant-data en)))))
    (setq before (entget en '("*")))
    (setq result (vl-catch-all-apply 'mp:setatts (list en '(("ID" "invalido")))))
    (vt:check "Rechaza lista mal formada" (vl-catch-all-error-p result))
    (vt:check "Datos invalidos no modifican entidad" (equal before (entget en '("*"))))
    (vt:check "Rechaza lista punteada" (not (mp:cant-patch-valid-p '(("A" . "B") . "C"))))
    (vt:check "Acepta parche vacio" (mp:cant-patch-valid-p nil))
    (setq saved-store mp:store-cant-data)
    (defun mp:store-cant-data (en vals) nil)
    (setq result (vl-catch-all-apply 'mp:setatts (list en '(("ID" . "FALLARA")))))
    (setq mp:store-cant-data saved-store)
    (vt:check "Fallo escritura aborta" (vl-catch-all-error-p result))
    (vt:check "Fallo escritura restaura atributo" (= "" (vla-get-TextString (entnext en))))
    (vt:check "Fallo escritura conserva registro" (equal before (entget en '("*"))))
    (setq new-rec (urb:q-record "TEST" "" "X" "" "1" "1" "M3" -5 "1" "OK" "" ""))
    (vt:check "Cantidad negativa queda REVISAR" (= (nth 9 new-rec) "REVISAR"))
    (vt:check "Cantidad negativa no aprobada" (= 0 (urb:q-approved-record-count (list new-rec))))
    (vt:check "Diagnostico detecta cantidad negativa" (= 1 (length (urb:q-integrity-controls (list new-rec)))))
    (setq new-rec (urb:q-record "TEST" "" "X" "" "1" "1" "M3" 0 "1" "OK" "" ""))
    (vt:check "Cantidad cero valida conserva estado" (= (nth 9 new-rec) "OK"))
    (vt:check "Cama tuberia piso" (equal 0.1 (mp:pipe-bedding-thickness 0.2) 1e-9))
    (vt:check "Cama tuberia intermedio" (equal 0.125 (mp:pipe-bedding-thickness 0.5) 1e-9))
    (vt:check "Cama tuberia techo" (equal 0.15 (mp:pipe-bedding-thickness 1.0) 1e-9))
    (vt:check "Volumen constante" (equal 20.0 (mp:integrate-trench-volume '(2.0 2.0 2.0) 10.0 1.0) 1e-9))
    (vt:check "Volumen variable trapezoidal" (equal 25.0 (mp:integrate-trench-volume '(1.0 3.0 3.0) 10.0 1.0) 1e-9))
    (setq generated (urb:write-main-menu-dcl))
    (vt:check "Generacion DCL menus" (and generated (findfile generated)))
    (if generated (vl-file-copy generated (strcat (getenv "URB_TEST_LAB") "/menu.dcl")))
    (foreach item (urb:quality-selftests)
      (vt:check (strcat "Autoprueba integrada: " (car item)) (cadr item)))
    (setq saved-collect urb:q-collect-readonly saved-refresh urb:q-refresh-network-segments)
    (defun urb:q-refresh-network-segments () '(0 1))
    (setq vt-read-called nil)
    (defun urb:q-collect-readonly () (setq vt-read-called T) nil)
    (setq result (vl-catch-all-apply 'urb:q-collect-all nil))
    (vt:check "Exportacion aborta tras fallo de recalculo" (vl-catch-all-error-p result))
    (vt:check "No recoge datos obsoletos tras fallo" (not vt-read-called))
    (setq urb:q-collect-readonly saved-collect urb:q-refresh-network-segments saved-refresh)
    ;; Recorrer el controlador de dialogo con adaptador DCL: detalle,
    ;; seleccion por handle, cierre y lista vacia; no prueba visual.
    (setq vt-dialog-steps '(2 3) vt-selected nil vt-alerts nil vt-files nil)
    (defun load_dialog (filename)
      (setq vt-files (cons filename vt-files)) 1)
    (defun new_dialog (name dcl) T)
    (defun unload_dialog (dcl) T)
    (defun set_tile (key value) T)
    (defun start_list (key) T)
    (defun add_list (value) T)
    (defun end_list () T)
    (defun mode_tile (key mode) T)
    (defun action_tile (key expr) T)
    (defun start_dialog (/ step)
      (setq step (car vt-dialog-steps) vt-dialog-steps (cdr vt-dialog-steps))
      (if step step 0))
    (defun alert (message) (setq vt-alerts (cons message vt-alerts)) nil)
    (defun sssetfirst (grips selection) (setq vt-selected selection))
    (urb:q-report-dialog "Prueba" (list (urb:q-control-row "ALTA" "TEST"
      (cdr (assoc 5 (entget en))) "Objeto" "Hallazgo" "Accion")))
    (vt:check "Dialogo abre detalle" (= 1 (length vt-alerts)))
    (vt:check "Dialogo selecciona entidad correcta" (and vt-selected (eq en (ssname vt-selected 0))))
    (vt:check "Dialogo elimina temporal" (not (findfile (car vt-files))))
    (setq vt-dialog-steps '(0))
    (setq result (vl-catch-all-apply 'urb:q-report-dialog (list "Vacio" nil)))
    (if (vl-catch-all-error-p result) (vt:log (vl-catch-all-error-message result)))
    (vt:check "Dialogo vacio cierra sin error" (not (vl-catch-all-error-p result)))
    (setq vt-alerts nil)
    (urb:version-info-command)
    (vt:check "Version muestra autopruebas" (vl-string-search "14/14" (car vt-alerts)))
    (vt:log "Las pruebas ActiveX usan un adaptador de prueba; no validan la interfaz de Civil 3D completo.")) nil))
(if (vl-catch-all-error-p caught)
  (progn (setq failed (1+ failed)) (vt:log (strcat "EXCEPCION " (vl-catch-all-error-message caught)))))
(vt:log (strcat "RESULTADO " (itoa passed) " OK / " (itoa failed) " FALLOS"))
(vt:log "DONE")
(close vf)
(princ)
