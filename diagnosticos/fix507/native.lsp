(vl-load-com)
(setq *urb-suppress-auto-migration* T)
(defun ac:log (v / f) (setq f (open "C:/Users/juanbusper/Documents/URBANISMO/work/fix507/native_result.txt" "a")) (write-line (vl-princ-to-string (list (getvar "MILLISECS") v)) f) (close f))
(defun ac:ok (name ok detail / fh sh)
  (if (wcmatch name "*_FAST_EQUALS_FULL")
    (progn
      (setq fh (mapcar 'vla-get-Handle fast) sh (mapcar 'vla-get-Handle slow))
      (setq ok (and (= (length fh) (length sh))
        (vl-every '(lambda (h) (member h sh)) fh)))))
  (if (wcmatch name "*_AREAS") (setq ok (< (abs (- actual full)) 0.000003)))
  (ac:log (list (if ok 'OK 'FAIL) name detail)))
(ac:log 'LOAD_START)
(load "C:/Users/juanbusper/Streaming de Google Drive/Mi unidad/VARIOS/CLAUDE/proyectos/URBANISMO EXTERNO/urbanismo_cantidades.lsp")
(ac:log 'LOADED)
(defun ac:bench (label en side expected / t0 buildms packms built blk h attrs def n item bb ib bad full fast slow savedparent total actual a g w region)
  (urb:set-anden-data en "Loseta" "1" "1" "Si" "Si" "20 x 20 cm" "No" "SUP_TN" "Via creada")
  (setq *urb-current-tactile-side-choice* nil *urb-current-tactile-side-point* side
    h (cdr (assoc 5 (entget en))) bb (urb:object-box-points (vlax-ename->vla-object en)) t0 (getvar "MILLISECS"))
  (ac:log (list label 'BUILD_START h))
  (setq built (urb:build-anden-finish en "Loseta" "Si" "Si" "20 x 20 cm") buildms (- (getvar "MILLISECS") t0))
  (ac:ok (strcat label "_BUILD") built buildms)
  (if built (progn
    (setq fast (urb:generated-objects h) savedparent *urb-generation-parent* *urb-generation-parent* nil)
    (setq slow (urb:generated-objects h) *urb-generation-parent* savedparent)
    (ac:ok (strcat label "_FAST_EQUALS_FULL")
      (equal (mapcar 'vla-get-Handle fast) (mapcar 'vla-get-Handle slow)) (list (length fast) (length slow)))
    (setq t0 (getvar "MILLISECS") blk (urb:package-anden en) packms (- (getvar "MILLISECS") t0))
    (ac:ok (strcat label "_BLOCK") (= (type blk) 'VLA-OBJECT) (list 'BUILD_MS buildms 'PACK_MS packms 'TOTAL_MS (+ buildms packms)))
    (setq attrs (urb:block-attribute-values blk) def (vla-Item (vla-get-Blocks (urb:doc)) (vla-get-Name blk)) n 0 bad 0)
    (vlax-for item def
      (setq n (1+ n))
      (if (member (vla-get-ObjectName item) '("AcDbRegion" "AcDbHatch"))
        (progn (setq ib (urb:object-box-points item))
          (if (or (< (caar ib) (- (caar bb) 0.01)) (< (cadar ib) (- (cadar bb) 0.01))
            (> (car (nth 2 ib)) (+ (car (nth 2 bb)) 0.01)) (> (cadr (nth 2 ib)) (+ (cadr (nth 2 bb)) 0.01))) (setq bad (1+ bad))))))
    (ac:ok (strcat label "_NO_OVERSIZED_FILL") (= bad 0) (list bad n))
    (setq actual (atof (mp:getval "AREA_SIN_SOBREANCHO_M2" attrs "0"))
      full (+ (atof (mp:getval "LOSETA_LISA_M2" attrs "0")) (atof (mp:getval "ADOQUIN_20X10_M2" attrs "0"))
        (atof (mp:getval "LOSETA_GUIA_M2" attrs "0")) (atof (mp:getval "LOSETA_TOPEROL_M2" attrs "0"))))
    (ac:ok (strcat label "_AREAS") (< (abs (- actual full)) 0.025) (list actual full))
    (ac:ok (strcat label "_TACTILE_LENGTH")
      (and (> (atof (mp:getval "LOSETA_GUIA_ML" attrs "0")) (* expected 0.97))
           (> (atof (mp:getval "LOSETA_TOPEROL_ML" attrs "0")) (* expected 0.97)))
      (list (mp:getval "LOSETA_GUIA_ML" attrs "0") (mp:getval "LOSETA_TOPEROL_ML" attrs "0")))
    (ac:ok (strcat label "_NO_LOOSE") (null (urb:generated-objects h)) 'FULL_SCAN)
    (ac:log (list label 'HANDLE (vla-get-Handle blk))))))
(setq ac:curve (vla-Copy (vlax-ename->vla-object (handent "B490B"))))
(vla-Move ac:curve (vlax-3d-point '(0.0 0.0 0.0)) (vlax-3d-point '(500.0 0.0 0.0)))
(setq ac:result (vl-catch-all-apply 'ac:bench (list "CURVE188" (vlax-vla-object->ename ac:curve) '(100953.0 100005.0) 188.0)))
(if (vl-catch-all-error-p ac:result) (ac:log (list 'ERROR (vl-catch-all-error-message ac:result))))
;; S de dos arcos verdaderos con curvaturas opuestas, 80 m, ancho3.5.
(defun ac:s (/ r th d b p0 p1 p2 q0 q1 q2 dx dy)
  (setq r 80.0 th 0.5 d 1.75 b (/ (sin (/ th 4.0)) (cos (/ th 4.0))) dx 101500.0 dy 99000.0
    p0 (list dx (+ dy d)) p1 (list (+ dx (* (- r d) (sin th))) (+ dy r (- (* (- r d) (cos th)))))
    p2 (list (+ dx (* 2 r (sin th))) (+ dy (* 2 r (- 1 (cos th))) d))
    q0 (list dx (- dy d)) q1 (list (+ dx (* (+ r d) (sin th))) (+ dy r (- (* (+ r d) (cos th)))))
    q2 (list (+ dx (* 2 r (sin th))) (- (+ dy (* 2 r (- 1 (cos th)))) d)))
  (entmakex (list '(0 . "LWPOLYLINE") '(100 . "AcDbEntity") '(8 . "0") '(100 . "AcDbPolyline") '(90 . 6) '(70 . 1)
    (cons 10 p0) (cons 42 b) (cons 10 p1) (cons 42 (- b)) (cons 10 p2) '(42 . 0.0)
    (cons 10 q2) (cons 42 b) (cons 10 q1) (cons 42 (- b)) (cons 10 q0) '(42 . 0.0))))
(setq ac:result (vl-catch-all-apply 'ac:bench (list "SCURVE80" (ac:s) '(101502.0 99001.5) 80.0)))
(if (vl-catch-all-error-p ac:result) (ac:log (list 'ERROR (vl-catch-all-error-message ac:result))))
(command "_.QSAVE")
(ac:log 'DONE)
(princ)
