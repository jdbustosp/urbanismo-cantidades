;; Volcado de geometria SIN explotar (2026-09-11, Claude): recorre la
;; definicion de cada bloque (tambien los dinamicos *U) aplicando la matriz
;; de la insercion. Solo entget/tblobjname: sirve en la consola sin graficos.
;; SOLO LECTURA (se corre sobre una copia que no se guarda).
;; Registros: L c x1 y1 x2 y2 | P c n pts | C c x y r | F c S|P n pts | T (translucido)

(defun w (s) (write-line s *o*))
(defun r2 (v) (rtos v 2 3))

(defun mx-mul (a b / bt)
  (setq bt (apply 'mapcar (cons 'list b)))
  (mapcar '(lambda (row) (mapcar '(lambda (col) (apply '+ (mapcar '* row col))) bt)) a))
(defun mx-id () '((1.0 0.0 0.0 0.0) (0.0 1.0 0.0 0.0) (0.0 0.0 1.0 0.0) (0.0 0.0 0.0 1.0)))
(defun mx-pt (m p / v)
  (setq v (list (car p) (cadr p) (if (caddr p) (caddr p) 0.0) 1.0))
  (list (apply '+ (mapcar '* (car m) v)) (apply '+ (mapcar '* (cadr m) v))))
(defun mx-scale (m) ; factor de escala lineal (para radios)
  (sqrt (abs (- (* (car (car m)) (cadr (cadr m))) (* (cadr (car m)) (car (cadr m)))))))
;; OCS con normal -Z: x -> -x
(defun ocs-m (ed / n)
  (setq n (cdr (assoc 210 ed)))
  (if (and n (< (caddr n) 0.0))
    '((-1.0 0.0 0.0 0.0) (0.0 1.0 0.0 0.0) (0.0 0.0 -1.0 0.0) (0.0 0.0 0.0 1.0))
    (mx-id)))

(defun ins-matrix (ed / p sx sy sz r b bn tb c s)
  (setq p (cdr (assoc 10 ed))
        sx (cond ((cdr (assoc 41 ed))) (1.0))
        sy (cond ((cdr (assoc 42 ed))) (1.0))
        sz (cond ((cdr (assoc 43 ed))) (1.0))
        r (cond ((cdr (assoc 50 ed))) (0.0))
        bn (cdr (assoc 2 ed))
        tb (entget (tblobjname "BLOCK" bn))
        b (cond ((cdr (assoc 10 tb))) ('(0.0 0.0 0.0)))
        c (cos r) s (sin r))
  (mx-mul (ocs-m ed)
    (mx-mul
      (list (list (* c sx) (* (- s) sy) 0.0 (car p))
            (list (* s sx) (* c sy) 0.0 (cadr p))
            (list 0.0 0.0 sz (caddr p))
            '(0.0 0.0 0.0 1.0))
      (list (list 1.0 0.0 0.0 (- (car b)))
            (list 0.0 1.0 0.0 (- (cadr b)))
            (list 0.0 0.0 1.0 (- (caddr b)))
            '(0.0 0.0 0.0 1.0)))))

(defun ent-color (ed parent / c lay)
  (setq c (cdr (assoc 62 ed)))
  (cond
    ((null c)
      (setq lay (tblsearch "LAYER" (cdr (assoc 8 ed))))
      (if (and (= (cdr (assoc 8 ed)) "0") parent) parent
        (if lay (abs (cdr (assoc 62 lay))) 7)))
    ((= c 0) (if parent parent 7))
    ((= c 256)
      (setq lay (tblsearch "LAYER" (cdr (assoc 8 ed))))
      (if lay (abs (cdr (assoc 62 lay))) 7))
    (T (abs c))))

(defun layer-off-p (ed / lay)
  (setq lay (tblsearch "LAYER" (cdr (assoc 8 ed))))
  (and lay (or (< (cdr (assoc 62 lay)) 0) (= 1 (logand 1 (cdr (assoc 70 lay)))))))

;; arco de bulge entre p1 y p2 (sin p1), en coordenadas locales
(defun bulge-pts (p1 p2 b / ang ch r mid cen a1 k res)
  (if (or (null b) (< (abs b) 1e-9) (< (distance p1 p2) 1e-9))
    (list p2)
    (progn
      (setq ang (* 4.0 (atan b)) ch (distance p1 p2)
            r (/ ch (* 2.0 (sin (/ ang 2.0))))
            mid (polar p1 (angle p1 p2) (/ ch 2.0))
            cen (polar mid (+ (angle p1 p2) (/ pi 2.0)) (* r (cos (/ ang 2.0))))
            a1 (angle cen p1) k 1 res nil)
      (repeat 12
        (setq res (cons (polar cen (+ a1 (* ang (/ k 12.0))) (abs r)) res) k (1+ k)))
      (reverse res))))

(defun arc-pts (cen r a0 a1 ccw / k res)
  ;; ccw nil/1 = antihorario
  (if (or (null ccw) (= ccw 1))
    (progn (if (< a1 a0) (setq a1 (+ a1 (* 2 pi)))))
    (progn (setq a0 (- a0) a1 (- a1)) (if (> a1 a0) (setq a1 (- a1 (* 2 pi))))))
  (setq k 0)
  (repeat 17
    (setq res (cons (polar cen (+ a0 (* (- a1 a0) (/ k 16.0))) r) res) k (1+ k)))
  (reverse res))

(defun vtx-ring (vs closed / out k n p q)
  ;; vs = ((pt bulge) ...) -> puntos muestreados
  (setq n (length vs) k 0 out nil)
  (repeat (if closed n (1- n))
    (setq p (nth k vs) q (nth (rem (1+ k) n) vs))
    (if (= k 0) (setq out (list (car p))))
    (setq out (append out (bulge-pts (car p) (car q) (cadr p))))
    (setq k (1+ k)))
  out)

(defun out-pts (tag c m pts / s)
  (setq s "")
  (foreach p pts (setq p (mx-pt m p) s (strcat s " " (r2 (car p)) " " (r2 (cadr p)))))
  (w (strcat tag " " (if (= (type c) 'STR) c (itoa c)) " " (itoa (length pts)) s)))

(defun hatch-loops (ed / rest lazos flag nv p b q ne tipo cen r a0 a1 ccw k vs)
  (setq rest (cdr (member (assoc 91 ed) ed)) lazos nil)
  (while (and rest (= (caar rest) 92))
    (setq flag (cdar rest) rest (cdr rest))
    (if (= 2 (logand flag 2))
      (progn
        (setq rest (member (assoc 93 rest) rest) nv (cdar rest) rest (cdr rest) vs nil)
        (repeat nv
          (setq p (cdar rest) rest (cdr rest) b 0.0)
          (if (= (caar rest) 42) (setq b (cdar rest) rest (cdr rest)))
          (setq vs (cons (list p b) vs)))
        (setq lazos (cons (vtx-ring (reverse vs) T) lazos)))
      (progn
        (setq rest (member (assoc 93 rest) rest) ne (cdar rest) rest (cdr rest) q nil)
        (repeat ne
          (setq tipo (cdar rest) rest (cdr rest))
          (cond
            ((= tipo 1)
              (setq q (append q (list (cdr (assoc 10 rest)) (cdr (assoc 11 rest)))))
              (setq rest (cdr (member (assoc 11 rest) rest))))
            ((= tipo 2)
              (setq cen (cdr (assoc 10 rest)) r (cdr (assoc 40 rest))
                    a0 (* pi (/ (cdr (assoc 50 rest)) 180.0))
                    a1 (* pi (/ (cdr (assoc 51 rest)) 180.0))
                    ccw (cdr (assoc 73 rest)))
              (setq q (append q (arc-pts cen r a0 a1 ccw)))
              (setq rest (cdr (member (assoc 73 rest) rest))))
            (T (setq rest nil))))
        (setq lazos (cons q lazos))))
    (if (and rest (= (caar rest) 97))
      (progn (setq k (cdar rest) rest (cdr rest))
             (repeat k (if (and rest (= (caar rest) 330)) (setq rest (cdr rest)))))))
  lazos)

(defun dump-ent (en m parent depth / ed tp c pts vs e2 cen r m2 tr tag)
  (setq ed (entget en) tp (cdr (assoc 0 ed)))
  (if (not (layer-off-p ed))
    (progn
      (setq c (ent-color ed parent))
      (cond
        ((= tp "LINE")
          (setq pts (list (mx-pt m (cdr (assoc 10 ed))) (mx-pt m (cdr (assoc 11 ed)))))
          (w (strcat "L " (itoa c) " " (r2 (car (car pts))) " " (r2 (cadr (car pts)))
               " " (r2 (car (cadr pts))) " " (r2 (cadr (cadr pts))))))
        ((= tp "LWPOLYLINE")
          (setq vs nil m2 (mx-mul m (ocs-m ed)))
          (setq e2 ed)
          (while (setq e2 (member (assoc 10 e2) e2))
            (setq vs (cons (list (cdar e2)
                                 (cdr (assoc 42 (cdr e2)))) vs)
                  e2 (cdr e2)))
          ;; el 42 que se toma es el primero despues del 10 (siempre existe)
          (setq vs (reverse vs))
          (if (> (length vs) 1)
            (out-pts "P" c m2 (vtx-ring vs (= 1 (logand 1 (cdr (assoc 70 ed))))))))
        ((= tp "CIRCLE")
          (setq m2 (mx-mul m (ocs-m ed)) cen (mx-pt m2 (cdr (assoc 10 ed)))
                r (* (cdr (assoc 40 ed)) (mx-scale m2)))
          (w (strcat "C " (itoa c) " " (r2 (car cen)) " " (r2 (cadr cen)) " " (rtos r 2 4))))
        ((= tp "ARC")
          (setq m2 (mx-mul m (ocs-m ed)))
          (out-pts "P" c m2 (arc-pts (cdr (assoc 10 ed)) (cdr (assoc 40 ed))
                               (cdr (assoc 50 ed)) (cdr (assoc 51 ed)) 1)))
        ((member tp '("SOLID" "TRACE"))
          (setq m2 (mx-mul m (ocs-m ed)))
          (out-pts "F" (strcat (itoa c) " S") m2
            (list (cdr (assoc 10 ed)) (cdr (assoc 11 ed))
                  (cdr (assoc 13 ed)) (cdr (assoc 12 ed)))))
        ((= tp "HATCH")
          (setq m2 (mx-mul m (ocs-m ed)))
          (setq tr (cdr (assoc 440 ed)))
          (setq tag (if (and tr (/= tr 0) (< (logand tr 255) 250)) "T" "F"))
          (foreach q (hatch-loops ed)
            (if (> (length q) 2)
              (w (strcat tag " " (itoa c) " "
                   (if (= 1 (cdr (assoc 70 ed))) "S" "P") " " (itoa (length q))
                   (apply 'strcat (mapcar '(lambda (p / pp) (setq pp (mx-pt m2 p))
                                             (strcat " " (r2 (car pp)) " " (r2 (cadr pp)))) q)))))))
        ((= tp "INSERT")
          (if (< depth 8)
            (dump-block (cdr (assoc 2 ed)) (mx-mul m (ins-matrix ed)) c (1+ depth))))))))

(defun dump-block (name m parent depth / en ed)
  (setq en (tblobjname "BLOCK" name))
  (if en (setq en (entnext en)))
  (while (and en (/= (cdr (assoc 0 (setq ed (entget en)))) "ENDBLK"))
    (vl-catch-all-apply 'dump-ent (list en m parent depth))
    (setq en (entnext en))))

(defun ref-pt (ed / p)
  (setq p (cdr (assoc 10 ed)))
  (if (and p (cdr (assoc 210 ed)) (< (caddr (cdr (assoc 210 ed))) 0.0))
    (list (- (car p)) (cadr p))
    p))

;; ventana: todo lo del modelo cuyo punto de referencia cae dentro (+ margen)
(defun ventanax (nombre x1 y1 x2 y2 margen / ss i ed p n)
  (w (strcat "W " nombre " " (r2 x1) " " (r2 y1) " " (r2 x2) " " (r2 y2)))
  (setq ss (ssget "_X" '((410 . "Model"))) i 0 n 0)
  (repeat (if ss (sslength ss) 0)
    (setq ed (entget (ssname ss i)) p (ref-pt ed))
    (if (and p (> (car p) (- x1 margen)) (< (car p) (+ x2 margen))
             (> (cadr p) (- y1 margen)) (< (cadr p) (+ y2 margen)))
      (progn (setq n (1+ n))
             (vl-catch-all-apply 'dump-ent (list (ssname ss i) (mx-id) nil 0))))
    (setq i (1+ i)))
  (w (strcat "E " nombre " " (itoa n))))
