(vl-load-com)
(if (/= (strcase (strcat (getvar "DWGPREFIX") (getvar "DWGNAME")))
        "C:\\USERS\\JUANBUSPER\\DOCUMENTS\\URBANISMO\\WORK\\ANDEN552\\FIXTURE.DWG")
  (progn (prompt "LAB: dibujo incorrecto, abortando") (exit)))
(setq *urb-suppress-auto-migration* T nx:fail 0 nx:blocks nil)
(defun nx:log (x / f)
  (setq f (open "C:/Users/juanbusper/Documents/URBANISMO/work/anden552/result.txt" "a"))
  (write-line (vl-princ-to-string x) f) (close f))
(defun nx:check (name ok)
  (nx:log (list name (if ok 'OK 'FAIL)))
  (if (not ok) (setq nx:fail (1+ nx:fail))))
(defun nx:curve (r / dx dy th b d p0 p1 p2 q0 q1 q2)
  (setq dx 82800.0 dy 102400.0 th 0.209 d 1.75
        b (/ (sin (/ th 4.0)) (cos (/ th 4.0)))
        p0 (list dx (+ dy d))
        p1 (list (+ dx (* (- r d) (sin th))) (+ dy r (- (* (- r d) (cos th)))))
        p2 (list (+ dx (* 2 r (sin th))) (+ dy (* 2 r (- 1 (cos th))) d))
        q0 (list dx (- dy d))
        q1 (list (+ dx (* (+ r d) (sin th))) (+ dy r (- (* (+ r d) (cos th)))))
        q2 (list (+ dx (* 2 r (sin th))) (- (+ dy (* 2 r (- 1 (cos th)))) d)))
  (entmakex (list '(0 . "LWPOLYLINE") '(100 . "AcDbEntity") '(8 . "0")
    '(100 . "AcDbPolyline") '(90 . 6) '(70 . 1)
    (cons 10 p0) (cons 42 b) (cons 10 p1) (cons 42 (- b)) (cons 10 p2) '(42 . 0.0)
    (cons 10 q2) (cons 42 b) (cons 10 q1) (cons 42 (- b)) (cons 10 q0) '(42 . 0.0))))
(defun nx:less (a b)
  ;; Comparacion numerica, NO vl-princ-to-string: este ultimo redondea
  ;; coordenadas grandes y hace indistinguibles cuatro barras vecinas.
  (cond ((equal a b) nil)
        ((and (listp a) (listp b))
          (if (equal (car a) (car b)) (nx:less (cdr a) (cdr b)) (nx:less (car a) (car b))))
        (T (< a b))))
(defun nx:geometry (objects / result obj d def child)
  (foreach obj objects
    (setq d (entget (vlax-vla-object->ename obj)))
    (cond
      ((and (= (cdr (assoc 0 d)) "INSERT") (wcmatch (cdr (assoc 2 d)) "URB_GUIA_*"))
        (setq def (vla-Item (vla-get-Blocks (urb:doc)) (cdr (assoc 2 d))))
        (setq result (append (nx:geometry (urb:block-object-list def)) result)))
      ((and (wcmatch (cdr (assoc 8 d)) "*GUIA*")
            (member (cdr (assoc 0 d)) '("LINE" "LWPOLYLINE")))
        (setq result (cons (vl-remove-if-not
          '(lambda (p) (member (car p) '(0 8 62 90 70 10 11 42))) d) result)))))
  (mapcar '(lambda (i) (nth i result)) (vl-sort-i result 'nx:less)))
(defun nx:loose (h / *urb-generation-parent* *urb-generation-start*)
  (length (urb:generated-objects h)))
(defun nx:fallback (engine / en region cut cutter marker h objects data)
  (load engine)
  (setq en (entmakex '((0 . "LWPOLYLINE") (100 . "AcDbEntity") (8 . "0")
    (100 . "AcDbPolyline") (90 . 4) (70 . 1)
    (10 20.0 20.0) (10 23.0 20.0) (10 23.0 20.4) (10 20.0 20.4))))
  (setq h (cdr (assoc 5 (entget en))) region (urb:add-region-from-object (vlax-ename->vla-object en)))
  (setq cut (entmakex '((0 . "LWPOLYLINE") (100 . "AcDbEntity") (8 . "0")
    (100 . "AcDbPolyline") (90 . 4) (70 . 1)
    (10 21.0 19.9) (10 21.7 19.9) (10 21.7 20.6) (10 21.0 20.6))))
  (setq cutter (urb:add-region-from-object (vlax-ename->vla-object cut)))
  (vla-Boolean region 2 cutter)
  (setq *urb-generation-parent* h *urb-generation-start* (entlast))
  (urb:fill-tactile-symbols region "GUIA" 0.0 "URB-ANDEN-LOSETA-GUIA-20X20" 0.0 h 0.20)
  (setq objects (urb:generated-objects h) data (nx:geometry objects))
  (foreach marker objects (urb:safe-delete marker))
  (urb:safe-delete region) (entdel en) (entdel cut)
  data)
(defun nx:case (label radius / en h t0 built bms pms rms blk at objs geom count)
  (setq en (nx:curve radius) h (cdr (assoc 5 (entget en))))
  (urb:set-anden-data en "Loseta" "1" "1" "Si" "Si" "20 x 20 cm" "No" "Seleccionar en dibujo" "Via creada")
  (setq *urb-current-tactile-side-choice* nil *urb-current-tactile-side-point* '(82800.0 102401.0))
  (setq t0 (getvar "MILLISECS") built (urb:build-anden-finish en "Loseta" "Si" "Si" "20 x 20 cm") bms (- (getvar "MILLISECS") t0))
  (nx:check (list label 'BUILD) built)
  (setq objs (urb:generated-objects h) count (length objs) geom (nx:geometry objs))
  (setq t0 (getvar "MILLISECS") blk (urb:package-anden en) pms (- (getvar "MILLISECS") t0))
  (nx:check (list label 'SINGLE_BLOCK) (and blk (= (vla-get-ObjectName blk) "AcDbBlockReference")))
  (nx:check (list label 'NO_LOOSE_FULL_SCAN) (= 0 (nx:loose h)))
  (setq at (urb:block-attribute-values blk))
  (nx:check (list label 'GEOMETRY_PACKED) (equal geom (nx:geometry (urb:block-object-list (vla-Item (vla-get-Blocks (urb:doc)) (vla-get-Name blk)))) 1e-9))
  (setq t0 (getvar "MILLISECS")) (vla-Regen (urb:doc) 1) (setq rms (- (getvar "MILLISECS") t0))
  (nx:log (list label 'BUILD_MS bms 'PACK_MS pms 'REGEN_MS rms 'TOTAL_MS (+ bms pms rms) 'TOP_LEVEL_PIECES count 'GUIDE_GEOMETRIES (length geom)))
  (nx:log (list label 'QUANTITIES at))
  (setq nx:blocks (cons blk nx:blocks))
  (list geom at (+ bms pms rms) count))
(defun nx:run (/ before after result a pair)
  (nx:log 'BEGIN)
  (load "C:/Users/juanbusper/Documents/URBANISMO/work/anden552/baseline.lsp")
  (setq before (nx:case "BEFORE551_S188" 450.0))
  (foreach a nx:blocks (urb:safe-delete a)) (setq nx:blocks nil)
  (load "C:/Users/juanbusper/Documents/URBANISMO/work/anden552/candidate.lsp")
  (setq after (nx:case "AFTER552_S188" 450.0))
  (nx:check 'GUIDE_EXACT_GEOMETRY_BEFORE_AFTER (equal (car before) (car after) 1e-9))
  (foreach pair (cadr before)
    (if (or (wcmatch (car pair) "*M2,*ML,*UND") (wcmatch (car pair) "SOBREANCHO*"))
      (nx:check (list 'QUANTITY_UNCHANGED (car pair)) (equal (cdr pair) (cdr (assoc (car pair) (cadr after)))))))
  (nx:check 'FEWER_TOP_LEVEL_ENTITIES (< (nth 3 after) (* 0.5 (nth 3 before))))
  (nx:log (list 'SPEEDUP (/ (float (nth 2 before)) (max 1 (nth 2 after)))))
  (nx:case "AFTER552_S376" 900.0)
  (setq before (nx:fallback "C:/Users/juanbusper/Documents/URBANISMO/work/anden552/baseline.lsp")
        after (nx:fallback "C:/Users/juanbusper/Documents/URBANISMO/work/anden552/candidate.lsp"))
  (nx:check 'FALLBACK_OBSTACLE_IDENTICAL (and (> (length before) 0) (equal before after 1e-9)))
  (command "_.QSAVE")
  (nx:log (list 'DONE 'FAILURES nx:fail)))
(setq nx:r (vl-catch-all-apply 'nx:run nil))
(if (vl-catch-all-error-p nx:r) (nx:log (list 'ERROR (vl-catch-all-error-message nx:r))))
(princ)
