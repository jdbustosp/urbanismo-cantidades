(vl-load-com)
(setq rd579:out "C:/Users/juanbusper/Documents/URBANISMO/work/anden579_20260921/road579.txt")
(defun rd579:log (s / f) (setq f (open rd579:out "a")) (write-line s f) (close f))

(defun rd579:run (/ road data axis boundary surface depth left right direction
                    span axis-start local raw footprint points area step result via-id)
  (setq road (handent "169202"))
  (if (null road) (progn (rd579:log "FAIL ROAD_NOT_FOUND") (exit)))
  (setq data (urb:get-xdata-strings road "URB_VIA")
        via-id (urb:safe-string (nth 22 data) "")
        axis (urb:road-axis-recover road data via-id)
        boundary (urb:explode-road-block-boundary road)
        surface (urb:select-surface-object (nth 6 data))
        depth (urb:road-profile-depth (nth 4 data))
        left (atof (nth 14 data)) right (atof (nth 15 data))
        direction (urb:safe-string (nth 12 data) "Inicio")
        span (atof (nth 18 data)) axis-start (atof (nth 21 data))
        local (urb:road-design-grade-records road data))
  (rd579:log (strcat "AXIS " (if axis "YES" "NO")
    " BOUNDARY " (if boundary "YES" "NO")
    " SURFACE " (if surface "YES" "NO")
    " DEPTH " (rtos depth 2 4)
    " LR " (rtos left 2 3) "/" (rtos right 2 3)
    " SPAN " (rtos span 2 3) " START " (rtos axis-start 2 3)
    " GRADE " (vl-princ-to-string local)))
  (if (and axis boundary surface local)
    (progn
      (setq raw
        (mapcar '(lambda (r)
          (list (if (urb:string-equal-p direction "Final")
                  (- (+ axis-start span) (car r))
                  (+ axis-start (car r)))
                (cadr r))) local))
      (setq footprint (urb:road-earthwork-footprint boundary axis left right direction))
      (rd579:log (strcat "FOOTPRINT " (if footprint "YES" "NO")
        " DIAG " (vl-princ-to-string *urb-last-road-footprint-diagnostic*)))
      (if footprint
        (progn
          (setq points (urb:anden-earthwork-raw-points footprint)
                area (vla-get-Area (vlax-ename->vla-object footprint)))
          (setq result (urb:road-plan-converged footprint surface axis raw
            axis-start span direction depth 10.0))
          (rd579:log (strcat "CONVERGED " (if result "YES" "NO")
            " RESULT " (vl-princ-to-string result)
            " DIAG " (vl-princ-to-string *urb-last-road-plan-diagnostic*)))
          (entdel footprint)))))
  (if boundary (entdel boundary))
  (rd579:log "FINISHED"))

(if (findfile rd579:out) (vl-file-delete rd579:out))
(setq rd579:r (vl-catch-all-apply 'rd579:run nil))
(if (vl-catch-all-error-p rd579:r)
  (rd579:log (strcat "ERROR " (vl-catch-all-error-message rd579:r))))
(princ)
