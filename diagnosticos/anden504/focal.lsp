(load "C:/Users/juanbusper/Documents/URBANISMO/work/anden504/baseline503.lsp")
(defun oldpip504 (pt pts / n i j inside xi yi xj yj x y)
 (setq x (car pt) y (cadr pt) n (length pts) inside nil j (1- n) i 0)
 (while (< i n)
  (setq xi (car (nth i pts)) yi (cadr (nth i pts)) xj (car (nth j pts)) yj (cadr (nth j pts)))
  (if (and (not (eq (> yi y) (> yj y))) (< x (+ xj (/ (* (- xi xj) (- y yj)) (- yi yj))))) (setq inside (not inside)))
  (setq j i i (1+ i))) inside)
(setq p504 nil k504 0)
(repeat 500 (setq p504 (cons (list (* 10.0 (cos (* k504 0.012566370614))) (* 10.0 (sin (* k504 0.012566370614)))) p504) k504 (1+ k504)))
(setq t504 (getvar "MILLISECS"))
(repeat 300 (oldpip504 '(1.0 1.0) p504))
(setq msold504 (- (getvar "MILLISECS") t504))
(load "C:/Users/juanbusper/Streaming de Google Drive/Mi unidad/VARIOS/CLAUDE/proyectos/URBANISMO EXTERNO/urbanismo_cantidades.lsp")
(setq f504 (open "C:/Users/juanbusper/Documents/URBANISMO/work/anden504/focal.txt" "w"))
(setq t504 (getvar "MILLISECS"))
(repeat 300 (urb:point-in-poly-p '(1.0 1.0) p504))
(write-line (strcat "PIP old_ms=" (itoa msold504) " new_ms=" (itoa (- (getvar "MILLISECS") t504))) f504)
(setq fail504 0 k504 0)
(repeat 200 (setq q504 (list (- (* 0.15 k504) 15.0) (* 3.0 (sin k504)))) (if (not (equal (oldpip504 q504 p504) (urb:point-in-poly-p q504 p504))) (setq fail504 (1+ fail504))) (setq k504 (1+ k504)))
(write-line (strcat "PIP equivalence failures=" (itoa fail504)) f504)
(write-line (strcat "S_CURVE " (vl-princ-to-string (urb:anden-needs-segmented-p '((0 0) (20 0) (30 10) (40 0) (60 0))))) f504)
(foreach rad504 '(1.0 10.0 50.0 260.714)
 (foreach sweep504 '(0.00001 0.5 1.57079632679 4.0)
  (foreach dir504 '(0 1)
   (if (not (urb:hatch-arc-lines (list '(72 . 2) '(10 0.0 0.0) (cons 40 rad504) '(50 . 0.0) (cons 51 sweep504) (cons 73 dir504)))) (setq fail504 (1+ fail504))))))
(write-line (strcat "32_ARC_CASES combined_failures=" (itoa fail504)) f504)
(close f504)
(princ)
