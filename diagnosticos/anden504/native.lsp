(vl-load-com)
(load "C:/Users/juanbusper/Documents/URBANISMO/work/_lib/verify_lib.lsp")
(vlib:open "C:/Users/juanbusper/Documents/URBANISMO/work/anden504/native.txt")
(setq test504 (vl-catch-all-apply '(lambda (/ en res t0 block objs area top gui item data bad)
 (load "C:/Users/juanbusper/Streaming de Google Drive/Mi unidad/VARIOS/CLAUDE/proyectos/URBANISMO EXTERNO/urbanismo_cantidades.lsp")
 (setvar "FILEDIA" 0) (setvar "CMDECHO" 0)
 (foreach kind '(SHORT_CURVE LONG_188)
  (setq en (if (= kind 'SHORT_CURVE) (vlib:curved-corridor) (vlib:rect 300.0 0.0 488.0 3.5)))
  (urb:set-anden-data en "Loseta" "1" "1" "Si" "Si" "20 x 20 cm" "No" "SUP_TN" "Via creada")
  (setq *urb-current-tactile-side-point* (if (= kind 'SHORT_CURVE) '(5.0 0.0) '(305.0 0.0)))
  (setq t0 (getvar "MILLISECS") res (vl-catch-all-apply 'urb:build-anden-finish (list en "Loseta" "Si" "Si" "20 x 20 cm")))
  (vlib:check (strcat (vl-princ-to-string kind) " BUILD") (and res (not (vl-catch-all-error-p res))) (if (vl-catch-all-error-p res) (vl-catch-all-error-message res) res))
  (setq objs (urb:generated-objects (cdr (assoc 5 (entget en)))) top 0.0 gui 0.0 bad 0)
  (foreach item objs
   (setq data (entget (vlax-vla-object->ename item)))
   (if (and (= (cdr (assoc 0 data)) "HATCH") (urb:hatch-render-data data)) (setq bad (1+ bad)))
   (if (and (= (vla-get-ObjectName item) "AcDbRegion") (= (urb:generated-role item) "FILL"))
    (cond ((wcmatch (vla-get-Layer item) "*TOPEROL*") (setq top (+ top (vla-get-Area item))))
          ((wcmatch (vla-get-Layer item) "*GUIA*") (setq gui (+ gui (vla-get-Area item)))))))
  (vlib:check (strcat (vl-princ-to-string kind) " NO_ARC_HATCH") (= bad 0) bad)
  (vlib:log (list kind 'tactileAreas top gui 'buildMs (- (getvar "MILLISECS") t0)))
  (if (= kind 'LONG_188) (vlib:check "188m coverage" (and (> top 37.5) (< top 37.7) (> gui 37.5) (< gui 37.7)) (list top gui)))
  (setq block (vl-catch-all-apply 'urb:package-anden (list en)))
  (vlib:check (strcat (vl-princ-to-string kind) " BLOCK") (and (not (vl-catch-all-error-p block)) (urb:as-ename block)) (if (vl-catch-all-error-p block) (vl-catch-all-error-message block) (type block)))
  (vlib:log (list kind 'totalMs (- (getvar "MILLISECS") t0)))
 )
 (command "_.ZOOM" "_W" '(-4 -4) '(28 28))
 (command "_.REGENALL")
 (command "_.PNGOUT" "C:/Users/juanbusper/Documents/URBANISMO/work/anden504/short_curve.png" "")
 )))
(if (vl-catch-all-error-p test504) (vlib:check "EXCEPTION" nil (vl-catch-all-error-message test504)))
(vlib:close)
(princ)
