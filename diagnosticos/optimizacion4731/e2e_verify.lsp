(setq f (open "C:/Users/jdbus/Documents/URBANISMO/work/maipore4740/e2e.txt" "w"))
(write-line "START" f)(close f)
(defun test-log (s / f) (setq f (open "C:/Users/jdbus/Documents/URBANISMO/work/maipore4740/e2e.txt" "a")) (write-line s f)(close f))
(setq r (vl-catch-all-apply '(lambda ()
 (load "C:/Users/jdbus/Documents/URBANISMO/work/maipore4740/motor.lsp")
 (setq app (vlax-create-object "Excel.Application"))
 (vlax-put-property app 'Visible :vlax-false)
 (vlax-put-property app 'DisplayAlerts :vlax-false)
 (vlax-put-property app 'AutomationSecurity 3)
 (setq wb (vlax-invoke-method (vlax-get-property app 'Workbooks) 'Open "C:/Users/jdbus/Documents/URBANISMO/work/maipore4740/presupuesto.xlsx" 0 :vlax-false))
 (test-log "EXCEL OPEN")
 (setq cell (vlax-get-property (vlax-get-property (vlax-get-property wb 'Worksheets) 'Item "MEMORIAS") 'Range "J2"))
 (test-log (strcat "BEFORE " (vl-prin1-to-string (vlax-get-property cell 'Value2))))
 (vlax-put-property cell 'Value2 123456.789)
 (test-log "INJECTED 123456.789")
 (setq *urb-ppto-sin-dialogo* T)
 (urb:ppto-run wb)
 (test-log "EXPORT RETURNED")
 (test-log (strcat "AFTER " (vl-prin1-to-string (vlax-get-property cell 'Value2))))
 (test-log (strcat "STAGE " (vl-prin1-to-string *urb-ppto-stage*)))
 (test-log (strcat "FINAL ROWS " (itoa (length *urb-ppto-final-prev*))))
 (vlax-invoke-method wb 'Close :vlax-false)
 (vlax-invoke-method app 'Quit)
 (test-log "DONE")) nil))
(if (vl-catch-all-error-p r) (test-log (strcat "ERROR " (vl-catch-all-error-message r))))
(princ)
