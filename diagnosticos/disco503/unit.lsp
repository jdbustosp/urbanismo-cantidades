(setq uf503 (open "C:/Users/juanbusper/Documents/URBANISMO/work/disco503/unit.txt" "w"))
(setq ur503 (vl-catch-all-apply '(lambda (/ e flat endp oldall failcount pair)
  (load "C:/Users/juanbusper/Streaming de Google Drive/Mi unidad/VARIOS/CLAUDE/proyectos/URBANISMO EXTERNO/urbanismo_cantidades.lsp")
  (write-line (strcat "LOAD " *urb-version*) uf503)
  (foreach e '(((72 . 2) (10 82659.8 95448.7 0.0) (40 . 260.714) (50 . 0.436817) (51 . 0.436818) (73 . 0))
               ((72 . 2) (10 0.0 0.0 0.0) (40 . 267.5) (50 . 6.28) (51 . 0.003) (73 . 1)))
    (setq flat (urb:hatch-arc-lines e))
    (if (not flat) (vl-exit-with-error "SMALL_ARC_MISSED"))
    (setq endp (polar (cdr (assoc 10 e)) (* (if (= 0 (cdr (assoc 73 e))) -1.0 1.0) (cdr (assoc 51 e))) (cdr (assoc 40 e))))
    (if (> (distance endp (cdr (last flat))) 1e-7) (vl-exit-with-error "ARC_ENDPOINT")))
  (write-line "CW_CCW_WRAP_ENDPOINTS OK" uf503)
  (if (urb:hatch-arc-lines '((72 . 2) (10 0.0 0.0 0.0) (40 . 260.714) (50 . 0.0) (51 . 6.283185307179586) (73 . 1))) (vl-exit-with-error "GENUINE_CIRCLE_CHANGED"))
  (write-line "GENUINE_CIRCLE_UNCHANGED OK" uf503)
  (setq oldall (urb:quality-selftests) failcount 0)
  (foreach pair oldall (if (not (cadr pair)) (progn (setq failcount (1+ failcount)) (write-line (vl-princ-to-string pair) uf503))))
  (write-line (strcat "REGRESSION " (itoa (length oldall)) " cases " (itoa failcount) " failures") uf503)
  (write-line "DONE" uf503))))
(if (vl-catch-all-error-p ur503) (write-line (strcat "ERROR " (vl-catch-all-error-message ur503)) uf503))
(close uf503) (princ)
