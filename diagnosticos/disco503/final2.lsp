(vl-load-com)
(setq lab503 "C:/Users/juanbusper/Documents/URBANISMO/work/disco503/")
(defun log503 (s / f) (setq f (open (strcat lab503 "final2.txt") "a")) (write-line s f) (close f))
(setq er503 (vl-catch-all-apply '(lambda (/ ss i en saved t0 n eligible obj hatch data)
  (setvar "FILEDIA" 0) (setvar "CMDECHO" 0)
  (setq ss (ssget "_X" '((0 . "REGION,LWPOLYLINE"))) i 0)
  (repeat (sslength ss) (setq en (ssname ss i) i (1+ i) saved (cons (cons en (entget en '("*"))) saved)))
  (setq t0 (getvar "MILLISECS"))
  (load "C:/Users/juanbusper/Streaming de Google Drive/Mi unidad/VARIOS/CLAUDE/proyectos/URBANISMO EXTERNO/urbanismo_cantidades.lsp")
  (log503 (strcat "LOAD " *urb-version* " ANDEN " (vl-princ-to-string (type c:ANDEN)) " loadAndRepairMs=" (itoa (- (getvar "MILLISECS") t0))))
  (foreach pair saved (if (not (equal (cdr pair) (entget (car pair) '("*")))) (vl-exit-with-error "SOURCE_CHANGED")))
  (log503 (strcat "SOURCES_IDENTICAL " (itoa (length saved))))
  (setq ss (ssget "_X" '((0 . "HATCH"))) i 0 eligible 0)
  (repeat (sslength ss) (setq en (ssname ss i) i (1+ i)) (if (urb:hatch-render-data (entget en)) (setq eligible (1+ eligible))))
  (log503 (strcat "UNREPAIRED " (itoa eligible)))
  (if (> eligible 0) (vl-exit-with-error "HATCH_REPAIR_INCOMPLETE"))
  (if (/= 0 (urb:repair-anden-hatches)) (vl-exit-with-error "NOT_IDEMPOTENT"))
  (log503 "IDEMPOTENT OK")
  (setq n 0)
  (foreach pair saved
    (if (= "REGION" (cdr (assoc 0 (cdr pair))))
      (progn
        (setq obj (vlax-ename->vla-object (car pair)) hatch (urb:add-solid-hatch obj "URB-ANDEN-LOSETA-GRIS-20X20" 8) n (1+ n))
        (if (urb:hatch-render-data (entget (vlax-vla-object->ename hatch))) (vl-exit-with-error "NEW_UNSAFE")))))
  (log503 (strcat "NEW_HATCHES " (itoa n)))
  (command "_.ZOOM" "_W" '(82300 95000) '(83100 95750))
  (command "_.REGENALL")
  (command "_.PNGOUT" (strcat lab503 "final2_verified.png") "")
  (command "_.QSAVE")
  (log503 "DONE"))))
(if (vl-catch-all-error-p er503) (log503 (strcat "ERROR " (vl-catch-all-error-message er503))))
(princ)
