(setq p17:pass 0 p17:fail 0)
(defun p17:log (s / f) (setq f (open "C:/Users/juanbusper/Documents/URBANISMO/work/anden5717/verify.txt" "a")) (write-line s f) (close f))
(defun p17:check (ok s) (if ok (setq p17:pass (1+ p17:pass)) (setq p17:fail (1+ p17:fail))) (p17:log (strcat (if ok "PASS " "FAIL ") s)))
(defun p17:moments (samples / a x y s)
  (setq a 0.0 x 0.0 y 0.0)
  (foreach s samples (setq a (+ a (cadr s)) x (+ x (* (caar s) (cadr s))) y (+ y (* (cadar s) (cadr s)))))
  (list a x y))
(defun p17:run (/ pts old new en item ed ref raw start samples moments exact blocks itemCount tops toparea atts role)
  (p17:check (= *urb-version* "5.7.17") "version")
  (foreach pts '(((0.0 0.0) (10.0 0.0) (10.0 4.0) (0.0 4.0))
                ((0.0 0.0) (12.0 2.0) (10.0 5.0) (2.0 8.0) (3.0 3.0))
                ((0.0 0.0) (5.0 0.0) (5.0 0.001) (2.0 0.001) (2.0 5.0) (0.0 5.0))
                ((83000.0 95000.0) (83020.0 95007.0) (83019.0 95010.0) (83008.0 95005.0) (83001.0 95006.0)))
    (foreach pts (list pts (reverse pts))
      (setq old (p17:baseline-scanline pts 0.5) new (urb:earthwork-scanline-samples pts 0.5))
      (p17:check (= (length old) (length new)) "same sample count")
      (p17:check (equal (p17:moments old) (p17:moments new) 1e-5) "same area and first moments")
      (p17:check (equal (car (p17:moments new)) (abs (urb:polygon-signed-area pts)) 1e-4) "independent polygon area")))
  ;; Exact geometry from local DWG via DXF, without COM/TIN or rounded text export.
  (setq en (handent "1B3D3F"))
  (p17:check en "actual sidewalk found in copy")
  (setq item (tblobjname "BLOCK" (cdr (assoc 2 (entget en)))) tops 0 toparea 0.0)
  (while (and (setq item (entnext item)) (/= (cdr (assoc 0 (setq ed (entget item)))) "ENDBLK"))
    (setq role (urb:get-xdata-strings item "URB_ANDEN_GEN"))
    (if (and (= (cdr (assoc 0 ed)) "LWPOLYLINE") (member "EARTHWORK_BOUNDARY" role)) (setq raw item))
    (if (and (= (cdr (assoc 0 ed)) "HATCH") (wcmatch (cdr (assoc 8 ed)) "*TOPEROL*")) (setq tops (1+ tops))))
  (p17:log (strcat "TOPEROL HATCHES IN SAVED BLOCK " (itoa tops)))
  (p17:check raw "earthwork boundary preserved")
  (setq pts (urb:anden-earthwork-raw-points raw))
  (p17:log (strcat "EXACT VERTICES " (itoa (length pts))))
  (setq start (getvar "MILLISECS") samples (urb:earthwork-area-samples pts))
  (p17:log (strcat "MESH MS " (itoa (- (getvar "MILLISECS") start)) " SAMPLES " (itoa (length samples))))
  (setq moments (p17:moments samples) exact (abs (urb:polygon-signed-area pts)))
  (p17:log (strcat "AREA " (rtos (car moments) 2 8) " POLYGON " (rtos exact 2 8)))
  (p17:check (and samples (equal (car moments) exact (max 0.001 (* exact 0.0001)))) "actual footprint area")
  (p17:check (equal (urb:cota-at-axis-distance 10.0 '((0.0 100.0) (20.0 104.0))) 102.0 1e-9) "grade interpolation unchanged")
  (p17:log (strcat "SUMMARY pass=" (itoa p17:pass) " fail=" (itoa p17:fail)))
  (if (= p17:fail 0) (p17:log "FINISHED")))
(p17:log "STARTED")
(setq p17:r (vl-catch-all-apply 'p17:run nil))
(if (vl-catch-all-error-p p17:r) (p17:log (strcat "ERROR " (vl-catch-all-error-message p17:r))))
(princ)
