(defun p17:log (s / f) (setq f (open "C:/Users/juanbusper/Documents/URBANISMO/work/anden5717/apply-baseline.txt" "a")) (write-line s f) (close f))
(p17:log "STARTED")
(foreach p17:n '(1000 10000 40000 100000)
  (setq p17:values nil)
  (repeat p17:n (setq p17:values (cons 0.25 p17:values)))
  (p17:log (strcat "BEFORE APPLY " (itoa p17:n)))
  (setq p17:r (vl-catch-all-apply '(lambda () (apply '+ p17:values))))
  (p17:log (strcat "AFTER APPLY " (vl-princ-to-string p17:r))))
(p17:log "FINISHED")
