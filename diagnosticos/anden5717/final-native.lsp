(defun p17:log (s / f) (setq f (open "C:/Users/juanbusper/Documents/URBANISMO/work/anden5717/final-native.txt" "a")) (write-line s f) (close f))
(defun p17:final (/ en obj pts area r start)
  (if (/= (strcase (vl-string-translate "\\" "/" (strcat (getvar "DWGPREFIX") (getvar "DWGNAME"))))
    "C:/USERS/JUANBUSPER/DOCUMENTS/URBANISMO/WORK/ANDEN5717/FIXTURE.DWG") (exit))
  (setq en (handent "1B3D3F") obj (urb:as-vla-object en)
        pts (urb:anden-block-points en) area (urb:anden-earthwork-area obj))
  (p17:log (strcat "START TARGET " (cdr (assoc 5 (entget en))) " VERSION " *urb-version*))
  (setq start (getvar "MILLISECS")
        r (vl-catch-all-apply 'urb:run-anden-earthworks (list obj pts area "SUP_TN" "Via creada")))
  (p17:log (strcat "RESULT " (vl-princ-to-string r) " STAGE " *urb-anden-earthwork-stage* " MS " (itoa (- (getvar "MILLISECS") start))))
  (p17:log (strcat "MOV " (vl-princ-to-string (urb:get-xdata-strings en "URB_ANDEN_MOV"))))
  (if (and r (not (vl-catch-all-error-p r))) (p17:log "FINISHED")))
(p17:log "LOADED")
(setq p17:r (vl-catch-all-apply 'p17:final nil))
(if (vl-catch-all-error-p p17:r) (p17:log (vl-catch-all-error-message p17:r)))
