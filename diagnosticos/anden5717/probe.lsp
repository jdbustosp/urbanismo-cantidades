(vl-load-com)
(setq p17:dir "C:/Users/juanbusper/Documents/URBANISMO/work/anden5717/")
(defun p17:log (s / f) (setq f (open (strcat p17:dir "probe.txt") "a")) (write-line s f) (close f))
(defun p17:run (/ ss i en obj pts area target samples total ref surface r f)
  (if (/= (strcase (vl-string-translate "\\" "/" (strcat (getvar "DWGPREFIX") (getvar "DWGNAME"))))
    (strcase (strcat p17:dir "fixture.dwg"))) (exit))
  (setq ss (ssget "_X" '((0 . "INSERT") (-3 ("URB_ANDEN_BLOCK")))) i 0)
  (repeat (if ss (sslength ss) 0)
    (setq en (ssname ss i) i (1+ i) obj (urb:as-vla-object en)
      area (atof (cdr (assoc "AREA_M2" (urb:block-attribute-values obj)))) )
    (if (or (< (abs (- area 454.84)) 1.0) (< (abs (- area 425.56)) 1.0)) (setq target en)))
  (if (null target) (progn (p17:log "TARGET NOT FOUND") (exit)))
  (p17:log (strcat "TARGET " (cdr (assoc 5 (entget target)))))
  (setq pts (urb:anden-earthwork-points target))
  (setq f (open (strcat p17:dir "points.lsp") "w")) (prin1 (list 'setq 'p17:points (list 'quote pts)) f) (close f)
  (p17:log (strcat "POINTS " (itoa (length pts))))
  (setq *urb-anden-grade-points* pts)
  (p17:log "BEFORE REFERENCE")
  (setq ref (urb:select-anden-grade-reference "Via creada"))
  (p17:log (strcat "REFERENCE " (vl-princ-to-string ref)))
  (p17:log "BEFORE SAMPLES")
  (setq samples (urb:earthwork-area-samples pts))
  (p17:log (strcat "SAMPLES " (itoa (length samples))))
  (setq total 0.0) (foreach s samples (setq total (+ total (cadr s))))
  (p17:log (strcat "ITERATIVE AREA " (rtos total 2 8)))
  (p17:log "BEFORE OLD APPLY")
  (setq r (vl-catch-all-apply '(lambda () (apply '+ (mapcar 'cadr samples)))))
  (p17:log (strcat "OLD APPLY " (vl-princ-to-string r)))
  (p17:log "FINISHED"))
(p17:log "STARTED")
(setq p17:r (vl-catch-all-apply 'p17:run nil))
(if (vl-catch-all-error-p p17:r) (p17:log (vl-catch-all-error-message p17:r)))
(princ)
