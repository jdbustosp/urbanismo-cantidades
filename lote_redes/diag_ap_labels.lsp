(load "C:/Users/jdbus/Documents/URBANISMO/work/lote_redes/lote_redes.lsp")
(setq pf (open "C:/Users/jdbus/Documents/URBANISMO/work/lote_redes/diag_ap_labels.txt" "w"))
(defun dg (m) (write-line m pf))
;; 1) el poste huerfano en PPTO-EQUIPOS-ELECTRICOS
(setq en (handent "5C3C0"))
(if en
  (dg (strcat "Poste huerfano 5C3C0: " (vl-princ-to-string (mp:att-alist en))))
  (dg "Poste huerfano 5C3C0: no encontrado"))
;; 2) histograma de |LONGITUD-attr - distv-geometrico| en TODOS los tramos BTAP
(setq ss (ssget "_X" '((0 . "INSERT") (2 . "MP_TRAMO_BTAP_*"))))
(setq n (if ss (sslength ss) 0) i 0 hist nil grandes 0)
(while (< i n)
  (setq e (ssname ss i) ed (entget e))
  (setq bn (cdr (assoc 2 ed)))
  (setq distv (atof (vl-string-translate "_" "."
    (substr bn (+ 6 (vl-string-search "BTAP_" bn))))))
  (setq sub (entnext e) lngv 0.0)
  (while (and sub (/= (cdr (assoc 0 (entget sub))) "SEQEND"))
    (setq sd (entget sub))
    (if (and (= (cdr (assoc 0 sd)) "ATTRIB") (= (cdr (assoc 2 sd)) "LONGITUD"))
      (setq lngv (atof (cdr (assoc 1 sd)))))
    (setq sub (entnext sub)))
  (setq dif (- lngv distv))
  (if (> (abs dif) (max 2.0 (* 0.4 distv)))
    (setq grandes (1+ grandes)))
  (setq k (rtos (* 1.0 (fix (+ 0.5 (/ dif 1.0)))) 2 0))
  (setq par (assoc k hist))
  (if par (setq hist (subst (cons k (1+ (cdr par))) par hist))
    (setq hist (cons (cons k 1) hist)))
  (setq i (1+ i)))
(dg (strcat "RESUMEN: " (itoa n) " tramos BTAP | discrepancia GRANDE (>max(2, 40%%)): "
  (itoa grandes)))
(dg "HISTOGRAMA dif (LONGITUD-attr - distv-geom), paso 1m:")
(foreach par (vl-sort hist '(lambda (a b) (< (atof (car a)) (atof (car b)))))
  (dg (strcat "  " (car par) " m -> " (itoa (cdr par)) " tramos")))
(dg "DIAGAP-OK")
(close pf)
(princ)
