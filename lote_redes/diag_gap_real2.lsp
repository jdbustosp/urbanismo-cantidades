(setq pf (open "C:/Users/jdbus/Documents/URBANISMO/work/lote_redes/diag_gap_real2.txt" "w"))
(defun wl (m) (write-line m pf))
;; indexar cajas MT por ID (via mp:att-alist, que mezcla ATTRIB+XDATA)
(setq cajas nil)
(setq ss2 (ssget "_X" '((0 . "INSERT") (2 . "MP_PUNTO_CAMARA_CS276,MP_PUNTO_CAMARA_CS280"))))
(setq n2 (if ss2 (sslength ss2) 0) j 0)
(while (< j n2)
  (setq e2 (ssname ss2 j))
  (setq atts (mp:att-alist e2))
  (setq idv (cdr (assoc "ID" atts)))
  (if idv (setq cajas (cons (cons idv (cdr (assoc 10 (entget e2)))) cajas)))
  (setq j (1+ j)))
(wl (strcat "Cajas MT indexadas: " (itoa (length cajas))))
(setq ss (ssget "_X" '((0 . "INSERT") (2 . "MP_TRAMO_MT_*"))))
(setq n (if ss (sslength ss) 0) i 0 cnt 0 sinmatch 0)
(while (< i n)
  (setq e (ssname ss i) ed (entget e))
  (setq bn (cdr (assoc 2 ed)) ip (cdr (assoc 10 ed)) rot (cdr (assoc 50 ed)))
  (setq distv (atof (vl-string-translate "_" "." (substr bn (+ 4 (vl-string-search "MT_" bn))))))
  (setq atts (mp:att-alist e))
  (setq pini (cdr (assoc "POZO_INI" atts)) pfin (cdr (assoc "POZO_FIN" atts))
        lngv (cdr (assoc "LONGITUD" atts)))
  (if (and pini pfin (assoc pini cajas) (assoc pfin cajas))
    (if (< cnt 6)
      (progn
        (setq cnt (1+ cnt))
        (setq pc1 (cdr (assoc pini cajas)) pc2 (cdr (assoc pfin cajas)))
        (setq dist-real (sqrt (+ (expt (- (car pc2) (car pc1)) 2)
                                 (expt (- (cadr pc2) (cadr pc1)) 2))))
        (setq blkrec (tblsearch "BLOCK" bn))
        (setq be (cdr (assoc -2 blkrec)) x0 nil x1 nil)
        (while be
          (setq bd (entget be))
          (if (= (cdr (assoc 0 bd)) "LWPOLYLINE")
            (progn
              (setq pts nil)
              (foreach par bd (if (= (car par) 10) (setq pts (cons (cadr par) pts))))
              (setq x0 (apply 'min pts) x1 (apply 'max pts))))
          (setq be (entnext be)))
        (setq wx0 (+ (car ip) (* x0 (cos rot))) wy0 (+ (cadr ip) (* x0 (sin rot))))
        (setq wx1 (+ (car ip) (* x1 (cos rot))) wy1 (+ (cadr ip) (* x1 (sin rot))))
        (setq gap-ini (sqrt (+ (expt (- wx0 (car pc1)) 2) (expt (- wy0 (cadr pc1)) 2))))
        (setq gap-fin (sqrt (+ (expt (- wx1 (car pc2)) 2) (expt (- wy1 (cadr pc2)) 2))))
        (wl (strcat "=== " bn " (" pini "-" pfin ") handle=" (cdr (assoc 5 ed)) " ==="))
        (wl (strcat "  LONGITUD-attr=" (if lngv lngv "?") " | distv-nombre=" (rtos distv 2 2)
          " | dist-real-cajas=" (rtos dist-real 2 3)))
        (wl (strcat "  def local: x0=" (rtos x0 2 3) " x1=" (rtos x1 2 3)))
        (wl (strcat "  GAP real inicio (" pini "): " (rtos gap-ini 2 3) " m"))
        (wl (strcat "  GAP real final (" pfin "): " (rtos gap-fin 2 3) " m"))))
    (setq sinmatch (1+ sinmatch)))
  (setq i (1+ i)))
(wl (strcat "Tramos sin match pozo_ini/fin en cajas: " (itoa sinmatch) " de " (itoa n)))
(wl "DIAGGAP2-OK")
(close pf)
(princ)
