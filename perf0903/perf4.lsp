;;; perf4 - desglose de fases del export (donde se van los 21-27 min)
(defun p4:log (msg / f)
  (setq f (open "C:/Users/jdbus/Documents/URBANISMO/work/perf0903/perf4.txt" "a"))
  (if f (progn (write-line msg f) (close f)))
  (princ (strcat "\n" msg)) (princ))
(defun p4:sec (t0) (rtos (/ (- (getvar "MILLISECS") t0) 1000.0) 2 1))
(defun c:PERF4 (/ t0 path attach app wb propia lo vocab raw dwg final t1)
  (vl-load-com)
  (setq path (urb:ppto-config-read))
  (p4:log (strcat "libro: " path))
  (setq t0 (getvar "MILLISECS"))
  (setq attach (urb:ppto-attach-excel path)
        app (nth 0 attach) wb (nth 1 attach) propia (nth 2 attach))
  (p4:log (strcat "FASE abrir Excel: " (p4:sec t0) " s"))
  (if (null wb) (progn (p4:log "NO ABRIO") (exit)))
  (setq t0 (getvar "MILLISECS"))
  (setq lo (urb:ppto-memorias-table wb))
  (setq vocab (urb:ppto-read-vocab wb))
  (setq *urb-ppto-vocab* vocab *urb-ppto-wb* wb
        *urb-ppto-param* (urb:ppto-param-read wb)
        *urb-ppto-param-dirty* nil
        *urb-ppto-equiv* (urb:ppto-equiv-read wb))
  (p4:log (strcat "FASE leer vocab/equiv/param (" (itoa (length vocab))
    " actividades): " (p4:sec t0) " s"))
  ;; generacion por grupo
  (setq t0 (getvar "MILLISECS")) (setq raw (urb:ppto-rows-vias))
  (p4:log (strcat "FASE filas VIAS (" (itoa (length raw)) "): " (p4:sec t0) " s"))
  (setq t0 (getvar "MILLISECS")) (setq raw (append raw (urb:ppto-rows-andenes)))
  (p4:log (strcat "FASE filas ANDENES: " (p4:sec t0) " s"))
  (setq t0 (getvar "MILLISECS")) (setq raw (append raw (urb:ppto-rows-prefabs)))
  (p4:log (strcat "FASE filas PREFABS: " (p4:sec t0) " s"))
  (setq t0 (getvar "MILLISECS")) (setq raw (append raw (urb:ppto-rows-rampas)))
  (p4:log (strcat "FASE filas RAMPAS: " (p4:sec t0) " s"))
  (setq t0 (getvar "MILLISECS")) (setq raw (append raw (urb:ppto-rows-tramos)))
  (p4:log (strcat "FASE filas TRAMOS: " (p4:sec t0) " s"))
  (setq t0 (getvar "MILLISECS")) (setq raw (append raw (urb:ppto-rows-puntos)))
  (p4:log (strcat "FASE filas PUNTOS: " (p4:sec t0) " s"))
  (setq t0 (getvar "MILLISECS")) (setq raw (append raw (urb:ppto-rows-mobiliario)))
  (p4:log (strcat "FASE filas MOBILIARIO: " (p4:sec t0) " s"))
  (setq t0 (getvar "MILLISECS")) (setq raw (append raw (urb:ppto-rows-senderos)))
  (p4:log (strcat "FASE filas SENDEROS: " (p4:sec t0) " s"))
  (setq t0 (getvar "MILLISECS")) (setq raw (append raw (urb:ppto-rows-bioswale)))
  (p4:log (strcat "FASE filas BIOSWALE: " (p4:sec t0) " s"))
  (p4:log (strcat "TOTAL filas crudas: " (itoa (length raw))))
  ;; match
  (setq dwg (vl-filename-base (getvar "DWGNAME")))
  (setq t0 (getvar "MILLISECS"))
  (setq final (urb:ppto-match-all raw vocab dwg))
  (p4:log (strcat "FASE match-all (" (itoa (length final)) " ok): "
    (p4:sec t0) " s"))
  ;; escritura masiva
  (setq t0 (getvar "MILLISECS"))
  (urb:ppto-write-rows lo final dwg)
  (p4:log (strcat "FASE escritura masiva: " (p4:sec t0) " s"))
  ;; guardar y cerrar
  (setq t0 (getvar "MILLISECS"))
  (vl-catch-all-apply '(lambda () (vlax-invoke-method wb 'Save)))
  (p4:log (strcat "FASE guardar libro: " (p4:sec t0) " s"))
  (vl-catch-all-apply '(lambda () (vlax-invoke-method wb 'Close :vlax-false)))
  (if propia (vl-catch-all-apply '(lambda () (vlax-invoke-method app 'Quit))))
  (p4:log "FIN-PERF4")
  (princ))
(princ "\nperf4 listo")(princ)
